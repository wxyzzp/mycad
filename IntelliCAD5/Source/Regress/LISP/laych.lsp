(defun c:laych()
(setq lay (tblnext "Layer" T) n 0)
(setq layname (cdr (assoc 2 lay)))
(while (/= lay nil)
(princ "\n No of Entities in Layer ")(princ layname)(princ " is ")(princ)
(setq ssa (ssget "X" (list (cons 8 layname))))
(if (not ssa)
(setq ssl 0)
(progn
(setq ssl (sslength ssa))
)
)
(princ ssl)

(setq lay (tblnext "Layer"))
(setq layname (cdr (assoc 2 lay)))
)
(princ)
)
