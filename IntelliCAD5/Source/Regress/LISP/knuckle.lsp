;;;;;;;;;;;This_Lisp_is_created_by_Srinivas_Chavan;;;;;;;;;;;;
(defun c:knj ()
  (command "layer" "color" "red" "" "")
  (setq d (getdist "\nENTER THE DIAMETER OF ROD :"))
  (setq	d2 (* 2 d)
	d3 (* 1.5 d)
	t0  (* 1.25 d)
	t1 (* 0.75 d)
	t2 (* 0.5 d)
  )
  (setq p1 (getpoint "\nENTER THE INSERTION POINT :"))
  (command "text" p1 (* 0.1 d) 0 "1")
  (command "chprop" "L" "" "color" "cyan" "")
  (setq	p50 (polar p1 0 (/ d 2))
	p51 (polar p50 (/ pi 2) (* 0.5 d))
  )
  (command "text" p50 (* 0.1 d) 0 "50")
  (command "chprop" "L" "" "color" "cyan" "")
  (command "text" p51 (* 0.1 d) 0 "51")
  (command "chprop" "L" "" "color" "cyan" "")
  (command "line"
	   (polar p50 (/ pi -2) (* 0.2 d))
	   (polar p50 (/ pi 2) (* d 4.2))
	   ""
  )
  (command "chprop" "L" "" "lt" "center" "color" "blue" "")
  (command "circle" p51 "D" (/ t2 2))
  (command "line" 
	   (polar p51 pi (/ t2 2))
	   (polar p51 0 (/ t2 2))
	   ""
  )
  (command "chprop" "L" "" "lt" "center" "color" "yellow" "")
  (setq	p2 (polar p1 0 d)
	p3 (polar p2 (/ pi 2) (* 0.25 d))
  )
  (setq	p4 (polar p3 0 (* 0.25 d))
	p5 (polar p3 pi d)
  )
  (command "text" p2 (* 0.1 d) 0 "2")
  (command "chprop" "L" "" "color" "cyan" "")
  (command "text" p3 (* 0.1 d) 0 "3")
  (command "chprop" "L" "" "color" "cyan" "")
  (command "text" p4 (* 0.1 d) 0 "4")
  (command "chprop" "L" "" "color" "cyan" "")
  (command "text" p5 (* 0.1 d) 0 "5")
  (command "chprop" "L" "" "color" "cyan" "")
  (command "line" p3 (polar p3 (/ pi 2) (* 3.2 d)) "")
  (command "chprop" "l" "" "lt" "hidden" "color" "green" "")
  (command "line" p5 (polar p5 (/ pi 2) (* 3.2 d)) "")
  (command "chprop" "l" "" "lt" "hidden" "color" "green" "")
  (setq	p6 (polar p4 pi d3)
	p7 (polar p6 (/ pi 2) t2)
	p8 (polar p7 0 d3)
  )
  (command "line" p1 p2 p3 p4 p8 p7 p6 p3 "")
  (command "line" p1 p5 "")
  (setq	p9  (polar p8 0 (* 0.25 d))
	p10 (polar p9 (/ pi 2) t1)
  )
  (setq	p11 (polar p10 pi d2)
	p12 (polar p11 (/ pi -2) t1)
  )
  (command "text" p6 (* 0.1 d) 0 "6")
  (command "chprop" "L" "" "color" "cyan" "")
  (command "text" p7 (* 0.1 d) 0 "7")
  (command "chprop" "L" "" "color" "cyan" "")
  (command "text" p8 (* 0.1 d) 0 "8")
  (command "chprop" "L" "" "color" "cyan" "")
  (command "text" p9 (* 0.1 d) 0 "9")
  (command "chprop" "L" "" "color" "cyan" "")
  (command "text" p10 (* 0.1 d) 0 "10")
  (command "chprop" "L" "" "color" "cyan" "")
  (command "text" p11 (* 0.1 d) 0 "11")
  (command "chprop" "L" "" "color" "cyan" "")
  (command "text" p12 (* 0.1 d) 0 "12")
  (command "chprop" "L" "" "color" "cyan" "")
  (command "line" p7 p12 (polar p12 (/ pi 2) (* d 0.15)) "")
  (command "line" p8 p9 p10 p11 "")
  (setq	p13 (polar p11 (/ pi 2) (* d 1.2))
	p14 (polar p13 0 d2)
  )
  (setq	p15 (polar p14 (/ pi 2) t1)
	p16 (polar p15 pi d2)
  )
  (setq	p17 (list (car p8) (cadr p15))
	p18 (polar p17 pi d3)
  )
  (setq	p19 (polar p17 (/ pi 2) t2)
	p20 (polar p19 pi d3)
  )
  (command "text" p13 (* 0.1 d) 0 "13")
  (command "chprop" "L" "" "color" "cyan" "")
  (command "text" p14 (* 0.1 d) 0 "14")
  (command "chprop" "L" "" "color" "cyan" "")
  (command "text" p15 (* 0.1 d) 0 "15")
  (command "chprop" "L" "" "color" "cyan" "")
  (command "text" p16 (* 0.1 d) 0 "16")
  (command "chprop" "L" "" "color" "cyan" "")
  (command "text" p17 (* 0.1 d) 0 "17")
  (command "chprop" "L" "" "color" "cyan" "")
  (command "text" p18 (* 0.1 d) 0 "18")
  (command "chprop" "L" "" "color" "cyan" "")
  (command "text" p19 (* 0.1 d) 0 "19")
  (command "chprop" "L" "" "color" "cyan" "")
  (command "text" p20 (* 0.1 d) 0 "20")
  (command "chprop" "L" "" "color" "cyan" "")
  (command "line"
	   p11
	   p13
	   p14
	   p15
	   p16
	   (polar p16 (/ pi -2) (* d 0.15))
	   ""
  )
  (command "line" p17 p19 p20 p18 "")
  (setq p21 (list (- (car p12) (* d 0.2)) (+ (cadr p10) (* 0.6 d))))
  (setq p22 (list (- (car p21) (* d 0.6)) (cadr p21)))
  (setq p23 (list (car p21) (+ (cadr p21) (* 0.6 d))))
  (setq p24 (list (car p21) (- (cadr p21) (* 0.6 d))))
  (command "text" p21 (* 0.1 d) 0 "21")
  (command "chprop" "L" "" "color" "cyan" "")
  (command "text" p22 (* 0.1 d) 0 "22")
  (command "chprop" "L" "" "color" "cyan" "")
  (command "text" p23 (* 0.1 d) 0 "23")
  (command "chprop" "L" "" "color" "cyan" "")
  (command "text" p24 (* 0.1 d) 0 "24")
  (command "chprop" "L" "" "color" "cyan" "")
  (command "arc" p23 p22 p24)
  (command "line" p23 p13 "")
  (command "line" p24 p11 "")
  (setq	p25 (list (+ (car p12) d) (cadr p21))
	p26 (list (- (car p25) (* d 4.5)) (cadr p25))
  )
  (setq	p27 (polar p26 (/ pi 2) (* d 0.6))
	p28 (polar p26 (/ pi -2) (* d 0.6))
  )
  (setq p29 (list (+ (car p25) (* d 4)) (cadr p25)))
  (command "text" p25 (* 0.1 d) 0 "25")
  (command "chprop" "L" "" "color" "cyan" "")
  (command "text" p26 (* 0.1 d) 0 "26")
  (command "chprop" "L" "" "color" "cyan" "")
  (command "text" p27 (* 0.1 d) 0 "27")
  (command "chprop" "L" "" "color" "cyan" "")
  (command "text" p28 (* 0.1 d) 0 "28")
  (command "chprop" "L" "" "color" "cyan" "")
  (command "text" p29 (* 0.1 d) 0 "29")
  (command "chprop" "L" "" "color" "cyan" "")
  (command "line"
	   (polar p26 pi (* d 1.45))
	   (polar p29 0 (* d 1.45))
	   ""
  )
  (command "chprop" "l" "" "lt" "center" "color" "blue" "")
  (setq	p30 (polar p29 (/ pi 2) (* d 0.55))
	p31 (polar p29 (/ pi -2) (* 0.55 d))
  )
  (setq	p32 (polar p30 pi (* d 1.2))
	p33 (polar p31 pi (* 1.2 d))
  )
  (setq	p34 (polar p27 0 (* d 1.2))
	p35 (polar p28 0 (* 1.2 d))
  )
  (command "text" p30 (* 0.1 d) 0 "30")
  (command "chprop" "L" "" "color" "cyan" "")
  (command "text" p31 (* 0.1 d) 0 "31")
  (command "chprop" "L" "" "color" "cyan" "")
  (command "text" p32 (* 0.1 d) 0 "32")
  (command "chprop" "L" "" "color" "cyan" "")
  (command "text" p33 (* 0.1 d) 0 "33")
  (command "chprop" "L" "" "color" "cyan" "")
  (command "text" p34 (* 0.1 d) 0 "34")
  (command "chprop" "L" "" "color" "cyan" "")
  (command "text" p35 (* 0.1 d) 0 "35")
  (command "chprop" "L" "" "color" "cyan" "")
  (command "line" p27 p28 p35 p34 "c")
  (command "line" p30 p31 p33 p32 "c")
  (setq	p36 (polar p26 (/ pi 2) (/ d 2))
	p37 (polar p26 (/ pi -2) (/ d 2))
  )
  (setq	p38 (polar p29 (/ pi 2) (/ d 2))
	p39 (polar p29 (/ pi -2) (/ d 2))
  )
  (command "text" p36 (* 0.1 d) 0 "36")
  (command "chprop" "L" "" "color" "cyan" "")
  (command "text" p37 (* 0.1 d) 0 "37")
  (command "chprop" "L" "" "color" "cyan" "")
  (command "text" p38 (* 0.1 d) 0 "38")
  (command "chprop" "L" "" "color" "cyan" "")
  (command "text" p39 (* 0.1 d) 0 "39")
  (command "chprop" "L" "" "color" "cyan" "")
  (command "line" p37 (polar p37 pi t0) "")
  (command "line" p36 (polar p36 pi t0) "")
  (command "line" p38 (polar p38 0 t0) "")
  (command "line" p39 (polar p39 0 t0) "")
  (setq p40 (list (car p21) (+ (cadr p21) (* d 1.2))))
  (setq p41 (list (car p21) (- (cadr p21) (* d 1.2))))
  (setq	p42 (list (- (car p21) (* d 1.039230485))
		  (+ (cadr p21) (* d 0.6))
	    )
  )
  (command "text" p40 (* 0.1 d) 0 "40")
  (command "chprop" "L" "" "color" "cyan" "")
  (command "text" p41 (* 0.1 d) 0 "41")
  (command "chprop" "L" "" "color" "cyan" "")
  (command "text" p42 (* 0.1 d) 0 "42")
  (command "chprop" "L" "" "color" "cyan" "")
  (command "arc" p40 "c" p21 p42)
  (setq	p43 (list (- (car p21) (* d 1.039230485))
		  (- (cadr p21) (* d 0.6))
	    )
  )
  (command "text" p43 (* 0.1 d) 0 "43")
  (command "chprop" "L" "" "color" "cyan" "")
  (command "arc" p43 "c" p21 p41)
  (command "line" p34 p42 "")
  (command "line" p35 p43 "")
  (command "line"
	   (polar p27 (/ pi -2) (* d 0.25))
	   (polar p34 (/ pi -2) (* d 0.25))
	   ""
  )
  (command "line"
	   (polar p28 (/ pi 2) (* d 0.25))
	   (polar p35 (/ pi 2) (* d 0.25))
	   ""
  )
  (command "line"
	   (polar p32 (/ pi -2) (* d 0.23))
	   (polar p30 (/ pi -2) (* d 0.23))
	   ""
  )
  (command "line"
	   (polar p33 (/ pi 2) (* d 0.23))
	   (polar p31 (/ pi 2) (* d 0.23))
	   ""
  )
  (setq	p44 (polar p40 0 d)
	p45 (polar p41 0 d)
  )
  (command "text" p44 (* 0.1 d) 0 "44")
  (command "chprop" "L" "" "color" "cyan" "")
  (command "text" p45 (* 0.1 d) 0 "45")
  (command "chprop" "L" "" "color" "cyan" "")
  (command "line" p40 p44 (polar p44 (/ pi 2) (* d 0.15)) "")
  (command "line" p41 p45 (polar p45 (/ pi -2) (* d 0.15)) "")
  (setq	p46 (polar p32 pi (* d 1.8))
	p47 (polar p33 pi (* d 1.8))
  )
  (command "text" p46 (* 0.1 d) 0 "46")
  (command "chprop" "L" "" "color" "cyan" "")
  (command "text" p47 (* 0.1 d) 0 "47")
  (command "chprop" "L" "" "color" "cyan" "")
  (command "line" p32 p46 (polar p46 (/ pi 2) (* d 0.075)) "")
  (command "line"
	   p33
	   p47
	   (polar p47 (/ pi -2) (* d 0.075))
	   ""
  )
  (setq p1 (polar p36 pi t0))
  (setq	p2 (polar p1 (/ pi -2) (/ d 2))
	p3 (list (- (car p2) (* d 0.125)) (+ (cadr p2) (* d 0.25)))
	p4 (polar p3 (/ pi -2) (/ d 2))
	p5 (polar p1 (/ pi -2) d)
	p6 (polar p4 0 (* d 0.25))
  )
  (command "text" p1 (* 0.1 d) 0 "1")
  (command "chprop" "L" "" "color" "cyan" "")
  (command "text" p2 (* 0.1 d) 0 "2")
  (command "chprop" "L" "" "color" "cyan" "")
  (command "text" p3 (* 0.1 d) 0 "3")
  (command "chprop" "L" "" "color" "cyan" "")
  (command "text" p4 (* 0.1 d) 0 "4")
  (command "chprop" "L" "" "color" "cyan" "")
  (command "text" p5 (* 0.1 d) 0 "5")
  (command "chprop" "L" "" "color" "cyan" "")
  (command "text" p6 (* 0.1 d) 0 "6")
  (command "chprop" "L" "" "color" "cyan" "")
  (command "arc" p1 p3 p2)
  (command "arc" p2 p4 p5)
  (command "arc" p5 p6 p2)
  (command "hatch" "u" 45 (* d 0.1) "n" p4 p6 "")
  (setq p1 (polar p39 0 t0))
  (setq	p2 (polar p1 (/ pi 2) (/ d 2))
	p3 (list (+ (car p1) (* d 0.125)) (+ (cadr p1) (* d 0.25)))
	p4 (polar p3 (/ pi 2) (/ d 2))
	p5 (polar p1 (/ pi 2) d)
	p6 (polar p4 pi (* d 0.25))
  )
  (command "text" p1 (* 0.1 d) 0 "1")
  (command "chprop" "L" "" "color" "cyan" "")
  (command "text" p2 (* 0.1 d) 0 "2")
  (command "chprop" "L" "" "color" "cyan" "")
  (command "text" p3 (* 0.1 d) 0 "3")
  (command "chprop" "L" "" "color" "cyan" "")
  (command "text" p4 (* 0.1 d) 0 "4")
  (command "chprop" "L" "" "color" "cyan" "")
  (command "text" p5 (* 0.1 d) 0 "5")
  (command "chprop" "L" "" "color" "cyan" "")
  (command "text" p6 (* 0.1 d) 0 "6")
  (command "chprop" "L" "" "color" "cyan" "")
  (command "arc" p1 p3 p2)
  (command "arc" p2 p4 p5)
  (command "arc" p5 p6 p2)
  (command "hatch" "u" 45 (* d 0.1) "n" p4 p6 "")
)
