(defun checkXDataExists	(entHand appName)
  (setq checkResult nil)
  (foreach va
	      (assoc (- 3)
		     (entget entHand '("*"))
	      )
    (if	(listp va)
      (if (= (car va) appName)
	(setq checkResult T)
      )
    )
  )
  checkResult
)
(defun addxdata	(enHand appname type val)
  (setq endata (entget enHand))
  (regapp appname)
  (setq xd nil)
  (setq xd (cons type val))
  (setq xd (list appname xd))
  (setq xd (list (list (- 3) xd)))
  (setq endata (append endata xd))
  (entmod endata)
  (princ)
)
(defun appendXdata (enHand appname type val)
  (setq endata (entget enHand))
  (regapp appname)
  (setq xd nil)
  (setq xd (cons type val))
  (setq xd (list appname xd))
  (foreach va
	      (assoc (- 3)
		     (entget enHand '("*"))
	      )
    (if	(listp va)
      (append xd va)
    )
  )
  (princ xd)
  (setq xd (list (list (- 3) xd)))
  (setq endata (append endata xd))
  (entmod endata)
  (princ)
)
