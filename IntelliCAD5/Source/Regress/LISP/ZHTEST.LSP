(defun zhtest()
 (setq p1 (list -100000000.00 -100000000.00) p2 (list 100000000.00 100000000.00))
 (command "LINE" p1 p2 "")
 (command "ZOOM" "E")
 (command "ERASE" p1 "")
 (command "LAYER" "NEW" "CGBMAIN" "SET" "CGBMAIN" "COLOR" "CYAN" "" "")
 (command "LAYER" "NEW" "CGBCMNT" "SET" "CGBCMNT" "COLOR" "142" "" "")
 (command "LAYER" "NEW" "CGBHLHDR" "SET" "CGBHLHDR" "COLOR" "YELLOW" "" "")
 (command "LAYER" "NEW" "CGBHZID" "SET" "CGBHZID" "COLOR" "36" "" "")
 (command "LAYER" "NEW" "CGBLITHCD" "SET" "CGBLITHCD" "COLOR" "55" "" "")
 (command "LAYER" "NEW" "CGBLITHTXT" "SET" "CGBLITHTXT" "COLOR" "95" "" "")
 (command "LAYER" "NEW" "CGBTHK" "SET" "CGBTHK" "COLOR" "95" "" "")
 (command "LAYER" "NEW" "CGBSEAM" "SET" "CGBSEAM" "COLOR" "WHITE" "" "")
 (command "LAYER" "S" "CGBMAIN" "")
 (setq p1 (list 107.00 1953.25) p2 (list 113.00 1953.25) p3 (list 113.00 1935.25) p4 (list 107.00 1935.25))
 (command "PLINE" p1 p2 p3 p4 "c")
 (command "LINE" p1 p3 "")
 (command "LINE" p2 p4 "")
 (command "COLOR" "BYLAYER")
 (command "LAYER" "S" "CGBLITHCD" "")
 (setq p1 (list 113.00 1944.25) p2 (list 114.35 1944.25))
 (command "LINE" p1 p2 "")
 (setq p1 (list 114.50 1943.88) p2 (list 0.00 0.00))
 (command "TEXT" "J" "ML" p1   0.75  0.00 "001")
 (command "LAYER" "S" "CGBTHK" "")
 (setq p1 (list 119.00 1943.88) p2 (list 0.00 0.00))
 (command "TEXT" "J" "ML" p1   0.75  0.00 "18.00")
 (command "LAYER" "S" "CGBHZID" "")
 (setq p1 (list 123.50 1943.88) p2 (list 0.00 0.00))
 (command "TEXT" "J" "ML" p1   0.75  0.00 "")
 (setq p1 (list 125.75 1943.88) p2 (list 0.00 0.00))
 (command "TEXT" "J" "ML" p1   0.75  0.00 "9990")
 (command "LAYER" "S" "CGBLITHTXT" "")
 (setq p1 (list 129.50 1943.88) p2 (list 0.00 0.00))
 (command "TEXT" "J" "ML" p1   0.75  0.00 "CASING")
 (command "LAYER" "S" "CGBCMNT" "")
 (setq p1 (list 149.75 1943.88) p2 (list 0.00 0.00))
 (command "TEXT" "J" "ML" p1   0.75  0.00 "")
 (command "LAYER" "S" "CGBMAIN" "")
 (setq p1 (list 107.00 1935.25) p2 (list 113.00 1935.25) p3 (list 113.00 1923.25) p4 (list 107.00 1923.25))
 (command "PLINE" p1 p2 p3 p4 "c")
 (command "LINE" p1 p3 "")
 (command "LINE" p2 p4 "")
 (command "COLOR" "BYLAYER")
 (command "LAYER" "S" "CGBLITHCD" "")
 (setq p1 (list 113.00 1929.25) p2 (list 114.35 1929.25))
 (command "LINE" p1 p2 "")
 (setq p1 (list 114.50 1928.88) p2 (list 0.00 0.00))
 (command "TEXT" "J" "ML" p1   0.75  0.00 "001")
 (command "LAYER" "S" "CGBTHK" "")
 (setq p1 (list 119.00 1928.88) p2 (list 0.00 0.00))
 (command "TEXT" "J" "ML" p1   0.75  0.00 "12.00")
 (command "LAYER" "S" "CGBHZID" "")
 (setq p1 (list 123.50 1928.88) p2 (list 0.00 0.00))
 (command "TEXT" "J" "ML" p1   0.75  0.00 "")
 (setq p1 (list 125.75 1928.88) p2 (list 0.00 0.00))
 (command "TEXT" "J" "ML" p1   0.75  0.00 "9990")
 (command "LAYER" "S" "CGBLITHTXT" "")
 (setq p1 (list 129.50 1928.88) p2 (list 0.00 0.00))
 (command "TEXT" "J" "ML" p1   0.75  0.00 "CASING")
 (command "LAYER" "S" "CGBCMNT" "")
 (setq p1 (list 149.75 1928.88) p2 (list 0.00 0.00))
 (command "TEXT" "J" "ML" p1   0.75  0.00 "CASING")
 (command "LAYER" "S" "CGBMAIN" "")
 (setq p1 (list 107.00 1923.25) p2 (list 113.00 1923.25) p3 (list 113.00 1903.25) p4 (list 107.00 1903.25))
 (command "PLINE" p1 p2 p3 p4 "c")
 (command "HATCH" "ZIGZAG" 2.50 90.00 "L" "")
 (command "COLOR" "BYLAYER")
 (command "LAYER" "S" "CGBLITHCD" "")
 (setq p1 (list 113.00 1913.25) p2 (list 114.35 1913.25))
 (command "LINE" p1 p2 "")
 (setq p1 (list 114.50 1912.88) p2 (list 0.00 0.00))
 (command "TEXT" "J" "ML" p1   0.75  0.00 "320")
 (command "LAYER" "S" "CGBTHK" "")
 (setq p1 (list 119.00 1912.88) p2 (list 0.00 0.00))
 (command "TEXT" "J" "ML" p1   0.75  0.00 "20.00")
 (command "LAYER" "S" "CGBHZID" "")
 (setq p1 (list 123.50 1912.88) p2 (list 0.00 0.00))
 (command "TEXT" "J" "ML" p1   0.75  0.00 "")
 (setq p1 (list 125.75 1912.88) p2 (list 0.00 0.00))
 (command "TEXT" "J" "ML" p1   0.75  0.00 "9990")
 (command "LAYER" "S" "CGBLITHTXT" "")
 (setq p1 (list 129.50 1912.88) p2 (list 0.00 0.00))
 (command "TEXT" "J" "ML" p1   0.75  0.00 "DRK GRY SDY SH")
 (command "LAYER" "S" "CGBCMNT" "")
 (setq p1 (list 149.75 1912.88) p2 (list 0.00 0.00))
 (command "TEXT" "J" "ML" p1   0.75  0.00 "CHIPPED")
 (command "LAYER" "S" "CGBMAIN" "")
 (setq p1 (list 107.00 1903.25) p2 (list 113.00 1903.25) p3 (list 113.00 1897.88) p4 (list 107.00 1897.88))
 (command "PLINE" p1 p2 p3 p4 "c")
 (command "HATCH" "ZIGZAG" 4.00 0.00 "L" "")
 (command "COLOR" "BYLAYER")
 (command "LAYER" "S" "CGBLITHCD" "")
 (setq p1 (list 113.00 1900.57) p2 (list 114.35 1900.57))
 (command "LINE" p1 p2 "")
 (setq p1 (list 114.50 1900.19) p2 (list 0.00 0.00))
 (command "TEXT" "J" "ML" p1   0.75  0.00 "124")
 (command "LAYER" "S" "CGBTHK" "")
 (setq p1 (list 119.00 1900.19) p2 (list 0.00 0.00))
 (command "TEXT" "J" "ML" p1   0.75  0.00 "5.37")
 (command "LAYER" "S" "CGBHZID" "")
 (setq p1 (list 123.50 1900.19) p2 (list 0.00 0.00))
 (command "TEXT" "J" "ML" p1   0.75  0.00 "")
 (setq p1 (list 125.75 1900.19) p2 (list 0.00 0.00))
 (command "TEXT" "J" "ML" p1   0.75  0.00 "9990")
 (command "LAYER" "S" "CGBLITHTXT" "")
 (setq p1 (list 129.50 1900.19) p2 (list 0.00 0.00))
 (command "TEXT" "J" "ML" p1   0.75  0.00 "DRK GRY SH")
 (command "LAYER" "S" "CGBCMNT" "")
 (setq p1 (list 149.75 1900.19) p2 (list 0.00 0.00))
 (command "TEXT" "J" "ML" p1   0.75  0.00 "BDLY WTHRD S&")
 (command "LAYER" "S" "CGBMAIN" "")
 (setq p1 (list 107.00 1897.88) p2 (list 113.00 1897.88) p3 (list 113.00 1894.35) p4 (list 107.00 1894.35))
 (command "PLINE" p1 p2 p3 p4 "c")
 (command "HATCH" "ZIGZAG" 0.25 0.00 "L" "")
 (command "COLOR" "BYLAYER")
 (command "LAYER" "S" "CGBLITHCD" "")
 (setq p1 (list 113.00 1896.12) p2 (list 114.35 1896.12))
 (command "LINE" p1 p2 "")
 (setq p1 (list 114.50 1895.74) p2 (list 0.00 0.00))
 (command "TEXT" "J" "ML" p1   0.75  0.00 "127")
 (command "LAYER" "S" "CGBTHK" "")
 (setq p1 (list 119.00 1895.74) p2 (list 0.00 0.00))
 (command "TEXT" "J" "ML" p1   0.75  0.00 "3.53")
 (command "LAYER" "S" "CGBHZID" "")
 (setq p1 (list 123.50 1895.74) p2 (list 0.00 0.00))
 (command "TEXT" "J" "ML" p1   0.75  0.00 "")
 (setq p1 (list 125.75 1895.74) p2 (list 0.00 0.00))
 (command "TEXT" "J" "ML" p1   0.75  0.00 "9990")
 (command "LAYER" "S" "CGBLITHTXT" "")
 (setq p1 (list 129.50 1895.74) p2 (list 0.00 0.00))
 (command "TEXT" "J" "ML" p1   0.75  0.00 "DRK GRY FIRECLAY")
 (command "LAYER" "S" "CGBCMNT" "")
 (setq p1 (list 149.75 1895.74) p2 (list 0.00 0.00))
 (command "TEXT" "J" "ML" p1   0.75  0.00 "BRKN WTHRD")
 (command "LAYER" "S" "CGBMAIN" "")
 (setq p1 (list 107.00 1894.35) p2 (list 113.00 1894.35) p3 (list 113.00 1893.51) p4 (list 107.00 1893.51))
 (command "PLINE" p1 p2 p3 p4 "c")
 (command "HATCH" "ZIGZAG" 5.00 0.00 "L" "")
 (command "COLOR" "BYLAYER")
 (command "LAYER" "S" "CGBLITHCD" "")
 (setq p1 (list 113.00 1893.93) p2 (list 114.35 1893.93))
 (command "LINE" p1 p2 "")
 (setq p1 (list 114.50 1893.56) p2 (list 0.00 0.00))
 (command "TEXT" "J" "ML" p1   0.75  0.00 "137")
 (command "LAYER" "S" "CGBTHK" "")
 (setq p1 (list 119.00 1893.56) p2 (list 0.00 0.00))
 (command "TEXT" "J" "ML" p1   0.75  0.00 "0.84")
 (command "LAYER" "S" "CGBHZID" "")
 (setq p1 (list 123.50 1893.56) p2 (list 0.00 0.00))
 (command "TEXT" "J" "ML" p1   0.75  0.00 "")
 (setq p1 (list 125.75 1893.56) p2 (list 0.00 0.00))
 (command "TEXT" "J" "ML" p1   0.75  0.00 "9990")
 (command "LAYER" "S" "CGBLITHTXT" "")
 (setq p1 (list 129.50 1893.56) p2 (list 0.00 0.00))
 (command "TEXT" "J" "ML" p1   0.75  0.00 "LT GRY GRN FIRECLAY")
 (command "LAYER" "S" "CGBCMNT" "")
 (setq p1 (list 149.75 1893.56) p2 (list 0.00 0.00))
 (command "TEXT" "J" "ML" p1   0.75  0.00 "SFT W/CRB LAY")
 (command "LAYER" "S" "CGBMAIN" "")
 (setq p1 (list 107.00 1893.51) p2 (list 113.00 1893.51) p3 (list 113.00 1891.37) p4 (list 107.00 1891.37))
 (command "PLINE" p1 p2 p3 p4 "c")
 (command "HATCH" "ZIGZAG" 5.00 0.00 "L" "")
 (command "COLOR" "BYLAYER")
 (command "LAYER" "S" "CGBLITHCD" "")
 (setq p1 (list 113.00 1892.44) p2 (list 114.35 1892.44))
 (command "LINE" p1 p2 "")
 (setq p1 (list 114.50 1892.07) p2 (list 0.00 0.00))
 (command "TEXT" "J" "ML" p1   0.75  0.00 "247")
 (command "LAYER" "S" "CGBTHK" "")
 (setq p1 (list 119.00 1892.07) p2 (list 0.00 0.00))
 (command "TEXT" "J" "ML" p1   0.75  0.00 "2.14")
 (command "LAYER" "S" "CGBHZID" "")
 (setq p1 (list 123.50 1892.07) p2 (list 0.00 0.00))
 (command "TEXT" "J" "ML" p1   0.75  0.00 "")
 (setq p1 (list 125.75 1892.07) p2 (list 0.00 0.00))
 (command "TEXT" "J" "ML" p1   0.75  0.00 "9990")
 (command "LAYER" "S" "CGBLITHTXT" "")
 (setq p1 (list 129.50 1892.07) p2 (list 0.00 0.00))
 (command "TEXT" "J" "ML" p1   0.75  0.00 "GRN CLYSTN W/LS NODS")
 (command "LAYER" "S" "CGBCMNT" "")
 (setq p1 (list 149.75 1892.07) p2 (list 0.00 0.00))
 (command "TEXT" "J" "ML" p1   0.75  0.00 "V SFT, PLASTC")
 (command "LAYER" "S" "CGBMAIN" "")
 (setq p1 (list 107.00 1891.37) p2 (list 113.00 1891.37) p3 (list 113.00 1889.05) p4 (list 107.00 1889.05))
 (command "PLINE" p1 p2 p3 p4 "c")
 (command "HATCH" "ZIGZAG" 4.00 0.00 "L" "")
 (command "COLOR" "BYLAYER")
 (command "LAYER" "S" "CGBLITHCD" "")
 (setq p1 (list 113.00 1890.21) p2 (list 114.35 1890.21))
 (command "LINE" p1 p2 "")
 (setq p1 (list 114.50 1889.84) p2 (list 0.00 0.00))
 (command "TEXT" "J" "ML" p1   0.75  0.00 "444")
 (command "LAYER" "S" "CGBTHK" "")
 (setq p1 (list 119.00 1889.84) p2 (list 0.00 0.00))
 (command "TEXT" "J" "ML" p1   0.75  0.00 "2.32")
 (command "LAYER" "S" "CGBHZID" "")
 (setq p1 (list 123.50 1889.84) p2 (list 0.00 0.00))
 (command "TEXT" "J" "ML" p1   0.75  0.00 "")
 (setq p1 (list 125.75 1889.84) p2 (list 0.00 0.00))
 (command "TEXT" "J" "ML" p1   0.75  0.00 "9990")
 (command "LAYER" "S" "CGBLITHTXT" "")
 (setq p1 (list 129.50 1889.84) p2 (list 0.00 0.00))
 (command "TEXT" "J" "ML" p1   0.75  0.00 "GRN SDY SH W/LS NODS")
 (command "LAYER" "S" "CGBCMNT" "")
 (setq p1 (list 149.75 1889.84) p2 (list 0.00 0.00))
 (command "TEXT" "J" "ML" p1   0.75  0.00 "CRMB")
 (command "LAYER" "S" "CGBMAIN" "")
 (setq p1 (list 107.00 1889.05) p2 (list 113.00 1889.05) p3 (list 113.00 1887.21) p4 (list 107.00 1887.21))
 (command "PLINE" p1 p2 p3 p4 "c")
 (command "HATCH" "ZIGZAG" 0.50 0.00 "L" "")
 (command "COLOR" "BYLAYER")
 (command "LAYER" "S" "CGBLITHCD" "")
 (setq p1 (list 113.00 1888.13) p2 (list 114.35 1888.13))
 (command "LINE" p1 p2 "")
 (setq p1 (list 114.50 1887.76) p2 (list 0.00 0.00))
 (command "TEXT" "J" "ML" p1   0.75  0.00 "806")
 (command "LAYER" "S" "CGBTHK" "")
 (setq p1 (list 119.00 1887.76) p2 (list 0.00 0.00))
 (command "TEXT" "J" "ML" p1   0.75  0.00 "1.84")
 (command "LAYER" "S" "CGBHZID" "")
 (setq p1 (list 123.50 1887.76) p2 (list 0.00 0.00))
 (command "TEXT" "J" "ML" p1   0.75  0.00 "")
 (setq p1 (list 125.75 1887.76) p2 (list 0.00 0.00))
 (command "TEXT" "J" "ML" p1   0.75  0.00 "9990")
 (command "LAYER" "S" "CGBLITHTXT" "")
 (setq p1 (list 129.50 1887.76) p2 (list 0.00 0.00))
 (command "TEXT" "J" "ML" p1   0.75  0.00 "FN GRND SHLY LS W/LS NODS")
 (command "LAYER" "S" "CGBCMNT" "")
 (setq p1 (list 149.75 1887.76) p2 (list 0.00 0.00))
 (command "TEXT" "J" "ML" p1   0.75  0.00 "")
 (command "LAYER" "S" "CGBMAIN" "")
 (setq p1 (list 107.00 1887.21) p2 (list 113.00 1887.21) p3 (list 113.00 1886.16) p4 (list 107.00 1886.16))
 (command "PLINE" p1 p2 p3 p4 "c")
 (command "HATCH" "ZIGZAG" 4.00 0.00 "L" "")
 (command "COLOR" "BYLAYER")
 (command "LAYER" "S" "CGBLITHCD" "")
 (setq p1 (list 113.00 1886.69) p2 (list 114.35 1886.69))
 (command "LINE" p1 p2 "")
 (setq p1 (list 114.50 1886.31) p2 (list 0.00 0.00))
 (command "TEXT" "J" "ML" p1   0.75  0.00 "444")
 (command "LAYER" "S" "CGBTHK" "")
 (setq p1 (list 119.00 1886.31) p2 (list 0.00 0.00))
 (command "TEXT" "J" "ML" p1   0.75  0.00 "1.05")
 (command "LAYER" "S" "CGBHZID" "")
 (setq p1 (list 123.50 1886.31) p2 (list 0.00 0.00))
 (command "TEXT" "J" "ML" p1   0.75  0.00 "")
 (setq p1 (list 125.75 1886.31) p2 (list 0.00 0.00))
 (command "TEXT" "J" "ML" p1   0.75  0.00 "9990")
 (command "LAYER" "S" "CGBLITHTXT" "")
 (setq p1 (list 129.50 1886.31) p2 (list 0.00 0.00))
 (command "TEXT" "J" "ML" p1   0.75  0.00 "GRN SDY SH W/LS NODS")
 (command "LAYER" "S" "CGBCMNT" "")
 (setq p1 (list 149.75 1886.31) p2 (list 0.00 0.00))
 (command "TEXT" "J" "ML" p1   0.75  0.00 "")
 (command "LAYER" "S" "CGBMAIN" "")
 (setq p1 (list 107.00 1886.16) p2 (list 113.00 1886.16) p3 (list 113.00 1880.22) p4 (list 107.00 1880.22))
 (command "PLINE" p1 p2 p3 p4 "c")
 (command "HATCH" "ZIGZAG" 4.00 0.00 "L" "")
 (command "COLOR" "BYLAYER")
 (command "LAYER" "S" "CGBLITHCD" "")
 (setq p1 (list 113.00 1883.19) p2 (list 114.35 1883.19))
 (command "LINE" p1 p2 "")
 (setq p1 (list 114.50 1882.82) p2 (list 0.00 0.00))
 (command "TEXT" "J" "ML" p1   0.75  0.00 "344")
 (command "LAYER" "S" "CGBTHK" "")
 (setq p1 (list 119.00 1882.82) p2 (list 0.00 0.00))
 (command "TEXT" "J" "ML" p1   0.75  0.00 "5.94")
 (command "LAYER" "S" "CGBHZID" "")
 (setq p1 (list 123.50 1882.82) p2 (list 0.00 0.00))
 (command "TEXT" "J" "ML" p1   0.75  0.00 "")
 (setq p1 (list 125.75 1882.82) p2 (list 0.00 0.00))
 (command "TEXT" "J" "ML" p1   0.75  0.00 "9990")
 (command "LAYER" "S" "CGBLITHTXT" "")
 (setq p1 (list 129.50 1882.82) p2 (list 0.00 0.00))
 (command "TEXT" "J" "ML" p1   0.75  0.00 "GRN MASS SDY SH")
 (command "LAYER" "S" "CGBCMNT" "")
 (setq p1 (list 149.75 1882.82) p2 (list 0.00 0.00))
 (command "TEXT" "J" "ML" p1   0.75  0.00 "GB")
 (command "LAYER" "S" "CGBMAIN" "")
 (setq p1 (list 107.00 1880.22) p2 (list 113.00 1880.22) p3 (list 113.00 1874.37) p4 (list 107.00 1874.37))
 (command "PLINE" p1 p2 p3 p4 "c")
 (command "HATCH" "ZIGZAG" 4.00 0.00 "L" "")
 (command "COLOR" "BYLAYER")
 (command "LAYER" "S" "CGBLITHCD" "")
 (setq p1 (list 113.00 1877.30) p2 (list 114.35 1877.30))
 (command "LINE" p1 p2 "")
 (setq p1 (list 114.50 1876.92) p2 (list 0.00 0.00))
 (command "TEXT" "J" "ML" p1   0.75  0.00 "374")
 (command "LAYER" "S" "CGBTHK" "")
 (setq p1 (list 119.00 1876.92) p2 (list 0.00 0.00))
 (command "TEXT" "J" "ML" p1   0.75  0.00 "5.85")
 (command "LAYER" "S" "CGBHZID" "")
 (setq p1 (list 123.50 1876.92) p2 (list 0.00 0.00))
 (command "TEXT" "J" "ML" p1   0.75  0.00 "")
 (setq p1 (list 125.75 1876.92) p2 (list 0.00 0.00))
 (command "TEXT" "J" "ML" p1   0.75  0.00 "9990")
 (command "LAYER" "S" "CGBLITHTXT" "")
 (setq p1 (list 129.50 1876.92) p2 (list 0.00 0.00))
 (command "TEXT" "J" "ML" p1   0.75  0.00 "GRY/GRN SDY SH")
 (command "LAYER" "S" "CGBCMNT" "")
 (setq p1 (list 149.75 1876.92) p2 (list 0.00 0.00))
 (command "TEXT" "J" "ML" p1   0.75  0.00 "")
 (command "LAYER" "S" "CGBMAIN" "")
 (setq p1 (list 107.00 1874.37) p2 (list 113.00 1874.37) p3 (list 113.00 1873.73) p4 (list 107.00 1873.73))
 (command "PLINE" p1 p2 p3 p4 "c")
 (command "HATCH" "ZIGZAG" 4.00 0.00 "L" "")
 (command "COLOR" "BYLAYER")
 (command "LAYER" "S" "CGBLITHCD" "")
 (setq p1 (list 113.00 1874.05) p2 (list 114.35 1874.05))
 (command "LINE" p1 p2 "")
 (setq p1 (list 114.50 1873.68) p2 (list 0.00 0.00))
 (command "TEXT" "J" "ML" p1   0.75  0.00 "374")
 (command "LAYER" "S" "CGBTHK" "")
 (setq p1 (list 119.00 1873.68) p2 (list 0.00 0.00))
 (command "TEXT" "J" "ML" p1   0.75  0.00 "0.64")
 (command "LAYER" "S" "CGBHZID" "")
 (setq p1 (list 123.50 1873.68) p2 (list 0.00 0.00))
 (command "TEXT" "J" "ML" p1   0.75  0.00 "")
 (setq p1 (list 125.75 1873.68) p2 (list 0.00 0.00))
 (command "TEXT" "J" "ML" p1   0.75  0.00 "9990")
 (command "LAYER" "S" "CGBLITHTXT" "")
 (setq p1 (list 129.50 1873.68) p2 (list 0.00 0.00))
 (command "TEXT" "J" "ML" p1   0.75  0.00 "GRY/GRN SDY SH")
 (command "LAYER" "S" "CGBCMNT" "")
 (setq p1 (list 149.75 1873.68) p2 (list 0.00 0.00))
 (command "TEXT" "J" "ML" p1   0.75  0.00 "")
 (command "LAYER" "S" "CGBMAIN" "")
 (setq p1 (list 107.00 1873.73) p2 (list 113.00 1873.73) p3 (list 113.00 1867.84) p4 (list 107.00 1867.84))
 (command "PLINE" p1 p2 p3 p4 "c")
 (command "HATCH" "ZIGZAG" 4.00 0.00 "L" "")
 (command "COLOR" "BYLAYER")
 (command "LAYER" "S" "CGBLITHCD" "")
 (setq p1 (list 113.00 1870.79) p2 (list 114.35 1870.79))
 (command "LINE" p1 p2 "")
 (setq p1 (list 114.50 1870.41) p2 (list 0.00 0.00))
 (command "TEXT" "J" "ML" p1   0.75  0.00 "474")
 (command "LAYER" "S" "CGBTHK" "")
 (setq p1 (list 119.00 1870.41) p2 (list 0.00 0.00))
 (command "TEXT" "J" "ML" p1   0.75  0.00 "5.89")
 (command "LAYER" "S" "CGBHZID" "")
 (setq p1 (list 123.50 1870.41) p2 (list 0.00 0.00))
 (command "TEXT" "J" "ML" p1   0.75  0.00 "")
 (setq p1 (list 125.75 1870.41) p2 (list 0.00 0.00))
 (command "TEXT" "J" "ML" p1   0.75  0.00 "9990")
 (command "LAYER" "S" "CGBLITHTXT" "")
 (setq p1 (list 129.50 1870.41) p2 (list 0.00 0.00))
 (command "TEXT" "J" "ML" p1   0.75  0.00 "GRY/GRN SDY SH W/LS NODS")
 (command "LAYER" "S" "CGBCMNT" "")
 (setq p1 (list 149.75 1870.41) p2 (list 0.00 0.00))
 (command "TEXT" "J" "ML" p1   0.75  0.00 "")
 (command "LAYER" "S" "CGBMAIN" "")
 (setq p1 (list 107.00 1867.84) p2 (list 113.00 1867.84) p3 (list 113.00 1863.91) p4 (list 107.00 1863.91))
 (command "PLINE" p1 p2 p3 p4 "c")
 (command "HATCH" "ZIGZAG" 5.00 0.00 "L" "")
 (command "COLOR" "BYLAYER")
 (command "LAYER" "S" "CGBLITHCD" "")
 (setq p1 (list 113.00 1865.88) p2 (list 114.35 1865.88))
 (command "LINE" p1 p2 "")
 (setq p1 (list 114.50 1865.50) p2 (list 0.00 0.00))
 (command "TEXT" "J" "ML" p1   0.75  0.00 "322")
 (command "LAYER" "S" "CGBTHK" "")
 (setq p1 (list 119.00 1865.50) p2 (list 0.00 0.00))
 (command "TEXT" "J" "ML" p1   0.75  0.00 "3.93")
 (command "LAYER" "S" "CGBHZID" "")
 (setq p1 (list 123.50 1865.50) p2 (list 0.00 0.00))
 (command "TEXT" "J" "ML" p1   0.75  0.00 "")
 (setq p1 (list 125.75 1865.50) p2 (list 0.00 0.00))
 (command "TEXT" "J" "ML" p1   0.75  0.00 "9990")
 (command "LAYER" "S" "CGBLITHTXT" "")
 (setq p1 (list 129.50 1865.50) p2 (list 0.00 0.00))
 (command "TEXT" "J" "ML" p1   0.75  0.00 "DRK GRY SH+INTERBED SS")
 (command "LAYER" "S" "CGBCMNT" "")
 (setq p1 (list 149.75 1865.50) p2 (list 0.00 0.00))
 (command "TEXT" "J" "ML" p1   0.75  0.00 "ANG W/SFT SH")
 (command "LAYER" "S" "CGBMAIN" "")
 (setq p1 (list 107.00 1863.91) p2 (list 113.00 1863.91) p3 (list 113.00 1859.41) p4 (list 107.00 1859.41))
 (command "PLINE" p1 p2 p3 p4 "c")
 (command "HATCH" "ZIGZAG" 4.00 0.00 "L" "")
 (command "COLOR" "BYLAYER")
 (command "LAYER" "S" "CGBLITHCD" "")
 (setq p1 (list 113.00 1861.66) p2 (list 114.35 1861.66))
 (command "LINE" p1 p2 "")
 (setq p1 (list 114.50 1861.29) p2 (list 0.00 0.00))
 (command "TEXT" "J" "ML" p1   0.75  0.00 "563")
 (command "LAYER" "S" "CGBTHK" "")
 (setq p1 (list 119.00 1861.29) p2 (list 0.00 0.00))
 (command "TEXT" "J" "ML" p1   0.75  0.00 "4.50")
 (command "LAYER" "S" "CGBHZID" "")
 (setq p1 (list 123.50 1861.29) p2 (list 0.00 0.00))
 (command "TEXT" "J" "ML" p1   0.75  0.00 "")
 (setq p1 (list 125.75 1861.29) p2 (list 0.00 0.00))
 (command "TEXT" "J" "ML" p1   0.75  0.00 "9990")
 (command "LAYER" "S" "CGBLITHTXT" "")
 (setq p1 (list 129.50 1861.29) p2 (list 0.00 0.00))
 (command "TEXT" "J" "ML" p1   0.75  0.00 "HARD SS W/SH STKS")
 (command "LAYER" "S" "CGBCMNT" "")
 (setq p1 (list 149.75 1861.29) p2 (list 0.00 0.00))
 (command "TEXT" "J" "ML" p1   0.75  0.00 "")
 (command "LAYER" "S" "CGBMAIN" "")
 (setq p1 (list 107.00 1859.41) p2 (list 113.00 1859.41) p3 (list 113.00 1854.37) p4 (list 107.00 1854.37))
 (command "PLINE" p1 p2 p3 p4 "c")
 (command "HATCH" "ZIGZAG" 0.25 0.00 "L" "")
 (command "COLOR" "BYLAYER")
 (command "LAYER" "S" "CGBLITHCD" "")
 (setq p1 (list 113.00 1856.89) p2 (list 114.35 1856.89))
 (command "LINE" p1 p2 "")
 (setq p1 (list 114.50 1856.52) p2 (list 0.00 0.00))
 (command "TEXT" "J" "ML" p1   0.75  0.00 "762")
 (command "LAYER" "S" "CGBTHK" "")
 (setq p1 (list 119.00 1856.52) p2 (list 0.00 0.00))
 (command "TEXT" "J" "ML" p1   0.75  0.00 "5.04")
 (command "LAYER" "S" "CGBHZID" "")
 (setq p1 (list 123.50 1856.52) p2 (list 0.00 0.00))
 (command "TEXT" "J" "ML" p1   0.75  0.00 "")
 (setq p1 (list 125.75 1856.52) p2 (list 0.00 0.00))
 (command "TEXT" "J" "ML" p1   0.75  0.00 "9990")
 (command "LAYER" "S" "CGBLITHTXT" "")
 (setq p1 (list 129.50 1856.52) p2 (list 0.00 0.00))
 (command "TEXT" "J" "ML" p1   0.75  0.00 "HARD SH PEB CGL")
 (command "LAYER" "S" "CGBCMNT" "")
 (setq p1 (list 149.75 1856.52) p2 (list 0.00 0.00))
 (command "TEXT" "J" "ML" p1   0.75  0.00 "")
 (command "LAYER" "S" "CGBMAIN" "")
 (setq p1 (list 107.00 1854.37) p2 (list 113.00 1854.37) p3 (list 113.00 1851.64) p4 (list 107.00 1851.64))
 (command "PLINE" p1 p2 p3 p4 "c")
 (command "HATCH" "ZIGZAG" 0.25 0.00 "L" "")
 (command "COLOR" "BYLAYER")
 (command "LAYER" "S" "CGBLITHCD" "")
 (setq p1 (list 113.00 1853.01) p2 (list 114.35 1853.01))
 (command "LINE" p1 p2 "")
 (setq p1 (list 114.50 1852.63) p2 (list 0.00 0.00))
 (command "TEXT" "J" "ML" p1   0.75  0.00 "762")
 (command "LAYER" "S" "CGBTHK" "")
 (setq p1 (list 119.00 1852.63) p2 (list 0.00 0.00))
 (command "TEXT" "J" "ML" p1   0.75  0.00 "2.73")
 (command "LAYER" "S" "CGBHZID" "")
 (setq p1 (list 123.50 1852.63) p2 (list 0.00 0.00))
 (command "TEXT" "J" "ML" p1   0.75  0.00 "")
 (setq p1 (list 125.75 1852.63) p2 (list 0.00 0.00))
 (command "TEXT" "J" "ML" p1   0.75  0.00 "9990")
 (command "LAYER" "S" "CGBLITHTXT" "")
 (setq p1 (list 129.50 1852.63) p2 (list 0.00 0.00))
 (command "TEXT" "J" "ML" p1   0.75  0.00 "HARD SH PEB CGL")
 (command "LAYER" "S" "CGBCMNT" "")
 (setq p1 (list 149.75 1852.63) p2 (list 0.00 0.00))
 (command "TEXT" "J" "ML" p1   0.75  0.00 "")
 (command "LAYER" "S" "CGBMAIN" "")
 (setq p1 (list 107.00 1851.64) p2 (list 113.00 1851.64) p3 (list 113.00 1846.67) p4 (list 107.00 1846.67))
 (command "PLINE" p1 p2 p3 p4 "c")
 (command "HATCH" "ZIGZAG" 0.25 0.00 "L" "")
 (command "COLOR" "BYLAYER")
 (command "LAYER" "S" "CGBLITHCD" "")
 (setq p1 (list 113.00 1849.16) p2 (list 114.35 1849.16))
 (command "LINE" p1 p2 "")
 (setq p1 (list 114.50 1848.78) p2 (list 0.00 0.00))
 (command "TEXT" "J" "ML" p1   0.75  0.00 "768")
 (command "LAYER" "S" "CGBTHK" "")
 (setq p1 (list 119.00 1848.78) p2 (list 0.00 0.00))
 (command "TEXT" "J" "ML" p1   0.75  0.00 "4.97")
 (command "LAYER" "S" "CGBHZID" "")
 (setq p1 (list 123.50 1848.78) p2 (list 0.00 0.00))
 (command "TEXT" "J" "ML" p1   0.75  0.00 "")
 (setq p1 (list 125.75 1848.78) p2 (list 0.00 0.00))
 (command "TEXT" "J" "ML" p1   0.75  0.00 "9990")
 (command "LAYER" "S" "CGBLITHTXT" "")
 (setq p1 (list 129.50 1848.78) p2 (list 0.00 0.00))
 (command "TEXT" "J" "ML" p1   0.75  0.00 "HARD SS W/COAL BANDS")
 (command "LAYER" "S" "CGBCMNT" "")
 (setq p1 (list 149.75 1848.78) p2 (list 0.00 0.00))
 (command "TEXT" "J" "ML" p1   0.75  0.00 "")
 (command "LAYER" "S" "CGBMAIN" "")
 (setq p1 (list 107.00 1846.67) p2 (list 113.00 1846.67) p3 (list 113.00 1844.93) p4 (list 107.00 1844.93))
 (command "PLINE" p1 p2 p3 p4 "c")
 (command "HATCH" "ZIGZAG" 4.00 22.50 "L" "")
 (command "COLOR" "BYLAYER")
 (command "LAYER" "S" "CGBLITHCD" "")
 (setq p1 (list 113.00 1845.80) p2 (list 114.35 1845.80))
 (command "LINE" p1 p2 "")
 (setq p1 (list 114.50 1845.43) p2 (list 0.00 0.00))
 (command "TEXT" "J" "ML" p1   0.75  0.00 "114")
 (command "LAYER" "S" "CGBTHK" "")
 (setq p1 (list 119.00 1845.43) p2 (list 0.00 0.00))
 (command "TEXT" "J" "ML" p1   0.75  0.00 "1.74")
 (command "LAYER" "S" "CGBHZID" "")
 (setq p1 (list 123.50 1845.43) p2 (list 0.00 0.00))
 (command "TEXT" "J" "ML" p1   0.75  0.00 "")
 (setq p1 (list 125.75 1845.43) p2 (list 0.00 0.00))
 (command "TEXT" "J" "ML" p1   0.75  0.00 "9990")
 (command "LAYER" "S" "CGBLITHTXT" "")
 (setq p1 (list 129.50 1845.43) p2 (list 0.00 0.00))
 (command "TEXT" "J" "ML" p1   0.75  0.00 "BLK SH")
 (command "LAYER" "S" "CGBCMNT" "")
 (setq p1 (list 149.75 1845.43) p2 (list 0.00 0.00))
 (command "TEXT" "J" "ML" p1   0.75  0.00 "BRKN, SLX")
 (command "LAYER" "S" "CGBMAIN" "")
 (setq p1 (list 107.00 1844.93) p2 (list 113.00 1844.93) p3 (list 113.00 1839.75) p4 (list 107.00 1839.75))
 (command "PLINE" p1 p2 p3 p4 "c")
 (command "HATCH" "ZIGZAG" 4.00 0.00 "L" "")
 (command "COLOR" "BYLAYER")
 (command "LAYER" "S" "CGBLITHCD" "")
 (setq p1 (list 113.00 1842.34) p2 (list 114.35 1842.34))
 (command "LINE" p1 p2 "")
 (setq p1 (list 114.50 1841.97) p2 (list 0.00 0.00))
 (command "TEXT" "J" "ML" p1   0.75  0.00 "115")
 (command "LAYER" "S" "CGBTHK" "")
 (setq p1 (list 119.00 1841.97) p2 (list 0.00 0.00))
 (command "TEXT" "J" "ML" p1   0.75  0.00 "5.18")
 (command "LAYER" "S" "CGBHZID" "")
 (setq p1 (list 123.50 1841.97) p2 (list 0.00 0.00))
 (command "TEXT" "J" "ML" p1   0.75  0.00 "")
 (setq p1 (list 125.75 1841.97) p2 (list 0.00 0.00))
 (command "TEXT" "J" "ML" p1   0.75  0.00 "9990")
 (command "LAYER" "S" "CGBLITHTXT" "")
 (setq p1 (list 129.50 1841.97) p2 (list 0.00 0.00))
 (command "TEXT" "J" "ML" p1   0.75  0.00 "BLK CHRND SH")
 (command "LAYER" "S" "CGBCMNT" "")
 (setq p1 (list 149.75 1841.97) p2 (list 0.00 0.00))
 (command "TEXT" "J" "ML" p1   0.75  0.00 "FE NODS")
 (command "LAYER" "S" "CGBMAIN" "")
 (setq p1 (list 107.00 1839.75) p2 (list 113.00 1839.75) p3 (list 113.00 1839.54) p4 (list 107.00 1839.54))
 (command "PLINE" p1 p2 p3 p4 "c")
 (command "HATCH" "ZIGZAG" 2.00 45.00 "L" "")
 (command "COLOR" "BYLAYER")
 (command "LAYER" "S" "CGBLITHCD" "")
 (setq p1 (list 113.00 1839.65) p2 (list 114.35 1839.65))
 (command "LINE" p1 p2 "")
 (setq p1 (list 114.50 1839.27) p2 (list 0.00 0.00))
 (command "TEXT" "J" "ML" p1   0.75  0.00 "313")
 (command "LAYER" "S" "CGBTHK" "")
 (setq p1 (list 119.00 1839.27) p2 (list 0.00 0.00))
 (command "TEXT" "J" "ML" p1   0.75  0.00 "0.21")
 (command "LAYER" "S" "CGBHZID" "")
 (setq p1 (list 123.50 1839.27) p2 (list 0.00 0.00))
 (command "TEXT" "J" "ML" p1   0.75  0.00 "")
 (setq p1 (list 125.75 1839.27) p2 (list 0.00 0.00))
 (command "TEXT" "J" "ML" p1   0.75  0.00 "9990")
 (command "LAYER" "S" "CGBLITHTXT" "")
 (setq p1 (list 129.50 1839.27) p2 (list 0.00 0.00))
 (command "TEXT" "J" "ML" p1   0.75  0.00 "BLK SH W/SS STKS")
 (command "LAYER" "S" "CGBCMNT" "")
 (setq p1 (list 149.75 1839.27) p2 (list 0.00 0.00))
 (command "TEXT" "J" "ML" p1   0.75  0.00 "")
 (command "LAYER" "S" "CGBMAIN" "")
 (setq p1 (list 107.00 1839.54) p2 (list 113.00 1839.54) p3 (list 113.00 1834.37) p4 (list 107.00 1834.37))
 (command "PLINE" p1 p2 p3 p4 "c")
 (command "HATCH" "ZIGZAG" 4.00 22.50 "L" "")
 (command "COLOR" "BYLAYER")
 (command "LAYER" "S" "CGBLITHCD" "")
 (setq p1 (list 113.00 1836.96) p2 (list 114.35 1836.96))
 (command "LINE" p1 p2 "")
 (setq p1 (list 114.50 1836.58) p2 (list 0.00 0.00))
 (command "TEXT" "J" "ML" p1   0.75  0.00 "114")
 (command "LAYER" "S" "CGBTHK" "")
 (setq p1 (list 119.00 1836.58) p2 (list 0.00 0.00))
 (command "TEXT" "J" "ML" p1   0.75  0.00 "5.17")
 (command "LAYER" "S" "CGBHZID" "")
 (setq p1 (list 123.50 1836.58) p2 (list 0.00 0.00))
 (command "TEXT" "J" "ML" p1   0.75  0.00 "")
 (setq p1 (list 125.75 1836.58) p2 (list 0.00 0.00))
 (command "TEXT" "J" "ML" p1   0.75  0.00 "9990")
 (command "LAYER" "S" "CGBLITHTXT" "")
 (setq p1 (list 129.50 1836.58) p2 (list 0.00 0.00))
 (command "TEXT" "J" "ML" p1   0.75  0.00 "BLK SH")
 (command "LAYER" "S" "CGBCMNT" "")
 (setq p1 (list 149.75 1836.58) p2 (list 0.00 0.00))
 (command "TEXT" "J" "ML" p1   0.75  0.00 "SLX, FE NODS")
 (command "LAYER" "S" "CGBMAIN" "")
 (setq p1 (list 107.00 1834.37) p2 (list 113.00 1834.37) p3 (list 113.00 1829.45) p4 (list 107.00 1829.45))
 (command "PLINE" p1 p2 p3 p4 "c")
 (command "HATCH" "ZIGZAG" 4.00 0.00 "L" "")
 (command "COLOR" "BYLAYER")
 (command "LAYER" "S" "CGBLITHCD" "")
 (setq p1 (list 113.00 1831.91) p2 (list 114.35 1831.91))
 (command "LINE" p1 p2 "")
 (setq p1 (list 114.50 1831.54) p2 (list 0.00 0.00))
 (command "TEXT" "J" "ML" p1   0.75  0.00 "124")
 (command "LAYER" "S" "CGBTHK" "")
 (setq p1 (list 119.00 1831.54) p2 (list 0.00 0.00))
 (command "TEXT" "J" "ML" p1   0.75  0.00 "4.92")
 (command "LAYER" "S" "CGBHZID" "")
 (setq p1 (list 123.50 1831.54) p2 (list 0.00 0.00))
 (command "TEXT" "J" "ML" p1   0.75  0.00 "")
 (setq p1 (list 125.75 1831.54) p2 (list 0.00 0.00))
 (command "TEXT" "J" "ML" p1   0.75  0.00 "9990")
 (command "LAYER" "S" "CGBLITHTXT" "")
 (setq p1 (list 129.50 1831.54) p2 (list 0.00 0.00))
 (command "TEXT" "J" "ML" p1   0.75  0.00 "DRK GRY SH")
 (command "LAYER" "S" "CGBCMNT" "")
 (setq p1 (list 149.75 1831.54) p2 (list 0.00 0.00))
 (command "TEXT" "J" "ML" p1   0.75  0.00 "SFT, DRK")
 (command "LAYER" "S" "CGBMAIN" "")
 (setq p1 (list 107.00 1829.45) p2 (list 113.00 1829.45) p3 (list 113.00 1827.68) p4 (list 107.00 1827.68))
 (command "PLINE" p1 p2 p3 p4 "c")
 (command "HATCH" "ZIGZAG" 0.40 45.00 "L" "")
 (command "COLOR" "BYLAYER")
 (command "LAYER" "S" "CGBLITHCD" "")
 (setq p1 (list 113.00 1828.57) p2 (list 114.35 1828.57))
 (command "LINE" p1 p2 "")
 (setq p1 (list 114.50 1828.19) p2 (list 0.00 0.00))
 (command "TEXT" "J" "ML" p1   0.75  0.00 "022")
 (command "LAYER" "S" "CGBTHK" "")
 (setq p1 (list 119.00 1828.19) p2 (list 0.00 0.00))
 (command "TEXT" "J" "ML" p1   0.75  0.00 "1.77")
 (command "LAYER" "S" "CGBHZID" "")
 (setq p1 (list 123.50 1828.19) p2 (list 0.00 0.00))
 (command "TEXT" "J" "ML" p1   0.75  0.00 "")
 (setq p1 (list 125.75 1828.19) p2 (list 0.00 0.00))
 (command "TEXT" "J" "ML" p1   0.75  0.00 "8500")
 (command "LAYER" "S" "CGBLITHTXT" "")
 (setq p1 (list 129.50 1828.19) p2 (list 0.00 0.00))
 (command "TEXT" "J" "ML" p1   0.75  0.00 "COAL W/BONE LAYERS")
 (command "LAYER" "S" "CGBCMNT" "")
 (setq p1 (list 149.75 1828.19) p2 (list 0.00 0.00))
 (command "TEXT" "J" "ML" p1   0.75  0.00 "MOSTLY BRIGHT")
 (command "LAYER" "S" "CGBMAIN" "")
 (setq p1 (list 107.00 1827.68) p2 (list 113.00 1827.68) p3 (list 113.00 1826.80) p4 (list 107.00 1826.80))
 (command "PLINE" p1 p2 p3 p4 "c")
 (command "HATCH" "ZIGZAG" 5.00 0.00 "L" "")
 (command "COLOR" "BYLAYER")
 (command "LAYER" "S" "CGBLITHCD" "")
 (setq p1 (list 113.00 1827.24) p2 (list 114.35 1827.24))
 (command "LINE" p1 p2 "")
 (setq p1 (list 114.50 1826.87) p2 (list 0.00 0.00))
 (command "TEXT" "J" "ML" p1   0.75  0.00 "032")
 (command "LAYER" "S" "CGBTHK" "")
 (setq p1 (list 119.00 1826.87) p2 (list 0.00 0.00))
 (command "TEXT" "J" "ML" p1   0.75  0.00 "0.88")
 (command "LAYER" "S" "CGBHZID" "")
 (setq p1 (list 123.50 1826.87) p2 (list 0.00 0.00))
 (command "TEXT" "J" "ML" p1   0.75  0.00 "")
 (setq p1 (list 125.75 1826.87) p2 (list 0.00 0.00))
 (command "TEXT" "J" "ML" p1   0.75  0.00 "8500")
 (command "LAYER" "S" "CGBLITHTXT" "")
 (setq p1 (list 129.50 1826.87) p2 (list 0.00 0.00))
 (command "TEXT" "J" "ML" p1   0.75  0.00 "BONE W/COAL LAYERS")
 (command "LAYER" "S" "CGBCMNT" "")
 (setq p1 (list 149.75 1826.87) p2 (list 0.00 0.00))
 (command "TEXT" "J" "ML" p1   0.75  0.00 "DULL, GB")
 (command "LAYER" "S" "CGBMAIN" "")
 (setq p1 (list 107.00 1826.80) p2 (list 113.00 1826.80) p3 (list 113.00 1826.40) p4 (list 107.00 1826.40))
 (command "PLINE" p1 p2 p3 p4 "c")
 (command "HATCH" "ZIGZAG" 0.25 0.00 "L" "")
 (command "COLOR" "BYLAYER")
 (command "LAYER" "S" "CGBLITHCD" "")
 (setq p1 (list 113.00 1826.60) p2 (list 114.35 1825.35))
 (command "LINE" p1 p2 "")
 (setq p1 (list 114.50 1824.98) p2 (list 0.00 0.00))
 (command "TEXT" "J" "ML" p1   0.75  0.00 "127")
 (command "LAYER" "S" "CGBTHK" "")
 (setq p1 (list 119.00 1824.98) p2 (list 0.00 0.00))
 (command "TEXT" "J" "ML" p1   0.75  0.00 "0.40")
 (command "LAYER" "S" "CGBHZID" "")
 (setq p1 (list 123.50 1824.98) p2 (list 0.00 0.00))
 (command "TEXT" "J" "ML" p1   0.75  0.00 "")
 (setq p1 (list 125.75 1824.98) p2 (list 0.00 0.00))
 (command "TEXT" "J" "ML" p1   0.75  0.00 "8451")
 (command "LAYER" "S" "CGBLITHTXT" "")
 (setq p1 (list 129.50 1824.98) p2 (list 0.00 0.00))
 (command "TEXT" "J" "ML" p1   0.75  0.00 "DRK GRY FIRECLAY")
 (command "LAYER" "S" "CGBCMNT" "")
 (setq p1 (list 149.75 1824.98) p2 (list 0.00 0.00))
 (command "TEXT" "J" "ML" p1   0.75  0.00 "SFT, DRK")
 (command "LAYER" "S" "CGBMAIN" "")
 (setq p1 (list 107.00 1826.40) p2 (list 113.00 1826.40) p3 (list 113.00 1826.12) p4 (list 107.00 1826.12))
 (command "PLINE" p1 p2 p3 p4 "c")
 (command "HATCH" "ZIGZAG" 6.00 0.00 "L" "")
 (command "COLOR" "BYLAYER")
 (command "LAYER" "S" "CGBLITHCD" "")
 (setq p1 (list 113.00 1826.26) p2 (list 114.35 1824.10))
 (command "LINE" p1 p2 "")
 (setq p1 (list 114.50 1823.73) p2 (list 0.00 0.00))
 (command "TEXT" "J" "ML" p1   0.75  0.00 "113")
 (command "LAYER" "S" "CGBTHK" "")
 (setq p1 (list 119.00 1823.73) p2 (list 0.00 0.00))
 (command "TEXT" "J" "ML" p1   0.75  0.00 "0.28")
 (command "LAYER" "S" "CGBHZID" "")
 (setq p1 (list 123.50 1823.73) p2 (list 0.00 0.00))
 (command "TEXT" "J" "ML" p1   0.75  0.00 "")
 (setq p1 (list 125.75 1823.73) p2 (list 0.00 0.00))
 (command "TEXT" "J" "ML" p1   0.75  0.00 "8451")
 (command "LAYER" "S" "CGBLITHTXT" "")
 (setq p1 (list 129.50 1823.73) p2 (list 0.00 0.00))
 (command "TEXT" "J" "ML" p1   0.75  0.00 "BLK SH W/COAL STKS")
 (command "LAYER" "S" "CGBCMNT" "")
 (setq p1 (list 149.75 1823.73) p2 (list 0.00 0.00))
 (command "TEXT" "J" "ML" p1   0.75  0.00 "W/VIT BNDS")
 (command "LAYER" "S" "CGBMAIN" "")
 (setq p1 (list 107.00 1826.12) p2 (list 113.00 1826.12) p3 (list 113.00 1825.94) p4 (list 107.00 1825.94))
 (command "PLINE" p1 p2 p3 p4 "c")
 (command "HATCH" "ZIGZAG" 5.00 0.00 "L" "")
 (command "COLOR" "BYLAYER")
 (command "LAYER" "S" "CGBLITHCD" "")
 (setq p1 (list 113.00 1826.03) p2 (list 114.35 1822.85))
 (command "LINE" p1 p2 "")
 (setq p1 (list 114.50 1822.48) p2 (list 0.00 0.00))
 (command "TEXT" "J" "ML" p1   0.75  0.00 "033")
 (command "LAYER" "S" "CGBTHK" "")
 (setq p1 (list 119.00 1822.48) p2 (list 0.00 0.00))
 (command "TEXT" "J" "ML" p1   0.75  0.00 "0.18")
 (command "LAYER" "S" "CGBHZID" "")
 (setq p1 (list 123.50 1822.48) p2 (list 0.00 0.00))
 (command "TEXT" "J" "ML" p1   0.75  0.00 "")
 (setq p1 (list 125.75 1822.48) p2 (list 0.00 0.00))
 (command "TEXT" "J" "ML" p1   0.75  0.00 "8451")
 (command "LAYER" "S" "CGBLITHTXT" "")
 (setq p1 (list 129.50 1822.48) p2 (list 0.00 0.00))
 (command "TEXT" "J" "ML" p1   0.75  0.00 "BONE W/COAL STKS")
 (command "LAYER" "S" "CGBCMNT" "")
 (setq p1 (list 149.75 1822.48) p2 (list 0.00 0.00))
 (command "TEXT" "J" "ML" p1   0.75  0.00 "DULL")
 (command "LAYER" "S" "CGBMAIN" "")
 (setq p1 (list 107.00 1825.94) p2 (list 113.00 1825.94) p3 (list 113.00 1824.58) p4 (list 107.00 1824.58))
 (command "PLINE" p1 p2 p3 p4 "c")
 (command "HATCH" "ZIGZAG" 0.25 0.00 "L" "")
 (command "COLOR" "BYLAYER")
 (command "LAYER" "S" "CGBLITHCD" "")
 (setq p1 (list 113.00 1825.26) p2 (list 114.35 1821.60))
 (command "LINE" p1 p2 "")
 (setq p1 (list 114.50 1821.23) p2 (list 0.00 0.00))
 (command "TEXT" "J" "ML" p1   0.75  0.00 "127")
 (command "LAYER" "S" "CGBTHK" "")
 (setq p1 (list 119.00 1821.23) p2 (list 0.00 0.00))
 (command "TEXT" "J" "ML" p1   0.75  0.00 "1.36")
 (command "LAYER" "S" "CGBHZID" "")
 (setq p1 (list 123.50 1821.23) p2 (list 0.00 0.00))
 (command "TEXT" "J" "ML" p1   0.75  0.00 "")
 (setq p1 (list 125.75 1821.23) p2 (list 0.00 0.00))
 (command "TEXT" "J" "ML" p1   0.75  0.00 "8451")
 (command "LAYER" "S" "CGBLITHTXT" "")
 (setq p1 (list 129.50 1821.23) p2 (list 0.00 0.00))
 (command "TEXT" "J" "ML" p1   0.75  0.00 "DRK GRY FIRECLAY")
 (command "LAYER" "S" "CGBCMNT" "")
 (setq p1 (list 149.75 1821.23) p2 (list 0.00 0.00))
 (command "TEXT" "J" "ML" p1   0.75  0.00 "V SFT, MTTLD")
 (command "LAYER" "S" "CGBMAIN" "")
 (setq p1 (list 107.00 1824.58) p2 (list 113.00 1824.58) p3 (list 113.00 1820.05) p4 (list 107.00 1820.05))
 (command "PLINE" p1 p2 p3 p4 "c")
 (command "HATCH" "ZIGZAG" 4.00 0.00 "L" "")
 (command "COLOR" "BYLAYER")
 (command "LAYER" "S" "CGBLITHCD" "")
 (setq p1 (list 113.00 1822.32) p2 (list 114.35 1820.35))
 (command "LINE" p1 p2 "")
 (setq p1 (list 114.50 1819.98) p2 (list 0.00 0.00))
 (command "TEXT" "J" "ML" p1   0.75  0.00 "125")
 (command "LAYER" "S" "CGBTHK" "")
 (setq p1 (list 119.00 1819.98) p2 (list 0.00 0.00))
 (command "TEXT" "J" "ML" p1   0.75  0.00 "4.53")
 (command "LAYER" "S" "CGBHZID" "")
 (setq p1 (list 123.50 1819.98) p2 (list 0.00 0.00))
 (command "TEXT" "J" "ML" p1   0.75  0.00 "")
 (setq p1 (list 125.75 1819.98) p2 (list 0.00 0.00))
 (command "TEXT" "J" "ML" p1   0.75  0.00 "8451")
 (command "LAYER" "S" "CGBLITHTXT" "")
 (setq p1 (list 129.50 1819.98) p2 (list 0.00 0.00))
 (command "TEXT" "J" "ML" p1   0.75  0.00 "DRK GRY CHRND SH")
 (command "LAYER" "S" "CGBCMNT" "")
 (setq p1 (list 149.75 1819.98) p2 (list 0.00 0.00))
 (command "TEXT" "J" "ML" p1   0.75  0.00 "SFT, CALC NOD")
 (command "LAYER" "S" "CGBMAIN" "")
 (setq p1 (list 107.00 1820.05) p2 (list 113.00 1820.05) p3 (list 113.00 1817.95) p4 (list 107.00 1817.95))
 (command "PLINE" p1 p2 p3 p4 "c")
 (command "HATCH" "ZIGZAG" 4.00 22.50 "L" "")
 (command "COLOR" "BYLAYER")
 (command "LAYER" "S" "CGBLITHCD" "")
 (setq p1 (list 113.00 1819.00) p2 (list 114.35 1819.00))
 (command "LINE" p1 p2 "")
 (setq p1 (list 114.50 1818.63) p2 (list 0.00 0.00))
 (command "TEXT" "J" "ML" p1   0.75  0.00 "114")
 (command "LAYER" "S" "CGBTHK" "")
 (setq p1 (list 119.00 1818.63) p2 (list 0.00 0.00))
 (command "TEXT" "J" "ML" p1   0.75  0.00 "2.10")
 (command "LAYER" "S" "CGBHZID" "")
 (setq p1 (list 123.50 1818.63) p2 (list 0.00 0.00))
 (command "TEXT" "J" "ML" p1   0.75  0.00 "")
 (setq p1 (list 125.75 1818.63) p2 (list 0.00 0.00))
 (command "TEXT" "J" "ML" p1   0.75  0.00 "8451")
 (command "LAYER" "S" "CGBLITHTXT" "")
 (setq p1 (list 129.50 1818.63) p2 (list 0.00 0.00))
 (command "TEXT" "J" "ML" p1   0.75  0.00 "BLK SH")
 (command "LAYER" "S" "CGBCMNT" "")
 (setq p1 (list 149.75 1818.63) p2 (list 0.00 0.00))
 (command "TEXT" "J" "ML" p1   0.75  0.00 "FE NODS")
 (command "LAYER" "S" "CGBMAIN" "")
 (setq p1 (list 107.00 1817.95) p2 (list 113.00 1817.95) p3 (list 113.00 1817.57) p4 (list 107.00 1817.57))
 (command "PLINE" p1 p2 p3 p4 "c")
 (command "HATCH" "ZIGZAG" 4.00 0.00 "L" "")
 (command "COLOR" "BYLAYER")
 (command "LAYER" "S" "CGBLITHCD" "")
 (setq p1 (list 113.00 1817.76) p2 (list 114.35 1816.51))
 (command "LINE" p1 p2 "")
 (setq p1 (list 114.50 1816.14) p2 (list 0.00 0.00))
 (command "TEXT" "J" "ML" p1   0.75  0.00 "125")
 (command "LAYER" "S" "CGBTHK" "")
 (setq p1 (list 119.00 1816.14) p2 (list 0.00 0.00))
 (command "TEXT" "J" "ML" p1   0.75  0.00 "0.38")
 (command "LAYER" "S" "CGBHZID" "")
 (setq p1 (list 123.50 1816.14) p2 (list 0.00 0.00))
 (command "TEXT" "J" "ML" p1   0.75  0.00 "")
 (setq p1 (list 125.75 1816.14) p2 (list 0.00 0.00))
 (command "TEXT" "J" "ML" p1   0.75  0.00 "8451")
 (command "LAYER" "S" "CGBLITHTXT" "")
 (setq p1 (list 129.50 1816.14) p2 (list 0.00 0.00))
 (command "TEXT" "J" "ML" p1   0.75  0.00 "DRK GRY CHRND SH")
 (command "LAYER" "S" "CGBCMNT" "")
 (setq p1 (list 149.75 1816.14) p2 (list 0.00 0.00))
 (command "TEXT" "J" "ML" p1   0.75  0.00 "CRMB")
 (command "LAYER" "S" "CGBMAIN" "")
 (setq p1 (list 107.00 1817.57) p2 (list 113.00 1817.57) p3 (list 113.00 1808.50) p4 (list 107.00 1808.50))
 (command "PLINE" p1 p2 p3 p4 "c")
 (command "HATCH" "ZIGZAG" 5.00 0.00 "L" "")
 (command "COLOR" "BYLAYER")
 (command "LAYER" "S" "CGBLITHCD" "")
 (setq p1 (list 113.00 1813.04) p2 (list 114.35 1813.04))
 (command "LINE" p1 p2 "")
 (setq p1 (list 114.50 1812.66) p2 (list 0.00 0.00))
 (command "TEXT" "J" "ML" p1   0.75  0.00 "322")
 (command "LAYER" "S" "CGBTHK" "")
 (setq p1 (list 119.00 1812.66) p2 (list 0.00 0.00))
 (command "TEXT" "J" "ML" p1   0.75  0.00 "9.07")
 (command "LAYER" "S" "CGBHZID" "")
 (setq p1 (list 123.50 1812.66) p2 (list 0.00 0.00))
 (command "TEXT" "J" "ML" p1   0.75  0.00 "")
 (setq p1 (list 125.75 1812.66) p2 (list 0.00 0.00))
 (command "TEXT" "J" "ML" p1   0.75  0.00 "8451")
 (command "LAYER" "S" "CGBLITHTXT" "")
 (setq p1 (list 129.50 1812.66) p2 (list 0.00 0.00))
 (command "TEXT" "J" "ML" p1   0.75  0.00 "DRK GRY SH+INTERBED SS")
 (command "LAYER" "S" "CGBCMNT" "")
 (setq p1 (list 149.75 1812.66) p2 (list 0.00 0.00))
 (command "TEXT" "J" "ML" p1   0.75  0.00 "FE NODS")
 (command "LAYER" "S" "CGBMAIN" "")
 (setq p1 (list 107.00 1808.50) p2 (list 113.00 1808.50) p3 (list 113.00 1804.45) p4 (list 107.00 1804.45))
 (command "PLINE" p1 p2 p3 p4 "c")
 (command "HATCH" "ZIGZAG" 0.25 0.00 "L" "")
 (command "COLOR" "BYLAYER")
 (command "LAYER" "S" "CGBLITHCD" "")
 (setq p1 (list 113.00 1806.48) p2 (list 114.35 1806.48))
 (command "LINE" p1 p2 "")
 (setq p1 (list 114.50 1806.10) p2 (list 0.00 0.00))
 (command "TEXT" "J" "ML" p1   0.75  0.00 "762")
 (command "LAYER" "S" "CGBTHK" "")
 (setq p1 (list 119.00 1806.10) p2 (list 0.00 0.00))
 (command "TEXT" "J" "ML" p1   0.75  0.00 "4.05")
 (command "LAYER" "S" "CGBHZID" "")
 (setq p1 (list 123.50 1806.10) p2 (list 0.00 0.00))
 (command "TEXT" "J" "ML" p1   0.75  0.00 "")
 (setq p1 (list 125.75 1806.10) p2 (list 0.00 0.00))
 (command "TEXT" "J" "ML" p1   0.75  0.00 "8451")
 (command "LAYER" "S" "CGBLITHTXT" "")
 (setq p1 (list 129.50 1806.10) p2 (list 0.00 0.00))
 (command "TEXT" "J" "ML" p1   0.75  0.00 "HARD SH PEB CGL")
 (command "LAYER" "S" "CGBCMNT" "")
 (setq p1 (list 149.75 1806.10) p2 (list 0.00 0.00))
 (command "TEXT" "J" "ML" p1   0.75  0.00 "")
 (command "LAYER" "S" "CGBMAIN" "")
 (setq p1 (list 107.00 1804.45) p2 (list 113.00 1804.45) p3 (list 113.00 1802.95) p4 (list 107.00 1802.95))
 (command "PLINE" p1 p2 p3 p4 "c")
 (command "HATCH" "ZIGZAG" 4.00 0.00 "L" "")
 (command "COLOR" "BYLAYER")
 (command "LAYER" "S" "CGBLITHCD" "")
 (setq p1 (list 113.00 1803.70) p2 (list 114.35 1803.70))
 (command "LINE" p1 p2 "")
 (setq p1 (list 114.50 1803.33) p2 (list 0.00 0.00))
 (command "TEXT" "J" "ML" p1   0.75  0.00 "564")
 (command "LAYER" "S" "CGBTHK" "")
 (setq p1 (list 119.00 1803.33) p2 (list 0.00 0.00))
 (command "TEXT" "J" "ML" p1   0.75  0.00 "1.50")
 (command "LAYER" "S" "CGBHZID" "")
 (setq p1 (list 123.50 1803.33) p2 (list 0.00 0.00))
 (command "TEXT" "J" "ML" p1   0.75  0.00 "")
 (setq p1 (list 125.75 1803.33) p2 (list 0.00 0.00))
 (command "TEXT" "J" "ML" p1   0.75  0.00 "8451")
 (command "LAYER" "S" "CGBLITHTXT" "")
 (setq p1 (list 129.50 1803.33) p2 (list 0.00 0.00))
 (command "TEXT" "J" "ML" p1   0.75  0.00 "HARD MASS SS")
 (command "LAYER" "S" "CGBCMNT" "")
 (setq p1 (list 149.75 1803.33) p2 (list 0.00 0.00))
 (command "TEXT" "J" "ML" p1   0.75  0.00 "CRSN DWN")
 (command "LAYER" "S" "CGBMAIN" "")
 (setq p1 (list 107.00 1802.95) p2 (list 113.00 1802.95) p3 (list 113.00 1801.40) p4 (list 107.00 1801.40))
 (command "PLINE" p1 p2 p3 p4 "c")
 (command "HATCH" "ZIGZAG" 4.00 0.00 "L" "")
 (command "COLOR" "BYLAYER")
 (command "LAYER" "S" "CGBLITHCD" "")
 (setq p1 (list 113.00 1802.18) p2 (list 114.35 1802.18))
 (command "LINE" p1 p2 "")
 (setq p1 (list 114.50 1801.80) p2 (list 0.00 0.00))
 (command "TEXT" "J" "ML" p1   0.75  0.00 "564")
 (command "LAYER" "S" "CGBTHK" "")
 (setq p1 (list 119.00 1801.80) p2 (list 0.00 0.00))
 (command "TEXT" "J" "ML" p1   0.75  0.00 "1.55")
 (command "LAYER" "S" "CGBHZID" "")
 (setq p1 (list 123.50 1801.80) p2 (list 0.00 0.00))
 (command "TEXT" "J" "ML" p1   0.75  0.00 "")
 (setq p1 (list 125.75 1801.80) p2 (list 0.00 0.00))
 (command "TEXT" "J" "ML" p1   0.75  0.00 "8451")
 (command "LAYER" "S" "CGBLITHTXT" "")
 (setq p1 (list 129.50 1801.80) p2 (list 0.00 0.00))
 (command "TEXT" "J" "ML" p1   0.75  0.00 "HARD MASS SS")
 (command "LAYER" "S" "CGBCMNT" "")
 (setq p1 (list 149.75 1801.80) p2 (list 0.00 0.00))
 (command "TEXT" "J" "ML" p1   0.75  0.00 "CRSN DWN")
 (command "LAYER" "S" "CGBMAIN" "")
 (setq p1 (list 107.00 1801.40) p2 (list 113.00 1801.40) p3 (list 113.00 1799.47) p4 (list 107.00 1799.47))
 (command "PLINE" p1 p2 p3 p4 "c")
 (command "HATCH" "ZIGZAG" 0.25 0.00 "L" "")
 (command "COLOR" "BYLAYER")
 (command "LAYER" "S" "CGBLITHCD" "")
 (setq p1 (list 113.00 1800.44) p2 (list 114.35 1800.44))
 (command "LINE" p1 p2 "")
 (setq p1 (list 114.50 1800.06) p2 (list 0.00 0.00))
 (command "TEXT" "J" "ML" p1   0.75  0.00 "764")
 (command "LAYER" "S" "CGBTHK" "")
 (setq p1 (list 119.00 1800.06) p2 (list 0.00 0.00))
 (command "TEXT" "J" "ML" p1   0.75  0.00 "1.93")
 (command "LAYER" "S" "CGBHZID" "")
 (setq p1 (list 123.50 1800.06) p2 (list 0.00 0.00))
 (command "TEXT" "J" "ML" p1   0.75  0.00 "")
 (setq p1 (list 125.75 1800.06) p2 (list 0.00 0.00))
 (command "TEXT" "J" "ML" p1   0.75  0.00 "8451")
 (command "LAYER" "S" "CGBLITHTXT" "")
 (setq p1 (list 129.50 1800.06) p2 (list 0.00 0.00))
 (command "TEXT" "J" "ML" p1   0.75  0.00 "HARD QTZ PEB CGL")
 (command "LAYER" "S" "CGBCMNT" "")
 (setq p1 (list 149.75 1800.06) p2 (list 0.00 0.00))
 (command "TEXT" "J" "ML" p1   0.75  0.00 "SLC")
 (command "LAYER" "S" "CGBMAIN" "")
 (setq p1 (list 107.00 1799.47) p2 (list 113.00 1799.47) p3 (list 113.00 1797.17) p4 (list 107.00 1797.17))
 (command "PLINE" p1 p2 p3 p4 "c")
 (command "HATCH" "ZIGZAG" 0.25 0.00 "L" "")
 (command "COLOR" "BYLAYER")
 (command "LAYER" "S" "CGBLITHCD" "")
 (setq p1 (list 113.00 1798.32) p2 (list 114.35 1798.32))
 (command "LINE" p1 p2 "")
 (setq p1 (list 114.50 1797.95) p2 (list 0.00 0.00))
 (command "TEXT" "J" "ML" p1   0.75  0.00 "762")
 (command "LAYER" "S" "CGBTHK" "")
 (setq p1 (list 119.00 1797.95) p2 (list 0.00 0.00))
 (command "TEXT" "J" "ML" p1   0.75  0.00 "2.30")
 (command "LAYER" "S" "CGBHZID" "")
 (setq p1 (list 123.50 1797.95) p2 (list 0.00 0.00))
 (command "TEXT" "J" "ML" p1   0.75  0.00 "")
 (setq p1 (list 125.75 1797.95) p2 (list 0.00 0.00))
 (command "TEXT" "J" "ML" p1   0.75  0.00 "8451")
 (command "LAYER" "S" "CGBLITHTXT" "")
 (setq p1 (list 129.50 1797.95) p2 (list 0.00 0.00))
 (command "TEXT" "J" "ML" p1   0.75  0.00 "HARD SH PEB CGL")
 (command "LAYER" "S" "CGBCMNT" "")
 (setq p1 (list 149.75 1797.95) p2 (list 0.00 0.00))
 (command "TEXT" "J" "ML" p1   0.75  0.00 "SLC")
 (command "LAYER" "S" "CGBMAIN" "")
 (setq p1 (list 107.00 1797.17) p2 (list 113.00 1797.17) p3 (list 113.00 1793.95) p4 (list 107.00 1793.95))
 (command "PLINE" p1 p2 p3 p4 "c")
 (command "HATCH" "ZIGZAG" 0.25 0.00 "L" "")
 (command "COLOR" "BYLAYER")
 (command "LAYER" "S" "CGBLITHCD" "")
 (setq p1 (list 113.00 1795.56) p2 (list 114.35 1795.56))
 (command "LINE" p1 p2 "")
 (setq p1 (list 114.50 1795.19) p2 (list 0.00 0.00))
 (command "TEXT" "J" "ML" p1   0.75  0.00 "764")
 (command "LAYER" "S" "CGBTHK" "")
 (setq p1 (list 119.00 1795.19) p2 (list 0.00 0.00))
 (command "TEXT" "J" "ML" p1   0.75  0.00 "3.22")
 (command "LAYER" "S" "CGBHZID" "")
 (setq p1 (list 123.50 1795.19) p2 (list 0.00 0.00))
 (command "TEXT" "J" "ML" p1   0.75  0.00 "")
 (setq p1 (list 125.75 1795.19) p2 (list 0.00 0.00))
 (command "TEXT" "J" "ML" p1   0.75  0.00 "8451")
 (command "LAYER" "S" "CGBLITHTXT" "")
 (setq p1 (list 129.50 1795.19) p2 (list 0.00 0.00))
 (command "TEXT" "J" "ML" p1   0.75  0.00 "HARD QTZ PEB CGL")
 (command "LAYER" "S" "CGBCMNT" "")
 (setq p1 (list 149.75 1795.19) p2 (list 0.00 0.00))
 (command "TEXT" "J" "ML" p1   0.75  0.00 "CRS GR,SPAR,S")
 (command "LAYER" "S" "CGBMAIN" "")
 (setq p1 (list 107.00 1793.95) p2 (list 113.00 1793.95) p3 (list 113.00 1793.57) p4 (list 107.00 1793.57))
 (command "PLINE" p1 p2 p3 p4 "c")
 (command "HATCH" "ZIGZAG" 5.00 0.00 "L" "")
 (command "COLOR" "BYLAYER")
 (command "LAYER" "S" "CGBLITHCD" "")
 (setq p1 (list 113.00 1793.76) p2 (list 114.35 1793.76))
 (command "LINE" p1 p2 "")
 (setq p1 (list 114.50 1793.39) p2 (list 0.00 0.00))
 (command "TEXT" "J" "ML" p1   0.75  0.00 "244")
 (command "LAYER" "S" "CGBTHK" "")
 (setq p1 (list 119.00 1793.39) p2 (list 0.00 0.00))
 (command "TEXT" "J" "ML" p1   0.75  0.00 "0.38")
 (command "LAYER" "S" "CGBHZID" "")
 (setq p1 (list 123.50 1793.39) p2 (list 0.00 0.00))
 (command "TEXT" "J" "ML" p1   0.75  0.00 "")
 (setq p1 (list 125.75 1793.39) p2 (list 0.00 0.00))
 (command "TEXT" "J" "ML" p1   0.75  0.00 "8451")
 (command "LAYER" "S" "CGBLITHTXT" "")
 (setq p1 (list 129.50 1793.39) p2 (list 0.00 0.00))
 (command "TEXT" "J" "ML" p1   0.75  0.00 "GRN SH W/LS NODS")
 (command "LAYER" "S" "CGBCMNT" "")
 (setq p1 (list 149.75 1793.39) p2 (list 0.00 0.00))
 (command "TEXT" "J" "ML" p1   0.75  0.00 "")
 (command "LAYER" "S" "CGBMAIN" "")
 (setq p1 (list 107.00 1793.57) p2 (list 113.00 1793.57) p3 (list 113.00 1792.47) p4 (list 107.00 1792.47))
 (command "PLINE" p1 p2 p3 p4 "c")
 (command "HATCH" "ZIGZAG" 5.00 0.00 "L" "")
 (command "COLOR" "BYLAYER")
 (command "LAYER" "S" "CGBLITHCD" "")
 (setq p1 (list 113.00 1793.02) p2 (list 114.35 1791.77))
 (command "LINE" p1 p2 "")
 (setq p1 (list 114.50 1791.40) p2 (list 0.00 0.00))
 (command "TEXT" "J" "ML" p1   0.75  0.00 "906")
 (command "LAYER" "S" "CGBTHK" "")
 (setq p1 (list 119.00 1791.40) p2 (list 0.00 0.00))
 (command "TEXT" "J" "ML" p1   0.75  0.00 "1.10")
 (command "LAYER" "S" "CGBHZID" "")
 (setq p1 (list 123.50 1791.40) p2 (list 0.00 0.00))
 (command "TEXT" "J" "ML" p1   0.75  0.00 "")
 (setq p1 (list 125.75 1791.40) p2 (list 0.00 0.00))
 (command "TEXT" "J" "ML" p1   0.75  0.00 "8451")
 (command "LAYER" "S" "CGBLITHTXT" "")
 (setq p1 (list 129.50 1791.40) p2 (list 0.00 0.00))
 (command "TEXT" "J" "ML" p1   0.75  0.00 "NODULAR FN GRND LS")
 (command "LAYER" "S" "CGBCMNT" "")
 (setq p1 (list 149.75 1791.40) p2 (list 0.00 0.00))
 (command "TEXT" "J" "ML" p1   0.75  0.00 "")
 (command "LAYER" "S" "CGBMAIN" "")
 (setq p1 (list 107.00 1792.47) p2 (list 113.00 1792.47) p3 (list 113.00 1783.15) p4 (list 107.00 1783.15))
 (command "PLINE" p1 p2 p3 p4 "c")
 (command "HATCH" "ZIGZAG" 4.00 0.00 "L" "")
 (command "COLOR" "BYLAYER")
 (command "LAYER" "S" "CGBLITHCD" "")
 (setq p1 (list 113.00 1787.81) p2 (list 114.35 1787.81))
 (command "LINE" p1 p2 "")
 (setq p1 (list 114.50 1787.44) p2 (list 0.00 0.00))
 (command "TEXT" "J" "ML" p1   0.75  0.00 "444")
 (command "LAYER" "S" "CGBTHK" "")
 (setq p1 (list 119.00 1787.44) p2 (list 0.00 0.00))
 (command "TEXT" "J" "ML" p1   0.75  0.00 "9.32")
 (command "LAYER" "S" "CGBHZID" "")
 (setq p1 (list 123.50 1787.44) p2 (list 0.00 0.00))
 (command "TEXT" "J" "ML" p1   0.75  0.00 "")
 (setq p1 (list 125.75 1787.44) p2 (list 0.00 0.00))
 (command "TEXT" "J" "ML" p1   0.75  0.00 "8451")
 (command "LAYER" "S" "CGBLITHTXT" "")
 (setq p1 (list 129.50 1787.44) p2 (list 0.00 0.00))
 (command "TEXT" "J" "ML" p1   0.75  0.00 "GRN SDY SH W/LS NODS")
 (command "LAYER" "S" "CGBCMNT" "")
 (setq p1 (list 149.75 1787.44) p2 (list 0.00 0.00))
 (command "TEXT" "J" "ML" p1   0.75  0.00 "")
 (command "LAYER" "S" "CGBMAIN" "")
 (setq p1 (list 107.00 1783.15) p2 (list 113.00 1783.15) p3 (list 113.00 1775.05) p4 (list 107.00 1775.05))
 (command "PLINE" p1 p2 p3 p4 "c")
 (command "HATCH" "ZIGZAG" 4.00 0.00 "L" "")
 (command "COLOR" "BYLAYER")
 (command "LAYER" "S" "CGBLITHCD" "")
 (setq p1 (list 113.00 1779.10) p2 (list 114.35 1779.10))
 (command "LINE" p1 p2 "")
 (setq p1 (list 114.50 1778.73) p2 (list 0.00 0.00))
 (command "TEXT" "J" "ML" p1   0.75  0.00 "444")
 (command "LAYER" "S" "CGBTHK" "")
 (setq p1 (list 119.00 1778.73) p2 (list 0.00 0.00))
 (command "TEXT" "J" "ML" p1   0.75  0.00 "8.10")
 (command "LAYER" "S" "CGBHZID" "")
 (setq p1 (list 123.50 1778.73) p2 (list 0.00 0.00))
 (command "TEXT" "J" "ML" p1   0.75  0.00 "")
 (setq p1 (list 125.75 1778.73) p2 (list 0.00 0.00))
 (command "TEXT" "J" "ML" p1   0.75  0.00 "8451")
 (command "LAYER" "S" "CGBLITHTXT" "")
 (setq p1 (list 129.50 1778.73) p2 (list 0.00 0.00))
 (command "TEXT" "J" "ML" p1   0.75  0.00 "GRN SDY SH W/LS NODS")
 (command "LAYER" "S" "CGBCMNT" "")
 (setq p1 (list 149.75 1778.73) p2 (list 0.00 0.00))
 (command "TEXT" "J" "ML" p1   0.75  0.00 "")
 (command "LAYER" "S" "CGBMAIN" "")
 (setq p1 (list 107.00 1775.05) p2 (list 113.00 1775.05) p3 (list 113.00 1772.41) p4 (list 107.00 1772.41))
 (command "PLINE" p1 p2 p3 p4 "c")
 (command "HATCH" "ZIGZAG" 4.00 0.00 "L" "")
 (command "COLOR" "BYLAYER")
 (command "LAYER" "S" "CGBLITHCD" "")
 (setq p1 (list 113.00 1773.73) p2 (list 114.35 1773.73))
 (command "LINE" p1 p2 "")
 (setq p1 (list 114.50 1773.36) p2 (list 0.00 0.00))
 (command "TEXT" "J" "ML" p1   0.75  0.00 "122")
 (command "LAYER" "S" "CGBTHK" "")
 (setq p1 (list 119.00 1773.36) p2 (list 0.00 0.00))
 (command "TEXT" "J" "ML" p1   0.75  0.00 "2.64")
 (command "LAYER" "S" "CGBHZID" "")
 (setq p1 (list 123.50 1773.36) p2 (list 0.00 0.00))
 (command "TEXT" "J" "ML" p1   0.75  0.00 "")
 (setq p1 (list 125.75 1773.36) p2 (list 0.00 0.00))
 (command "TEXT" "J" "ML" p1   0.75  0.00 "8451")
 (command "LAYER" "S" "CGBLITHTXT" "")
 (setq p1 (list 129.50 1773.36) p2 (list 0.00 0.00))
 (command "TEXT" "J" "ML" p1   0.75  0.00 "DK GRY LAYERED SH")
 (command "LAYER" "S" "CGBCMNT" "")
 (setq p1 (list 149.75 1773.36) p2 (list 0.00 0.00))
 (command "TEXT" "J" "ML" p1   0.75  0.00 "SFT, GRN & BL")
 (command "LAYER" "S" "CGBMAIN" "")
 (setq p1 (list 107.00 1772.41) p2 (list 113.00 1772.41) p3 (list 113.00 1769.65) p4 (list 107.00 1769.65))
 (command "PLINE" p1 p2 p3 p4 "c")
 (command "HATCH" "ZIGZAG" 0.25 0.00 "L" "")
 (command "COLOR" "BYLAYER")
 (command "LAYER" "S" "CGBLITHCD" "")
 (setq p1 (list 113.00 1771.03) p2 (list 114.35 1771.03))
 (command "LINE" p1 p2 "")
 (setq p1 (list 114.50 1770.66) p2 (list 0.00 0.00))
 (command "TEXT" "J" "ML" p1   0.75  0.00 "127")
 (command "LAYER" "S" "CGBTHK" "")
 (setq p1 (list 119.00 1770.66) p2 (list 0.00 0.00))
 (command "TEXT" "J" "ML" p1   0.75  0.00 "2.76")
 (command "LAYER" "S" "CGBHZID" "")
 (setq p1 (list 123.50 1770.66) p2 (list 0.00 0.00))
 (command "TEXT" "J" "ML" p1   0.75  0.00 "")
 (setq p1 (list 125.75 1770.66) p2 (list 0.00 0.00))
 (command "TEXT" "J" "ML" p1   0.75  0.00 "8451")
 (command "LAYER" "S" "CGBLITHTXT" "")
 (setq p1 (list 129.50 1770.66) p2 (list 0.00 0.00))
 (command "TEXT" "J" "ML" p1   0.75  0.00 "DRK GRY FIRECLAY")
 (command "LAYER" "S" "CGBCMNT" "")
 (setq p1 (list 149.75 1770.66) p2 (list 0.00 0.00))
 (command "TEXT" "J" "ML" p1   0.75  0.00 "BRKN W/SLX")
 (command "LAYER" "S" "CGBMAIN" "")
 (setq p1 (list 107.00 1769.65) p2 (list 113.00 1769.65) p3 (list 113.00 1768.25) p4 (list 107.00 1768.25))
 (command "PLINE" p1 p2 p3 p4 "c")
 (command "HATCH" "ZIGZAG" 5.00 0.00 "L" "")
 (command "COLOR" "BYLAYER")
 (command "LAYER" "S" "CGBLITHCD" "")
 (setq p1 (list 113.00 1768.95) p2 (list 114.35 1768.95))
 (command "LINE" p1 p2 "")
 (setq p1 (list 114.50 1768.58) p2 (list 0.00 0.00))
 (command "TEXT" "J" "ML" p1   0.75  0.00 "147")
 (command "LAYER" "S" "CGBTHK" "")
 (setq p1 (list 119.00 1768.58) p2 (list 0.00 0.00))
 (command "TEXT" "J" "ML" p1   0.75  0.00 "1.40")
 (command "LAYER" "S" "CGBHZID" "")
 (setq p1 (list 123.50 1768.58) p2 (list 0.00 0.00))
 (command "TEXT" "J" "ML" p1   0.75  0.00 "")
 (setq p1 (list 125.75 1768.58) p2 (list 0.00 0.00))
 (command "TEXT" "J" "ML" p1   0.75  0.00 "8451")
 (command "LAYER" "S" "CGBLITHTXT" "")
 (setq p1 (list 129.50 1768.58) p2 (list 0.00 0.00))
 (command "TEXT" "J" "ML" p1   0.75  0.00 "GRN CLYSTN")
 (command "LAYER" "S" "CGBCMNT" "")
 (setq p1 (list 149.75 1768.58) p2 (list 0.00 0.00))
 (command "TEXT" "J" "ML" p1   0.75  0.00 "V SFT, CRMB")
 (command "LAYER" "S" "CGBMAIN" "")
 (setq p1 (list 107.00 1768.25) p2 (list 113.00 1768.25) p3 (list 113.00 1767.41) p4 (list 107.00 1767.41))
 (command "PLINE" p1 p2 p3 p4 "c")
 (command "HATCH" "ZIGZAG" 5.00 0.00 "L" "")
 (command "COLOR" "BYLAYER")
 (command "LAYER" "S" "CGBLITHCD" "")
 (setq p1 (list 113.00 1767.83) p2 (list 114.35 1766.58))
 (command "LINE" p1 p2 "")
 (setq p1 (list 114.50 1766.21) p2 (list 0.00 0.00))
 (command "TEXT" "J" "ML" p1   0.75  0.00 "147")
 (command "LAYER" "S" "CGBTHK" "")
 (setq p1 (list 119.00 1766.21) p2 (list 0.00 0.00))
 (command "TEXT" "J" "ML" p1   0.75  0.00 "0.84")
 (command "LAYER" "S" "CGBHZID" "")
 (setq p1 (list 123.50 1766.21) p2 (list 0.00 0.00))
 (command "TEXT" "J" "ML" p1   0.75  0.00 "")
 (setq p1 (list 125.75 1766.21) p2 (list 0.00 0.00))
 (command "TEXT" "J" "ML" p1   0.75  0.00 "8451")
 (command "LAYER" "S" "CGBLITHTXT" "")
 (setq p1 (list 129.50 1766.21) p2 (list 0.00 0.00))
 (command "TEXT" "J" "ML" p1   0.75  0.00 "GRN CLYSTN")
 (command "LAYER" "S" "CGBCMNT" "")
 (setq p1 (list 149.75 1766.21) p2 (list 0.00 0.00))
 (command "TEXT" "J" "ML" p1   0.75  0.00 "")
 (command "LAYER" "S" "CGBMAIN" "")
 (setq p1 (list 107.00 1767.41) p2 (list 113.00 1767.41) p3 (list 113.00 1757.15) p4 (list 107.00 1757.15))
 (command "PLINE" p1 p2 p3 p4 "c")
 (command "HATCH" "ZIGZAG" 5.00 0.00 "L" "")
 (command "COLOR" "BYLAYER")
 (command "LAYER" "S" "CGBLITHCD" "")
 (setq p1 (list 113.00 1762.28) p2 (list 114.35 1762.28))
 (command "LINE" p1 p2 "")
 (setq p1 (list 114.50 1761.91) p2 (list 0.00 0.00))
 (command "TEXT" "J" "ML" p1   0.75  0.00 "244")
 (command "LAYER" "S" "CGBTHK" "")
 (setq p1 (list 119.00 1761.91) p2 (list 0.00 0.00))
 (command "TEXT" "J" "ML" p1   0.75  0.00 "10.26")
 (command "LAYER" "S" "CGBHZID" "")
 (setq p1 (list 123.50 1761.91) p2 (list 0.00 0.00))
 (command "TEXT" "J" "ML" p1   0.75  0.00 "")
 (setq p1 (list 125.75 1761.91) p2 (list 0.00 0.00))
 (command "TEXT" "J" "ML" p1   0.75  0.00 "8451")
 (command "LAYER" "S" "CGBLITHTXT" "")
 (setq p1 (list 129.50 1761.91) p2 (list 0.00 0.00))
 (command "TEXT" "J" "ML" p1   0.75  0.00 "GRN SH W/LS NODS")
 (command "LAYER" "S" "CGBCMNT" "")
 (setq p1 (list 149.75 1761.91) p2 (list 0.00 0.00))
 (command "TEXT" "J" "ML" p1   0.75  0.00 "VEINS")
 (command "LAYER" "S" "CGBMAIN" "")
 (setq p1 (list 107.00 1757.15) p2 (list 113.00 1757.15) p3 (list 113.00 1756.52) p4 (list 107.00 1756.52))
 (command "PLINE" p1 p2 p3 p4 "c")
 (command "HATCH" "ZIGZAG" 5.00 0.00 "L" "")
 (command "COLOR" "BYLAYER")
 (command "LAYER" "S" "CGBLITHCD" "")
 (setq p1 (list 113.00 1756.84) p2 (list 114.35 1756.84))
 (command "LINE" p1 p2 "")
 (setq p1 (list 114.50 1756.46) p2 (list 0.00 0.00))
 (command "TEXT" "J" "ML" p1   0.75  0.00 "906")
 (command "LAYER" "S" "CGBTHK" "")
 (setq p1 (list 119.00 1756.46) p2 (list 0.00 0.00))
 (command "TEXT" "J" "ML" p1   0.75  0.00 "0.63")
 (command "LAYER" "S" "CGBHZID" "")
 (setq p1 (list 123.50 1756.46) p2 (list 0.00 0.00))
 (command "TEXT" "J" "ML" p1   0.75  0.00 "")
 (setq p1 (list 125.75 1756.46) p2 (list 0.00 0.00))
 (command "TEXT" "J" "ML" p1   0.75  0.00 "8451")
 (command "LAYER" "S" "CGBLITHTXT" "")
 (setq p1 (list 129.50 1756.46) p2 (list 0.00 0.00))
 (command "TEXT" "J" "ML" p1   0.75  0.00 "NODULAR FN GRND LS")
 (command "LAYER" "S" "CGBCMNT" "")
 (setq p1 (list 149.75 1756.46) p2 (list 0.00 0.00))
 (command "TEXT" "J" "ML" p1   0.75  0.00 "")
 (command "LAYER" "S" "CGBMAIN" "")
 (setq p1 (list 107.00 1756.52) p2 (list 113.00 1756.52) p3 (list 113.00 1754.71) p4 (list 107.00 1754.71))
 (command "PLINE" p1 p2 p3 p4 "c")
 (command "HATCH" "ZIGZAG" 5.00 0.00 "L" "")
 (command "COLOR" "BYLAYER")
 (command "LAYER" "S" "CGBLITHCD" "")
 (setq p1 (list 113.00 1755.62) p2 (list 114.35 1754.37))
 (command "LINE" p1 p2 "")
 (setq p1 (list 114.50 1753.99) p2 (list 0.00 0.00))
 (command "TEXT" "J" "ML" p1   0.75  0.00 "244")
 (command "LAYER" "S" "CGBTHK" "")
 (setq p1 (list 119.00 1753.99) p2 (list 0.00 0.00))
 (command "TEXT" "J" "ML" p1   0.75  0.00 "1.81")
 (command "LAYER" "S" "CGBHZID" "")
 (setq p1 (list 123.50 1753.99) p2 (list 0.00 0.00))
 (command "TEXT" "J" "ML" p1   0.75  0.00 "")
 (setq p1 (list 125.75 1753.99) p2 (list 0.00 0.00))
 (command "TEXT" "J" "ML" p1   0.75  0.00 "8451")
 (command "LAYER" "S" "CGBLITHTXT" "")
 (setq p1 (list 129.50 1753.99) p2 (list 0.00 0.00))
 (command "TEXT" "J" "ML" p1   0.75  0.00 "GRN SH W/LS NODS")
 (command "LAYER" "S" "CGBCMNT" "")
 (setq p1 (list 149.75 1753.99) p2 (list 0.00 0.00))
 (command "TEXT" "J" "ML" p1   0.75  0.00 "BRKN")
 (command "LAYER" "S" "CGBMAIN" "")
 (setq p1 (list 107.00 1754.71) p2 (list 113.00 1754.71) p3 (list 113.00 1753.25) p4 (list 107.00 1753.25))
 (command "PLINE" p1 p2 p3 p4 "c")
 (command "HATCH" "ZIGZAG" 4.00 0.00 "L" "")
 (command "COLOR" "BYLAYER")
 (command "LAYER" "S" "CGBLITHCD" "")
 (setq p1 (list 113.00 1753.98) p2 (list 114.35 1753.12))
 (command "LINE" p1 p2 "")
 (setq p1 (list 114.50 1752.74) p2 (list 0.00 0.00))
 (command "TEXT" "J" "ML" p1   0.75  0.00 "122")
 (command "LAYER" "S" "CGBTHK" "")
 (setq p1 (list 119.00 1752.74) p2 (list 0.00 0.00))
 (command "TEXT" "J" "ML" p1   0.75  0.00 "1.46")
 (command "LAYER" "S" "CGBHZID" "")
 (setq p1 (list 123.50 1752.74) p2 (list 0.00 0.00))
 (command "TEXT" "J" "ML" p1   0.75  0.00 "")
 (setq p1 (list 125.75 1752.74) p2 (list 0.00 0.00))
 (command "TEXT" "J" "ML" p1   0.75  0.00 "8451")
 (command "LAYER" "S" "CGBLITHTXT" "")
 (setq p1 (list 129.50 1752.74) p2 (list 0.00 0.00))
 (command "TEXT" "J" "ML" p1   0.75  0.00 "DK GRY LAYERED SH")
 (command "LAYER" "S" "CGBCMNT" "")
 (setq p1 (list 149.75 1752.74) p2 (list 0.00 0.00))
 (command "TEXT" "J" "ML" p1   0.75  0.00 "SFT, SLX")
 (command "LAYER" "S" "CGBMAIN" "")
 (setq p1 (list 107.00 1753.25) p2 (list 113.00 1753.25) p3 (list 113.00 1747.77) p4 (list 107.00 1747.77))
 (command "PLINE" p1 p2 p3 p4 "c")
 (command "HATCH" "ZIGZAG" 5.00 0.00 "L" "")
 (command "COLOR" "BYLAYER")
 (command "LAYER" "S" "CGBLITHCD" "")
 (setq p1 (list 113.00 1750.51) p2 (list 114.35 1750.51))
 (command "LINE" p1 p2 "")
 (setq p1 (list 114.50 1750.14) p2 (list 0.00 0.00))
 (command "TEXT" "J" "ML" p1   0.75  0.00 "274")
 (command "LAYER" "S" "CGBTHK" "")
 (setq p1 (list 119.00 1750.14) p2 (list 0.00 0.00))
 (command "TEXT" "J" "ML" p1   0.75  0.00 "5.48")
 (command "LAYER" "S" "CGBHZID" "")
 (setq p1 (list 123.50 1750.14) p2 (list 0.00 0.00))
 (command "TEXT" "J" "ML" p1   0.75  0.00 "")
 (setq p1 (list 125.75 1750.14) p2 (list 0.00 0.00))
 (command "TEXT" "J" "ML" p1   0.75  0.00 "8451")
 (command "LAYER" "S" "CGBLITHTXT" "")
 (setq p1 (list 129.50 1750.14) p2 (list 0.00 0.00))
 (command "TEXT" "J" "ML" p1   0.75  0.00 "GRY/GRN SH W/LS NODS")
 (command "LAYER" "S" "CGBCMNT" "")
 (setq p1 (list 149.75 1750.14) p2 (list 0.00 0.00))
 (command "TEXT" "J" "ML" p1   0.75  0.00 "SFT, SLX")
 (command "LAYER" "S" "CGBMAIN" "")
 (setq p1 (list 107.00 1747.77) p2 (list 113.00 1747.77) p3 (list 113.00 1745.35) p4 (list 107.00 1745.35))
 (command "PLINE" p1 p2 p3 p4 "c")
 (command "HATCH" "ZIGZAG" 4.00 0.00 "L" "")
 (command "COLOR" "BYLAYER")
 (command "LAYER" "S" "CGBLITHCD" "")
 (setq p1 (list 113.00 1746.56) p2 (list 114.35 1746.56))
 (command "LINE" p1 p2 "")
 (setq p1 (list 114.50 1746.19) p2 (list 0.00 0.00))
 (command "TEXT" "J" "ML" p1   0.75  0.00 "125")
 (command "LAYER" "S" "CGBTHK" "")
 (setq p1 (list 119.00 1746.19) p2 (list 0.00 0.00))
 (command "TEXT" "J" "ML" p1   0.75  0.00 "2.42")
 (command "LAYER" "S" "CGBHZID" "")
 (setq p1 (list 123.50 1746.19) p2 (list 0.00 0.00))
 (command "TEXT" "J" "ML" p1   0.75  0.00 "")
 (setq p1 (list 125.75 1746.19) p2 (list 0.00 0.00))
 (command "TEXT" "J" "ML" p1   0.75  0.00 "8451")
 (command "LAYER" "S" "CGBLITHTXT" "")
 (setq p1 (list 129.50 1746.19) p2 (list 0.00 0.00))
 (command "TEXT" "J" "ML" p1   0.75  0.00 "DRK GRY CHRND SH")
 (command "LAYER" "S" "CGBCMNT" "")
 (setq p1 (list 149.75 1746.19) p2 (list 0.00 0.00))
 (command "TEXT" "J" "ML" p1   0.75  0.00 "SFT")
 (command "LAYER" "S" "CGBMAIN" "")
 (setq p1 (list 107.00 1745.35) p2 (list 113.00 1745.35) p3 (list 113.00 1740.67) p4 (list 107.00 1740.67))
 (command "PLINE" p1 p2 p3 p4 "c")
 (command "HATCH" "ZIGZAG" 5.00 0.00 "L" "")
 (command "COLOR" "BYLAYER")
 (command "LAYER" "S" "CGBLITHCD" "")
 (setq p1 (list 113.00 1743.01) p2 (list 114.35 1743.01))
 (command "LINE" p1 p2 "")
 (setq p1 (list 114.50 1742.64) p2 (list 0.00 0.00))
 (command "TEXT" "J" "ML" p1   0.75  0.00 "274")
 (command "LAYER" "S" "CGBTHK" "")
 (setq p1 (list 119.00 1742.64) p2 (list 0.00 0.00))
 (command "TEXT" "J" "ML" p1   0.75  0.00 "4.68")
 (command "LAYER" "S" "CGBHZID" "")
 (setq p1 (list 123.50 1742.64) p2 (list 0.00 0.00))
 (command "TEXT" "J" "ML" p1   0.75  0.00 "")
 (setq p1 (list 125.75 1742.64) p2 (list 0.00 0.00))
 (command "TEXT" "J" "ML" p1   0.75  0.00 "8451")
 (command "LAYER" "S" "CGBLITHTXT" "")
 (setq p1 (list 129.50 1742.64) p2 (list 0.00 0.00))
 (command "TEXT" "J" "ML" p1   0.75  0.00 "GRY/GRN SH W/LS NODS")
 (command "LAYER" "S" "CGBCMNT" "")
 (setq p1 (list 149.75 1742.64) p2 (list 0.00 0.00))
 (command "TEXT" "J" "ML" p1   0.75  0.00 "")
 (command "LAYER" "S" "CGBMAIN" "")
 (command "LAYER" "S" "CGBLITHCD" "")
 (setq p1 (list 113.00 1740.67) p2 (list 114.35 1740.67))
 (command "LINE" p1 p2 "")
 (setq p1 (list 114.50 1740.30) p2 (list 0.00 0.00))
 (command "TEXT" "J" "ML" p1   0.75  0.00 "020")
 (command "LAYER" "S" "CGBTHK" "")
 (setq p1 (list 119.00 1740.30) p2 (list 0.00 0.00))
 (command "TEXT" "J" "ML" p1   0.75  0.00 "0.00")
 (command "LAYER" "S" "CGBHZID" "")
 (setq p1 (list 123.50 1740.30) p2 (list 0.00 0.00))
 (command "TEXT" "J" "ML" p1   0.75  0.00 "")
 (setq p1 (list 125.75 1740.30) p2 (list 0.00 0.00))
 (command "TEXT" "J" "ML" p1   0.75  0.00 "8000")
 (command "LAYER" "S" "CGBLITHTXT" "")
 (setq p1 (list 129.50 1740.30) p2 (list 0.00 0.00))
 (command "TEXT" "J" "ML" p1   0.75  0.00 "COAL")
 (command "LAYER" "S" "CGBCMNT" "")
 (setq p1 (list 149.75 1740.30) p2 (list 0.00 0.00))
 (command "TEXT" "J" "ML" p1   0.75  0.00 "BAK HRZN")
 (command "LAYER" "S" "CGBMAIN" "")
 (setq p1 (list 107.00 1740.67) p2 (list 113.00 1740.67) p3 (list 113.00 1739.55) p4 (list 107.00 1739.55))
 (command "PLINE" p1 p2 p3 p4 "c")
 (command "HATCH" "ZIGZAG" 4.00 0.00 "L" "")
 (command "COLOR" "BYLAYER")
 (command "LAYER" "S" "CGBLITHCD" "")
 (setq p1 (list 113.00 1740.11) p2 (list 114.35 1738.86))
 (command "LINE" p1 p2 "")
 (setq p1 (list 114.50 1738.49) p2 (list 0.00 0.00))
 (command "TEXT" "J" "ML" p1   0.75  0.00 "125")
 (command "LAYER" "S" "CGBTHK" "")
 (setq p1 (list 119.00 1738.49) p2 (list 0.00 0.00))
 (command "TEXT" "J" "ML" p1   0.75  0.00 "1.12")
 (command "LAYER" "S" "CGBHZID" "")
 (setq p1 (list 123.50 1738.49) p2 (list 0.00 0.00))
 (command "TEXT" "J" "ML" p1   0.75  0.00 "")
 (setq p1 (list 125.75 1738.49) p2 (list 0.00 0.00))
 (command "TEXT" "J" "ML" p1   0.75  0.00 "7951")
 (command "LAYER" "S" "CGBLITHTXT" "")
 (setq p1 (list 129.50 1738.49) p2 (list 0.00 0.00))
 (command "TEXT" "J" "ML" p1   0.75  0.00 "DRK GRY CHRND SH")
 (command "LAYER" "S" "CGBCMNT" "")
 (setq p1 (list 149.75 1738.49) p2 (list 0.00 0.00))
 (command "TEXT" "J" "ML" p1   0.75  0.00 "BRKN, CRMB")
 (command "LAYER" "S" "CGBMAIN" "")
 (setq p1 (list 107.00 1739.55) p2 (list 113.00 1739.55) p3 (list 113.00 1738.65) p4 (list 107.00 1738.65))
 (command "PLINE" p1 p2 p3 p4 "c")
 (command "HATCH" "ZIGZAG" 4.00 0.00 "L" "")
 (command "COLOR" "BYLAYER")
 (command "LAYER" "S" "CGBLITHCD" "")
 (setq p1 (list 113.00 1739.10) p2 (list 114.35 1737.61))
 (command "LINE" p1 p2 "")
 (setq p1 (list 114.50 1737.24) p2 (list 0.00 0.00))
 (command "TEXT" "J" "ML" p1   0.75  0.00 "344")
 (command "LAYER" "S" "CGBTHK" "")
 (setq p1 (list 119.00 1737.24) p2 (list 0.00 0.00))
 (command "TEXT" "J" "ML" p1   0.75  0.00 "0.90")
 (command "LAYER" "S" "CGBHZID" "")
 (setq p1 (list 123.50 1737.24) p2 (list 0.00 0.00))
 (command "TEXT" "J" "ML" p1   0.75  0.00 "")
 (setq p1 (list 125.75 1737.24) p2 (list 0.00 0.00))
 (command "TEXT" "J" "ML" p1   0.75  0.00 "7951")
 (command "LAYER" "S" "CGBLITHTXT" "")
 (setq p1 (list 129.50 1737.24) p2 (list 0.00 0.00))
 (command "TEXT" "J" "ML" p1   0.75  0.00 "GRN MASS SDY SH")
 (command "LAYER" "S" "CGBCMNT" "")
 (setq p1 (list 149.75 1737.24) p2 (list 0.00 0.00))
 (command "TEXT" "J" "ML" p1   0.75  0.00 "")
 (command "LAYER" "S" "CGBMAIN" "")
 (setq p1 (list 107.00 1738.65) p2 (list 113.00 1738.65) p3 (list 113.00 1736.85) p4 (list 107.00 1736.85))
 (command "PLINE" p1 p2 p3 p4 "c")
 (command "HATCH" "ZIGZAG" 3.00 0.00 "L" "")
 (command "COLOR" "BYLAYER")
 (command "LAYER" "S" "CGBLITHCD" "")
 (setq p1 (list 113.00 1737.75) p2 (list 114.35 1736.36))
 (command "LINE" p1 p2 "")
 (setq p1 (list 114.50 1735.99) p2 (list 0.00 0.00))
 (command "TEXT" "J" "ML" p1   0.75  0.00 "157")
 (command "LAYER" "S" "CGBTHK" "")
 (setq p1 (list 119.00 1735.99) p2 (list 0.00 0.00))
 (command "TEXT" "J" "ML" p1   0.75  0.00 "1.80")
 (command "LAYER" "S" "CGBHZID" "")
 (setq p1 (list 123.50 1735.99) p2 (list 0.00 0.00))
 (command "TEXT" "J" "ML" p1   0.75  0.00 "")
 (setq p1 (list 125.75 1735.99) p2 (list 0.00 0.00))
 (command "TEXT" "J" "ML" p1   0.75  0.00 "7951")
 (command "LAYER" "S" "CGBLITHTXT" "")
 (setq p1 (list 129.50 1735.99) p2 (list 0.00 0.00))
 (command "TEXT" "J" "ML" p1   0.75  0.00 "RED+GRN CLYSTN")
 (command "LAYER" "S" "CGBCMNT" "")
 (setq p1 (list 149.75 1735.99) p2 (list 0.00 0.00))
 (command "TEXT" "J" "ML" p1   0.75  0.00 "V SFT, BRKN,S")
 (command "LAYER" "S" "CGBMAIN" "")
 (setq p1 (list 107.00 1736.85) p2 (list 113.00 1736.85) p3 (list 113.00 1735.35) p4 (list 107.00 1735.35))
 (command "PLINE" p1 p2 p3 p4 "c")
 (command "HATCH" "ZIGZAG" 0.25 0.00 "L" "")
 (command "COLOR" "BYLAYER")
 (command "LAYER" "S" "CGBLITHCD" "")
 (setq p1 (list 113.00 1736.10) p2 (list 114.35 1735.11))
 (command "LINE" p1 p2 "")
 (setq p1 (list 114.50 1734.74) p2 (list 0.00 0.00))
 (command "TEXT" "J" "ML" p1   0.75  0.00 "177")
 (command "LAYER" "S" "CGBTHK" "")
 (setq p1 (list 119.00 1734.74) p2 (list 0.00 0.00))
 (command "TEXT" "J" "ML" p1   0.75  0.00 "1.50")
 (command "LAYER" "S" "CGBHZID" "")
 (setq p1 (list 123.50 1734.74) p2 (list 0.00 0.00))
 (command "TEXT" "J" "ML" p1   0.75  0.00 "")
 (setq p1 (list 125.75 1734.74) p2 (list 0.00 0.00))
 (command "TEXT" "J" "ML" p1   0.75  0.00 "7951")
 (command "LAYER" "S" "CGBLITHTXT" "")
 (setq p1 (list 129.50 1734.74) p2 (list 0.00 0.00))
 (command "TEXT" "J" "ML" p1   0.75  0.00 "GRY/GRN FIRECLAY")
 (command "LAYER" "S" "CGBCMNT" "")
 (setq p1 (list 149.75 1734.74) p2 (list 0.00 0.00))
 (command "TEXT" "J" "ML" p1   0.75  0.00 "GB")
 (command "LAYER" "S" "CGBMAIN" "")
 (setq p1 (list 107.00 1735.35) p2 (list 113.00 1735.35) p3 (list 113.00 1732.53) p4 (list 107.00 1732.53))
 (command "PLINE" p1 p2 p3 p4 "c")
 (command "HATCH" "ZIGZAG" 4.00 0.00 "L" "")
 (command "COLOR" "BYLAYER")
 (command "LAYER" "S" "CGBLITHCD" "")
 (setq p1 (list 113.00 1733.94) p2 (list 114.35 1733.86))
 (command "LINE" p1 p2 "")
 (setq p1 (list 114.50 1733.49) p2 (list 0.00 0.00))
 (command "TEXT" "J" "ML" p1   0.75  0.00 "374")
 (command "LAYER" "S" "CGBTHK" "")
 (setq p1 (list 119.00 1733.49) p2 (list 0.00 0.00))
 (command "TEXT" "J" "ML" p1   0.75  0.00 "2.82")
 (command "LAYER" "S" "CGBHZID" "")
 (setq p1 (list 123.50 1733.49) p2 (list 0.00 0.00))
 (command "TEXT" "J" "ML" p1   0.75  0.00 "")
 (setq p1 (list 125.75 1733.49) p2 (list 0.00 0.00))
 (command "TEXT" "J" "ML" p1   0.75  0.00 "7951")
 (command "LAYER" "S" "CGBLITHTXT" "")
 (setq p1 (list 129.50 1733.49) p2 (list 0.00 0.00))
 (command "TEXT" "J" "ML" p1   0.75  0.00 "GRY/GRN SDY SH")
 (command "LAYER" "S" "CGBCMNT" "")
 (setq p1 (list 149.75 1733.49) p2 (list 0.00 0.00))
 (command "TEXT" "J" "ML" p1   0.75  0.00 "GB")
 (command "LAYER" "S" "CGBMAIN" "")
 (setq p1 (list 107.00 1732.53) p2 (list 113.00 1732.53) p3 (list 113.00 1723.55) p4 (list 107.00 1723.55))
 (command "PLINE" p1 p2 p3 p4 "c")
 (command "HATCH" "ZIGZAG" 4.00 0.00 "L" "")
 (command "COLOR" "BYLAYER")
 (command "LAYER" "S" "CGBLITHCD" "")
 (setq p1 (list 113.00 1728.04) p2 (list 114.35 1728.04))
 (command "LINE" p1 p2 "")
 (setq p1 (list 114.50 1727.67) p2 (list 0.00 0.00))
 (command "TEXT" "J" "ML" p1   0.75  0.00 "544")
 (command "LAYER" "S" "CGBTHK" "")
 (setq p1 (list 119.00 1727.67) p2 (list 0.00 0.00))
 (command "TEXT" "J" "ML" p1   0.75  0.00 "8.98")
 (command "LAYER" "S" "CGBHZID" "")
 (setq p1 (list 123.50 1727.67) p2 (list 0.00 0.00))
 (command "TEXT" "J" "ML" p1   0.75  0.00 "")
 (setq p1 (list 125.75 1727.67) p2 (list 0.00 0.00))
 (command "TEXT" "J" "ML" p1   0.75  0.00 "7951")
 (command "LAYER" "S" "CGBLITHTXT" "")
 (setq p1 (list 129.50 1727.67) p2 (list 0.00 0.00))
 (command "TEXT" "J" "ML" p1   0.75  0.00 "GRY MASS SS")
 (command "LAYER" "S" "CGBCMNT" "")
 (setq p1 (list 149.75 1727.67) p2 (list 0.00 0.00))
 (command "TEXT" "J" "ML" p1   0.75  0.00 "")
 (command "LAYER" "S" "CGBMAIN" "")
 (setq p1 (list 107.00 1723.55) p2 (list 113.00 1723.55) p3 (list 113.00 1703.65) p4 (list 107.00 1703.65))
 (command "PLINE" p1 p2 p3 p4 "c")
 (command "HATCH" "ZIGZAG" 4.00 0.00 "L" "")
 (command "COLOR" "BYLAYER")
 (command "LAYER" "S" "CGBLITHCD" "")
 (setq p1 (list 113.00 1713.60) p2 (list 114.35 1713.60))
 (command "LINE" p1 p2 "")
 (setq p1 (list 114.50 1713.23) p2 (list 0.00 0.00))
 (command "TEXT" "J" "ML" p1   0.75  0.00 "544")
 (command "LAYER" "S" "CGBTHK" "")
 (setq p1 (list 119.00 1713.23) p2 (list 0.00 0.00))
 (command "TEXT" "J" "ML" p1   0.75  0.00 "19.90")
 (command "LAYER" "S" "CGBHZID" "")
 (setq p1 (list 123.50 1713.23) p2 (list 0.00 0.00))
 (command "TEXT" "J" "ML" p1   0.75  0.00 "")
 (setq p1 (list 125.75 1713.23) p2 (list 0.00 0.00))
 (command "TEXT" "J" "ML" p1   0.75  0.00 "7951")
 (command "LAYER" "S" "CGBLITHTXT" "")
 (setq p1 (list 129.50 1713.23) p2 (list 0.00 0.00))
 (command "TEXT" "J" "ML" p1   0.75  0.00 "GRY MASS SS")
 (command "LAYER" "S" "CGBCMNT" "")
 (setq p1 (list 149.75 1713.23) p2 (list 0.00 0.00))
 (command "TEXT" "J" "ML" p1   0.75  0.00 "CRSN DWN")
 (command "LAYER" "S" "CGBMAIN" "")
 (setq p1 (list 107.00 1703.65) p2 (list 113.00 1703.65) p3 (list 113.00 1702.95) p4 (list 107.00 1702.95))
 (command "PLINE" p1 p2 p3 p4 "c")
 (command "HATCH" "ZIGZAG" 4.00 0.00 "L" "")
 (command "COLOR" "BYLAYER")
 (command "LAYER" "S" "CGBLITHCD" "")
 (setq p1 (list 113.00 1703.30) p2 (list 114.35 1703.30))
 (command "LINE" p1 p2 "")
 (setq p1 (list 114.50 1702.93) p2 (list 0.00 0.00))
 (command "TEXT" "J" "ML" p1   0.75  0.00 "543")
 (command "LAYER" "S" "CGBTHK" "")
 (setq p1 (list 119.00 1702.93) p2 (list 0.00 0.00))
 (command "TEXT" "J" "ML" p1   0.75  0.00 "0.70")
 (command "LAYER" "S" "CGBHZID" "")
 (setq p1 (list 123.50 1702.93) p2 (list 0.00 0.00))
 (command "TEXT" "J" "ML" p1   0.75  0.00 "")
 (setq p1 (list 125.75 1702.93) p2 (list 0.00 0.00))
 (command "TEXT" "J" "ML" p1   0.75  0.00 "7951")
 (command "LAYER" "S" "CGBLITHTXT" "")
 (setq p1 (list 129.50 1702.93) p2 (list 0.00 0.00))
 (command "TEXT" "J" "ML" p1   0.75  0.00 "GRY SS W/SH STKS")
 (command "LAYER" "S" "CGBCMNT" "")
 (setq p1 (list 149.75 1702.93) p2 (list 0.00 0.00))
 (command "TEXT" "J" "ML" p1   0.75  0.00 "SLC")
 (command "LAYER" "S" "CGBMAIN" "")
 (setq p1 (list 107.00 1702.95) p2 (list 113.00 1702.95) p3 (list 113.00 1683.10) p4 (list 107.00 1683.10))
 (command "PLINE" p1 p2 p3 p4 "c")
 (command "HATCH" "ZIGZAG" 4.00 0.00 "L" "")
 (command "COLOR" "BYLAYER")
 (command "LAYER" "S" "CGBLITHCD" "")
 (setq p1 (list 113.00 1693.03) p2 (list 114.35 1693.03))
 (command "LINE" p1 p2 "")
 (setq p1 (list 114.50 1692.65) p2 (list 0.00 0.00))
 (command "TEXT" "J" "ML" p1   0.75  0.00 "541")
 (command "LAYER" "S" "CGBTHK" "")
 (setq p1 (list 119.00 1692.65) p2 (list 0.00 0.00))
 (command "TEXT" "J" "ML" p1   0.75  0.00 "19.85")
 (command "LAYER" "S" "CGBHZID" "")
 (setq p1 (list 123.50 1692.65) p2 (list 0.00 0.00))
 (command "TEXT" "J" "ML" p1   0.75  0.00 "")
 (setq p1 (list 125.75 1692.65) p2 (list 0.00 0.00))
 (command "TEXT" "J" "ML" p1   0.75  0.00 "7951")
 (command "LAYER" "S" "CGBLITHTXT" "")
 (setq p1 (list 129.50 1692.65) p2 (list 0.00 0.00))
 (command "TEXT" "J" "ML" p1   0.75  0.00 "GRY CROSSBED SS")
 (command "LAYER" "S" "CGBCMNT" "")
 (setq p1 (list 149.75 1692.65) p2 (list 0.00 0.00))
 (command "TEXT" "J" "ML" p1   0.75  0.00 "CRSN DWN")
 (command "LAYER" "S" "CGBMAIN" "")
 (setq p1 (list 107.00 1683.10) p2 (list 113.00 1683.10) p3 (list 113.00 1672.50) p4 (list 107.00 1672.50))
 (command "PLINE" p1 p2 p3 p4 "c")
 (command "HATCH" "ZIGZAG" 4.00 0.00 "L" "")
 (command "COLOR" "BYLAYER")
 (command "LAYER" "S" "CGBLITHCD" "")
 (setq p1 (list 113.00 1677.80) p2 (list 114.35 1677.80))
 (command "LINE" p1 p2 "")
 (setq p1 (list 114.50 1677.43) p2 (list 0.00 0.00))
 (command "TEXT" "J" "ML" p1   0.75  0.00 "541")
 (command "LAYER" "S" "CGBTHK" "")
 (setq p1 (list 119.00 1677.43) p2 (list 0.00 0.00))
 (command "TEXT" "J" "ML" p1   0.75  0.00 "10.60")
 (command "LAYER" "S" "CGBHZID" "")
 (setq p1 (list 123.50 1677.43) p2 (list 0.00 0.00))
 (command "TEXT" "J" "ML" p1   0.75  0.00 "")
 (setq p1 (list 125.75 1677.43) p2 (list 0.00 0.00))
 (command "TEXT" "J" "ML" p1   0.75  0.00 "7951")
 (command "LAYER" "S" "CGBLITHTXT" "")
 (setq p1 (list 129.50 1677.43) p2 (list 0.00 0.00))
 (command "TEXT" "J" "ML" p1   0.75  0.00 "GRY CROSSBED SS")
 (command "LAYER" "S" "CGBCMNT" "")
 (setq p1 (list 149.75 1677.43) p2 (list 0.00 0.00))
 (command "TEXT" "J" "ML" p1   0.75  0.00 "SLC, FRAC @ B")
 (command "LAYER" "S" "CGBMAIN" "")
 (setq p1 (list 107.00 1672.50) p2 (list 113.00 1672.50) p3 (list 113.00 1670.10) p4 (list 107.00 1670.10))
 (command "PLINE" p1 p2 p3 p4 "c")
 (command "HATCH" "ZIGZAG" 4.00 0.00 "L" "")
 (command "COLOR" "BYLAYER")
 (command "LAYER" "S" "CGBLITHCD" "")
 (setq p1 (list 113.00 1671.30) p2 (list 114.35 1671.30))
 (command "LINE" p1 p2 "")
 (setq p1 (list 114.50 1670.93) p2 (list 0.00 0.00))
 (command "TEXT" "J" "ML" p1   0.75  0.00 "344")
 (command "LAYER" "S" "CGBTHK" "")
 (setq p1 (list 119.00 1670.93) p2 (list 0.00 0.00))
 (command "TEXT" "J" "ML" p1   0.75  0.00 "2.40")
 (command "LAYER" "S" "CGBHZID" "")
 (setq p1 (list 123.50 1670.93) p2 (list 0.00 0.00))
 (command "TEXT" "J" "ML" p1   0.75  0.00 "")
 (setq p1 (list 125.75 1670.93) p2 (list 0.00 0.00))
 (command "TEXT" "J" "ML" p1   0.75  0.00 "7951")
 (command "LAYER" "S" "CGBLITHTXT" "")
 (setq p1 (list 129.50 1670.93) p2 (list 0.00 0.00))
 (command "TEXT" "J" "ML" p1   0.75  0.00 "GRN MASS SDY SH")
 (command "LAYER" "S" "CGBCMNT" "")
 (setq p1 (list 149.75 1670.93) p2 (list 0.00 0.00))
 (command "TEXT" "J" "ML" p1   0.75  0.00 "LOST H2O, FRA")
 (command "LAYER" "S" "CGBMAIN" "")
 (setq p1 (list 107.00 1670.10) p2 (list 113.00 1670.10) p3 (list 113.00 1663.30) p4 (list 107.00 1663.30))
 (command "PLINE" p1 p2 p3 p4 "c")
 (command "HATCH" "ZIGZAG" 4.00 0.00 "L" "")
 (command "COLOR" "BYLAYER")
 (command "LAYER" "S" "CGBLITHCD" "")
 (setq p1 (list 113.00 1666.70) p2 (list 114.35 1666.70))
 (command "LINE" p1 p2 "")
 (setq p1 (list 114.50 1666.33) p2 (list 0.00 0.00))
 (command "TEXT" "J" "ML" p1   0.75  0.00 "554")
 (command "LAYER" "S" "CGBTHK" "")
 (setq p1 (list 119.00 1666.33) p2 (list 0.00 0.00))
 (command "TEXT" "J" "ML" p1   0.75  0.00 "6.80")
 (command "LAYER" "S" "CGBHZID" "")
 (setq p1 (list 123.50 1666.33) p2 (list 0.00 0.00))
 (command "TEXT" "J" "ML" p1   0.75  0.00 "")
 (setq p1 (list 125.75 1666.33) p2 (list 0.00 0.00))
 (command "TEXT" "J" "ML" p1   0.75  0.00 "7951")
 (command "LAYER" "S" "CGBLITHTXT" "")
 (setq p1 (list 129.50 1666.33) p2 (list 0.00 0.00))
 (command "TEXT" "J" "ML" p1   0.75  0.00 "XTLIZED MASS SS")
 (command "LAYER" "S" "CGBCMNT" "")
 (setq p1 (list 149.75 1666.33) p2 (list 0.00 0.00))
 (command "TEXT" "J" "ML" p1   0.75  0.00 "CRSN DWN, CR")
 (command "LAYER" "S" "CGBMAIN" "")
 (setq p1 (list 107.00 1663.30) p2 (list 113.00 1663.30) p3 (list 113.00 1662.00) p4 (list 107.00 1662.00))
 (command "PLINE" p1 p2 p3 p4 "c")
 (command "HATCH" "ZIGZAG" 4.00 0.00 "L" "")
 (command "COLOR" "BYLAYER")
 (command "LAYER" "S" "CGBLITHCD" "")
 (setq p1 (list 113.00 1662.65) p2 (list 114.35 1662.65))
 (command "LINE" p1 p2 "")
 (setq p1 (list 114.50 1662.28) p2 (list 0.00 0.00))
 (command "TEXT" "J" "ML" p1   0.75  0.00 "554")
 (command "LAYER" "S" "CGBTHK" "")
 (setq p1 (list 119.00 1662.28) p2 (list 0.00 0.00))
 (command "TEXT" "J" "ML" p1   0.75  0.00 "1.30")
 (command "LAYER" "S" "CGBHZID" "")
 (setq p1 (list 123.50 1662.28) p2 (list 0.00 0.00))
 (command "TEXT" "J" "ML" p1   0.75  0.00 "")
 (setq p1 (list 125.75 1662.28) p2 (list 0.00 0.00))
 (command "TEXT" "J" "ML" p1   0.75  0.00 "7951")
 (command "LAYER" "S" "CGBLITHTXT" "")
 (setq p1 (list 129.50 1662.28) p2 (list 0.00 0.00))
 (command "TEXT" "J" "ML" p1   0.75  0.00 "XTLIZED MASS SS")
 (command "LAYER" "S" "CGBCMNT" "")
 (setq p1 (list 149.75 1662.28) p2 (list 0.00 0.00))
 (command "TEXT" "J" "ML" p1   0.75  0.00 "SLC")
 (command "LAYER" "S" "CGBMAIN" "")
 (setq p1 (list 107.00 1662.00) p2 (list 113.00 1662.00) p3 (list 113.00 1659.40) p4 (list 107.00 1659.40))
 (command "PLINE" p1 p2 p3 p4 "c")
 (command "HATCH" "ZIGZAG" 4.00 0.00 "L" "")
 (command "COLOR" "BYLAYER")
 (command "LAYER" "S" "CGBLITHCD" "")
 (setq p1 (list 113.00 1660.70) p2 (list 114.35 1660.70))
 (command "LINE" p1 p2 "")
 (setq p1 (list 114.50 1660.33) p2 (list 0.00 0.00))
 (command "TEXT" "J" "ML" p1   0.75  0.00 "541")
 (command "LAYER" "S" "CGBTHK" "")
 (setq p1 (list 119.00 1660.33) p2 (list 0.00 0.00))
 (command "TEXT" "J" "ML" p1   0.75  0.00 "2.60")
 (command "LAYER" "S" "CGBHZID" "")
 (setq p1 (list 123.50 1660.33) p2 (list 0.00 0.00))
 (command "TEXT" "J" "ML" p1   0.75  0.00 "")
 (setq p1 (list 125.75 1660.33) p2 (list 0.00 0.00))
 (command "TEXT" "J" "ML" p1   0.75  0.00 "7951")
 (command "LAYER" "S" "CGBLITHTXT" "")
 (setq p1 (list 129.50 1660.33) p2 (list 0.00 0.00))
 (command "TEXT" "J" "ML" p1   0.75  0.00 "GRY CROSSBED SS")
 (command "LAYER" "S" "CGBCMNT" "")
 (setq p1 (list 149.75 1660.33) p2 (list 0.00 0.00))
 (command "TEXT" "J" "ML" p1   0.75  0.00 "F GR, SLC")
 (command "LAYER" "S" "CGBMAIN" "")
 (setq p1 (list 107.00 1659.40) p2 (list 113.00 1659.40) p3 (list 113.00 1654.80) p4 (list 107.00 1654.80))
 (command "PLINE" p1 p2 p3 p4 "c")
 (command "HATCH" "ZIGZAG" 0.25 0.00 "L" "")
 (command "COLOR" "BYLAYER")
 (command "LAYER" "S" "CGBLITHCD" "")
 (setq p1 (list 113.00 1657.10) p2 (list 114.35 1657.10))
 (command "LINE" p1 p2 "")
 (setq p1 (list 114.50 1656.73) p2 (list 0.00 0.00))
 (command "TEXT" "J" "ML" p1   0.75  0.00 "754")
 (command "LAYER" "S" "CGBTHK" "")
 (setq p1 (list 119.00 1656.73) p2 (list 0.00 0.00))
 (command "TEXT" "J" "ML" p1   0.75  0.00 "4.60")
 (command "LAYER" "S" "CGBHZID" "")
 (setq p1 (list 123.50 1656.73) p2 (list 0.00 0.00))
 (command "TEXT" "J" "ML" p1   0.75  0.00 "")
 (setq p1 (list 125.75 1656.73) p2 (list 0.00 0.00))
 (command "TEXT" "J" "ML" p1   0.75  0.00 "7951")
 (command "LAYER" "S" "CGBLITHTXT" "")
 (setq p1 (list 129.50 1656.73) p2 (list 0.00 0.00))
 (command "TEXT" "J" "ML" p1   0.75  0.00 "XTLIZED QTZ PEB CGL")
 (command "LAYER" "S" "CGBCMNT" "")
 (setq p1 (list 149.75 1656.73) p2 (list 0.00 0.00))
 (command "TEXT" "J" "ML" p1   0.75  0.00 "SLC")
 (command "LAYER" "S" "CGBMAIN" "")
 (setq p1 (list 107.00 1654.80) p2 (list 113.00 1654.80) p3 (list 113.00 1654.06) p4 (list 107.00 1654.06))
 (command "PLINE" p1 p2 p3 p4 "c")
 (command "HATCH" "ZIGZAG" 4.00 0.00 "L" "")
 (command "COLOR" "BYLAYER")
 (command "LAYER" "S" "CGBLITHCD" "")
 (setq p1 (list 113.00 1654.43) p2 (list 114.35 1654.43))
 (command "LINE" p1 p2 "")
 (setq p1 (list 114.50 1654.06) p2 (list 0.00 0.00))
 (command "TEXT" "J" "ML" p1   0.75  0.00 "344")
 (command "LAYER" "S" "CGBTHK" "")
 (setq p1 (list 119.00 1654.06) p2 (list 0.00 0.00))
 (command "TEXT" "J" "ML" p1   0.75  0.00 "0.74")
 (command "LAYER" "S" "CGBHZID" "")
 (setq p1 (list 123.50 1654.06) p2 (list 0.00 0.00))
 (command "TEXT" "J" "ML" p1   0.75  0.00 "")
 (setq p1 (list 125.75 1654.06) p2 (list 0.00 0.00))
 (command "TEXT" "J" "ML" p1   0.75  0.00 "7951")
 (command "LAYER" "S" "CGBLITHTXT" "")
 (setq p1 (list 129.50 1654.06) p2 (list 0.00 0.00))
 (command "TEXT" "J" "ML" p1   0.75  0.00 "GRN MASS SDY SH")
 (command "LAYER" "S" "CGBCMNT" "")
 (setq p1 (list 149.75 1654.06) p2 (list 0.00 0.00))
 (command "TEXT" "J" "ML" p1   0.75  0.00 "SLC")
 (command "LAYER" "S" "CGBMAIN" "")
 (setq p1 (list 107.00 1654.06) p2 (list 113.00 1654.06) p3 (list 113.00 1653.26) p4 (list 107.00 1653.26))
 (command "PLINE" p1 p2 p3 p4 "c")
 (command "HATCH" "ZIGZAG" 5.00 0.00 "L" "")
 (command "COLOR" "BYLAYER")
 (command "LAYER" "S" "CGBLITHCD" "")
 (setq p1 (list 113.00 1653.66) p2 (list 114.35 1652.41))
 (command "LINE" p1 p2 "")
 (setq p1 (list 114.50 1652.04) p2 (list 0.00 0.00))
 (command "TEXT" "J" "ML" p1   0.75  0.00 "906")
 (command "LAYER" "S" "CGBTHK" "")
 (setq p1 (list 119.00 1652.04) p2 (list 0.00 0.00))
 (command "TEXT" "J" "ML" p1   0.75  0.00 "0.80")
 (command "LAYER" "S" "CGBHZID" "")
 (setq p1 (list 123.50 1652.04) p2 (list 0.00 0.00))
 (command "TEXT" "J" "ML" p1   0.75  0.00 "")
 (setq p1 (list 125.75 1652.04) p2 (list 0.00 0.00))
 (command "TEXT" "J" "ML" p1   0.75  0.00 "7951")
 (command "LAYER" "S" "CGBLITHTXT" "")
 (setq p1 (list 129.50 1652.04) p2 (list 0.00 0.00))
 (command "TEXT" "J" "ML" p1   0.75  0.00 "NODULAR FN GRND LS")
 (command "LAYER" "S" "CGBCMNT" "")
 (setq p1 (list 149.75 1652.04) p2 (list 0.00 0.00))
 (command "TEXT" "J" "ML" p1   0.75  0.00 "GB")
 (command "LAYER" "S" "CGBMAIN" "")
 (setq p1 (list 107.00 1653.26) p2 (list 113.00 1653.26) p3 (list 113.00 1643.45) p4 (list 107.00 1643.45))
 (command "PLINE" p1 p2 p3 p4 "c")
 (command "HATCH" "ZIGZAG" 5.00 0.00 "L" "")
 (command "COLOR" "BYLAYER")
 (command "LAYER" "S" "CGBLITHCD" "")
 (setq p1 (list 113.00 1648.36) p2 (list 114.35 1648.36))
 (command "LINE" p1 p2 "")
 (setq p1 (list 114.50 1647.98) p2 (list 0.00 0.00))
 (command "TEXT" "J" "ML" p1   0.75  0.00 "322")
 (command "LAYER" "S" "CGBTHK" "")
 (setq p1 (list 119.00 1647.98) p2 (list 0.00 0.00))
 (command "TEXT" "J" "ML" p1   0.75  0.00 "9.81")
 (command "LAYER" "S" "CGBHZID" "")
 (setq p1 (list 123.50 1647.98) p2 (list 0.00 0.00))
 (command "TEXT" "J" "ML" p1   0.75  0.00 "")
 (setq p1 (list 125.75 1647.98) p2 (list 0.00 0.00))
 (command "TEXT" "J" "ML" p1   0.75  0.00 "7951")
 (command "LAYER" "S" "CGBLITHTXT" "")
 (setq p1 (list 129.50 1647.98) p2 (list 0.00 0.00))
 (command "TEXT" "J" "ML" p1   0.75  0.00 "DRK GRY SH+INTERBED SS")
 (command "LAYER" "S" "CGBCMNT" "")
 (setq p1 (list 149.75 1647.98) p2 (list 0.00 0.00))
 (command "TEXT" "J" "ML" p1   0.75  0.00 "FNS DWN")
 (command "LAYER" "S" "CGBMAIN" "")
 (setq p1 (list 107.00 1643.45) p2 (list 113.00 1643.45) p3 (list 113.00 1641.59) p4 (list 107.00 1641.59))
 (command "PLINE" p1 p2 p3 p4 "c")
 (command "HATCH" "ZIGZAG" 5.00 0.00 "L" "")
 (command "COLOR" "BYLAYER")
 (command "LAYER" "S" "CGBLITHCD" "")
 (setq p1 (list 113.00 1642.52) p2 (list 114.35 1642.52))
 (command "LINE" p1 p2 "")
 (setq p1 (list 114.50 1642.15) p2 (list 0.00 0.00))
 (command "TEXT" "J" "ML" p1   0.75  0.00 "322")
 (command "LAYER" "S" "CGBTHK" "")
 (setq p1 (list 119.00 1642.15) p2 (list 0.00 0.00))
 (command "TEXT" "J" "ML" p1   0.75  0.00 "1.86")
 (command "LAYER" "S" "CGBHZID" "")
 (setq p1 (list 123.50 1642.15) p2 (list 0.00 0.00))
 (command "TEXT" "J" "ML" p1   0.75  0.00 "")
 (setq p1 (list 125.75 1642.15) p2 (list 0.00 0.00))
 (command "TEXT" "J" "ML" p1   0.75  0.00 "7951")
 (command "LAYER" "S" "CGBLITHTXT" "")
 (setq p1 (list 129.50 1642.15) p2 (list 0.00 0.00))
 (command "TEXT" "J" "ML" p1   0.75  0.00 "DRK GRY SH+INTERBED SS")
 (command "LAYER" "S" "CGBCMNT" "")
 (setq p1 (list 149.75 1642.15) p2 (list 0.00 0.00))
 (command "TEXT" "J" "ML" p1   0.75  0.00 "FNS DWN, GB")
 (command "LAYER" "S" "CGBMAIN" "")
 (setq p1 (list 107.00 1641.59) p2 (list 113.00 1641.59) p3 (list 113.00 1635.72) p4 (list 107.00 1635.72))
 (command "PLINE" p1 p2 p3 p4 "c")
 (command "HATCH" "ZIGZAG" 4.00 0.00 "L" "")
 (command "COLOR" "BYLAYER")
 (command "LAYER" "S" "CGBLITHCD" "")
 (setq p1 (list 113.00 1638.66) p2 (list 114.35 1638.66))
 (command "LINE" p1 p2 "")
 (setq p1 (list 114.50 1638.28) p2 (list 0.00 0.00))
 (command "TEXT" "J" "ML" p1   0.75  0.00 "124")
 (command "LAYER" "S" "CGBTHK" "")
 (setq p1 (list 119.00 1638.28) p2 (list 0.00 0.00))
 (command "TEXT" "J" "ML" p1   0.75  0.00 "5.87")
 (command "LAYER" "S" "CGBHZID" "")
 (setq p1 (list 123.50 1638.28) p2 (list 0.00 0.00))
 (command "TEXT" "J" "ML" p1   0.75  0.00 "")
 (setq p1 (list 125.75 1638.28) p2 (list 0.00 0.00))
 (command "TEXT" "J" "ML" p1   0.75  0.00 "7951")
 (command "LAYER" "S" "CGBLITHTXT" "")
 (setq p1 (list 129.50 1638.28) p2 (list 0.00 0.00))
 (command "TEXT" "J" "ML" p1   0.75  0.00 "DRK GRY SH")
 (command "LAYER" "S" "CGBCMNT" "")
 (setq p1 (list 149.75 1638.28) p2 (list 0.00 0.00))
 (command "TEXT" "J" "ML" p1   0.75  0.00 "FE STN, DRK @")
 (command "LAYER" "S" "CGBMAIN" "")
 (setq p1 (list 107.00 1635.72) p2 (list 113.00 1635.72) p3 (list 113.00 1635.08) p4 (list 107.00 1635.08))
 (command "PLINE" p1 p2 p3 p4 "c")
 (command "HATCH" "ZIGZAG" 0.80 0.00 "L" "")
 (command "COLOR" "BYLAYER")
 (command "LAYER" "S" "CGBLITHCD" "")
 (setq p1 (list 113.00 1635.40) p2 (list 114.35 1635.40))
 (command "LINE" p1 p2 "")
 (setq p1 (list 114.50 1635.03) p2 (list 0.00 0.00))
 (command "TEXT" "J" "ML" p1   0.75  0.00 "029")
 (command "LAYER" "S" "CGBTHK" "")
 (setq p1 (list 119.00 1635.03) p2 (list 0.00 0.00))
 (command "TEXT" "J" "ML" p1   0.75  0.00 "0.64")
 (command "LAYER" "S" "CGBHZID" "")
 (setq p1 (list 123.50 1635.03) p2 (list 0.00 0.00))
 (command "TEXT" "J" "ML" p1   0.75  0.00 "")
 (setq p1 (list 125.75 1635.03) p2 (list 0.00 0.00))
 (command "TEXT" "J" "ML" p1   0.75  0.00 "7500")
 (command "LAYER" "S" "CGBLITHTXT" "")
 (setq p1 (list 129.50 1635.03) p2 (list 0.00 0.00))
 (command "TEXT" "J" "ML" p1   0.75  0.00 "COAL W/PYRITE STKS")
 (command "LAYER" "S" "CGBCMNT" "")
 (setq p1 (list 149.75 1635.03) p2 (list 0.00 0.00))
 (command "TEXT" "J" "ML" p1   0.75  0.00 "DULL W/VIT &")
 (command "LAYER" "S" "CGBMAIN" "")
 (setq p1 (list 107.00 1635.08) p2 (list 113.00 1635.08) p3 (list 113.00 1633.77) p4 (list 107.00 1633.77))
 (command "PLINE" p1 p2 p3 p4 "c")
 (command "HATCH" "ZIGZAG" 0.25 0.00 "L" "")
 (command "COLOR" "BYLAYER")
 (command "LAYER" "S" "CGBLITHCD" "")
 (setq p1 (list 113.00 1634.43) p2 (list 114.35 1633.18))
 (command "LINE" p1 p2 "")
 (setq p1 (list 114.50 1632.80) p2 (list 0.00 0.00))
 (command "TEXT" "J" "ML" p1   0.75  0.00 "127")
 (command "LAYER" "S" "CGBTHK" "")
 (setq p1 (list 119.00 1632.80) p2 (list 0.00 0.00))
 (command "TEXT" "J" "ML" p1   0.75  0.00 "1.31")
 (command "LAYER" "S" "CGBHZID" "")
 (setq p1 (list 123.50 1632.80) p2 (list 0.00 0.00))
 (command "TEXT" "J" "ML" p1   0.75  0.00 "")
 (setq p1 (list 125.75 1632.80) p2 (list 0.00 0.00))
 (command "TEXT" "J" "ML" p1   0.75  0.00 "7451")
 (command "LAYER" "S" "CGBLITHTXT" "")
 (setq p1 (list 129.50 1632.80) p2 (list 0.00 0.00))
 (command "TEXT" "J" "ML" p1   0.75  0.00 "DRK GRY FIRECLAY")
 (command "LAYER" "S" "CGBCMNT" "")
 (setq p1 (list 149.75 1632.80) p2 (list 0.00 0.00))
 (command "TEXT" "J" "ML" p1   0.75  0.00 "")
 (command "LAYER" "S" "CGBMAIN" "")
 (setq p1 (list 107.00 1633.77) p2 (list 113.00 1633.77) p3 (list 113.00 1627.32) p4 (list 107.00 1627.32))
 (command "PLINE" p1 p2 p3 p4 "c")
 (command "HATCH" "ZIGZAG" 5.00 0.00 "L" "")
 (command "COLOR" "BYLAYER")
 (command "LAYER" "S" "CGBLITHCD" "")
 (setq p1 (list 113.00 1630.55) p2 (list 114.35 1630.55))
 (command "LINE" p1 p2 "")
 (setq p1 (list 114.50 1630.17) p2 (list 0.00 0.00))
 (command "TEXT" "J" "ML" p1   0.75  0.00 "322")
 (command "LAYER" "S" "CGBTHK" "")
 (setq p1 (list 119.00 1630.17) p2 (list 0.00 0.00))
 (command "TEXT" "J" "ML" p1   0.75  0.00 "6.45")
 (command "LAYER" "S" "CGBHZID" "")
 (setq p1 (list 123.50 1630.17) p2 (list 0.00 0.00))
 (command "TEXT" "J" "ML" p1   0.75  0.00 "")
 (setq p1 (list 125.75 1630.17) p2 (list 0.00 0.00))
 (command "TEXT" "J" "ML" p1   0.75  0.00 "7451")
 (command "LAYER" "S" "CGBLITHTXT" "")
 (setq p1 (list 129.50 1630.17) p2 (list 0.00 0.00))
 (command "TEXT" "J" "ML" p1   0.75  0.00 "DRK GRY SH+INTERBED SS")
 (command "LAYER" "S" "CGBCMNT" "")
 (setq p1 (list 149.75 1630.17) p2 (list 0.00 0.00))
 (command "TEXT" "J" "ML" p1   0.75  0.00 "CALC LAYRS")
 (command "LAYER" "S" "CGBMAIN" "")
 (setq p1 (list 107.00 1627.32) p2 (list 113.00 1627.32) p3 (list 113.00 1627.03) p4 (list 107.00 1627.03))
 (command "PLINE" p1 p2 p3 p4 "c")
 (command "HATCH" "ZIGZAG" 4.00 0.00 "L" "")
 (command "COLOR" "BYLAYER")
 (command "LAYER" "S" "CGBLITHCD" "")
 (setq p1 (list 113.00 1627.18) p2 (list 114.35 1627.18))
 (command "LINE" p1 p2 "")
 (setq p1 (list 114.50 1626.80) p2 (list 0.00 0.00))
 (command "TEXT" "J" "ML" p1   0.75  0.00 "510")
 (command "LAYER" "S" "CGBTHK" "")
 (setq p1 (list 119.00 1626.80) p2 (list 0.00 0.00))
 (command "TEXT" "J" "ML" p1   0.75  0.00 "0.29")
 (command "LAYER" "S" "CGBHZID" "")
 (setq p1 (list 123.50 1626.80) p2 (list 0.00 0.00))
 (command "TEXT" "J" "ML" p1   0.75  0.00 "")
 (setq p1 (list 125.75 1626.80) p2 (list 0.00 0.00))
 (command "TEXT" "J" "ML" p1   0.75  0.00 "7451")
 (command "LAYER" "S" "CGBLITHTXT" "")
 (setq p1 (list 129.50 1626.80) p2 (list 0.00 0.00))
 (command "TEXT" "J" "ML" p1   0.75  0.00 "LIME SS")
 (command "LAYER" "S" "CGBCMNT" "")
 (setq p1 (list 149.75 1626.80) p2 (list 0.00 0.00))
 (command "TEXT" "J" "ML" p1   0.75  0.00 "")
 (command "LAYER" "S" "CGBMAIN" "")
 (setq p1 (list 107.00 1627.03) p2 (list 113.00 1627.03) p3 (list 113.00 1623.55) p4 (list 107.00 1623.55))
 (command "PLINE" p1 p2 p3 p4 "c")
 (command "HATCH" "ZIGZAG" 5.00 0.00 "L" "")
 (command "COLOR" "BYLAYER")
 (command "LAYER" "S" "CGBLITHCD" "")
 (setq p1 (list 113.00 1625.29) p2 (list 114.35 1625.29))
 (command "LINE" p1 p2 "")
 (setq p1 (list 114.50 1624.92) p2 (list 0.00 0.00))
 (command "TEXT" "J" "ML" p1   0.75  0.00 "322")
 (command "LAYER" "S" "CGBTHK" "")
 (setq p1 (list 119.00 1624.92) p2 (list 0.00 0.00))
 (command "TEXT" "J" "ML" p1   0.75  0.00 "3.48")
 (command "LAYER" "S" "CGBHZID" "")
 (setq p1 (list 123.50 1624.92) p2 (list 0.00 0.00))
 (command "TEXT" "J" "ML" p1   0.75  0.00 "")
 (setq p1 (list 125.75 1624.92) p2 (list 0.00 0.00))
 (command "TEXT" "J" "ML" p1   0.75  0.00 "7451")
 (command "LAYER" "S" "CGBLITHTXT" "")
 (setq p1 (list 129.50 1624.92) p2 (list 0.00 0.00))
 (command "TEXT" "J" "ML" p1   0.75  0.00 "DRK GRY SH+INTERBED SS")
 (command "LAYER" "S" "CGBCMNT" "")
 (setq p1 (list 149.75 1624.92) p2 (list 0.00 0.00))
 (command "TEXT" "J" "ML" p1   0.75  0.00 "CALC")
 (command "LAYER" "S" "CGBMAIN" "")
 (setq p1 (list 107.00 1623.55) p2 (list 113.00 1623.55) p3 (list 113.00 1621.22) p4 (list 107.00 1621.22))
 (command "PLINE" p1 p2 p3 p4 "c")
 (command "HATCH" "ZIGZAG" 5.00 0.00 "L" "")
 (command "COLOR" "BYLAYER")
 (command "LAYER" "S" "CGBLITHCD" "")
 (setq p1 (list 113.00 1622.39) p2 (list 114.35 1622.39))
 (command "LINE" p1 p2 "")
 (setq p1 (list 114.50 1622.01) p2 (list 0.00 0.00))
 (command "TEXT" "J" "ML" p1   0.75  0.00 "224")
 (command "LAYER" "S" "CGBTHK" "")
 (setq p1 (list 119.00 1622.01) p2 (list 0.00 0.00))
 (command "TEXT" "J" "ML" p1   0.75  0.00 "2.33")
 (command "LAYER" "S" "CGBHZID" "")
 (setq p1 (list 123.50 1622.01) p2 (list 0.00 0.00))
 (command "TEXT" "J" "ML" p1   0.75  0.00 "")
 (setq p1 (list 125.75 1622.01) p2 (list 0.00 0.00))
 (command "TEXT" "J" "ML" p1   0.75  0.00 "7451")
 (command "LAYER" "S" "CGBLITHTXT" "")
 (setq p1 (list 129.50 1622.01) p2 (list 0.00 0.00))
 (command "TEXT" "J" "ML" p1   0.75  0.00 "DRK GRY SH W/LS NODS")
 (command "LAYER" "S" "CGBCMNT" "")
 (setq p1 (list 149.75 1622.01) p2 (list 0.00 0.00))
 (command "TEXT" "J" "ML" p1   0.75  0.00 "")
 (command "LAYER" "S" "CGBMAIN" "")
 (setq p1 (list 107.00 1621.22) p2 (list 113.00 1621.22) p3 (list 113.00 1619.28) p4 (list 107.00 1619.28))
 (command "PLINE" p1 p2 p3 p4 "c")
 (command "HATCH" "ZIGZAG" 4.00 0.00 "L" "")
 (command "COLOR" "BYLAYER")
 (command "LAYER" "S" "CGBLITHCD" "")
 (setq p1 (list 113.00 1620.25) p2 (list 114.35 1620.25))
 (command "LINE" p1 p2 "")
 (setq p1 (list 114.50 1619.88) p2 (list 0.00 0.00))
 (command "TEXT" "J" "ML" p1   0.75  0.00 "125")
 (command "LAYER" "S" "CGBTHK" "")
 (setq p1 (list 119.00 1619.88) p2 (list 0.00 0.00))
 (command "TEXT" "J" "ML" p1   0.75  0.00 "1.94")
 (command "LAYER" "S" "CGBHZID" "")
 (setq p1 (list 123.50 1619.88) p2 (list 0.00 0.00))
 (command "TEXT" "J" "ML" p1   0.75  0.00 "")
 (setq p1 (list 125.75 1619.88) p2 (list 0.00 0.00))
 (command "TEXT" "J" "ML" p1   0.75  0.00 "7451")
 (command "LAYER" "S" "CGBLITHTXT" "")
 (setq p1 (list 129.50 1619.88) p2 (list 0.00 0.00))
 (command "TEXT" "J" "ML" p1   0.75  0.00 "DRK GRY CHRND SH")
 (command "LAYER" "S" "CGBCMNT" "")
 (setq p1 (list 149.75 1619.88) p2 (list 0.00 0.00))
 (command "TEXT" "J" "ML" p1   0.75  0.00 "FRAC, GB")
 (command "LAYER" "S" "CGBMAIN" "")
 (setq p1 (list 107.00 1619.28) p2 (list 113.00 1619.28) p3 (list 113.00 1617.65) p4 (list 107.00 1617.65))
 (command "PLINE" p1 p2 p3 p4 "c")
 (command "HATCH" "ZIGZAG" 5.00 0.00 "L" "")
 (command "COLOR" "BYLAYER")
 (command "LAYER" "S" "CGBLITHCD" "")
 (setq p1 (list 113.00 1618.47) p2 (list 114.35 1618.47))
 (command "LINE" p1 p2 "")
 (setq p1 (list 114.50 1618.09) p2 (list 0.00 0.00))
 (command "TEXT" "J" "ML" p1   0.75  0.00 "322")
 (command "LAYER" "S" "CGBTHK" "")
 (setq p1 (list 119.00 1618.09) p2 (list 0.00 0.00))
 (command "TEXT" "J" "ML" p1   0.75  0.00 "1.63")
 (command "LAYER" "S" "CGBHZID" "")
 (setq p1 (list 123.50 1618.09) p2 (list 0.00 0.00))
 (command "TEXT" "J" "ML" p1   0.75  0.00 "")
 (setq p1 (list 125.75 1618.09) p2 (list 0.00 0.00))
 (command "TEXT" "J" "ML" p1   0.75  0.00 "7451")
 (command "LAYER" "S" "CGBLITHTXT" "")
 (setq p1 (list 129.50 1618.09) p2 (list 0.00 0.00))
 (command "TEXT" "J" "ML" p1   0.75  0.00 "DRK GRY SH+INTERBED SS")
 (command "LAYER" "S" "CGBCMNT" "")
 (setq p1 (list 149.75 1618.09) p2 (list 0.00 0.00))
 (command "TEXT" "J" "ML" p1   0.75  0.00 "LMY")
 (command "LAYER" "S" "CGBMAIN" "")
 (setq p1 (list 107.00 1617.65) p2 (list 113.00 1617.65) p3 (list 113.00 1609.72) p4 (list 107.00 1609.72))
 (command "PLINE" p1 p2 p3 p4 "c")
 (command "HATCH" "ZIGZAG" 5.00 0.00 "L" "")
 (command "COLOR" "BYLAYER")
 (command "LAYER" "S" "CGBLITHCD" "")
 (setq p1 (list 113.00 1613.69) p2 (list 114.35 1613.69))
 (command "LINE" p1 p2 "")
 (setq p1 (list 114.50 1613.31) p2 (list 0.00 0.00))
 (command "TEXT" "J" "ML" p1   0.75  0.00 "224")
 (command "LAYER" "S" "CGBTHK" "")
 (setq p1 (list 119.00 1613.31) p2 (list 0.00 0.00))
 (command "TEXT" "J" "ML" p1   0.75  0.00 "7.93")
 (command "LAYER" "S" "CGBHZID" "")
 (setq p1 (list 123.50 1613.31) p2 (list 0.00 0.00))
 (command "TEXT" "J" "ML" p1   0.75  0.00 "")
 (setq p1 (list 125.75 1613.31) p2 (list 0.00 0.00))
 (command "TEXT" "J" "ML" p1   0.75  0.00 "7451")
 (command "LAYER" "S" "CGBLITHTXT" "")
 (setq p1 (list 129.50 1613.31) p2 (list 0.00 0.00))
 (command "TEXT" "J" "ML" p1   0.75  0.00 "DRK GRY SH W/LS NODS")
 (command "LAYER" "S" "CGBCMNT" "")
 (setq p1 (list 149.75 1613.31) p2 (list 0.00 0.00))
 (command "TEXT" "J" "ML" p1   0.75  0.00 "BRKN IN SFT Z")
 (command "LAYER" "S" "CGBMAIN" "")
 (setq p1 (list 107.00 1609.72) p2 (list 113.00 1609.72) p3 (list 113.00 1607.03) p4 (list 107.00 1607.03))
 (command "PLINE" p1 p2 p3 p4 "c")
 (command "HATCH" "ZIGZAG" 0.25 0.00 "L" "")
 (command "COLOR" "BYLAYER")
 (command "LAYER" "S" "CGBLITHCD" "")
 (setq p1 (list 113.00 1608.38) p2 (list 114.35 1608.38))
 (command "LINE" p1 p2 "")
 (setq p1 (list 114.50 1608.00) p2 (list 0.00 0.00))
 (command "TEXT" "J" "ML" p1   0.75  0.00 "127")
 (command "LAYER" "S" "CGBTHK" "")
 (setq p1 (list 119.00 1608.00) p2 (list 0.00 0.00))
 (command "TEXT" "J" "ML" p1   0.75  0.00 "2.69")
 (command "LAYER" "S" "CGBHZID" "")
 (setq p1 (list 123.50 1608.00) p2 (list 0.00 0.00))
 (command "TEXT" "J" "ML" p1   0.75  0.00 "")
 (setq p1 (list 125.75 1608.00) p2 (list 0.00 0.00))
 (command "TEXT" "J" "ML" p1   0.75  0.00 "7451")
 (command "LAYER" "S" "CGBLITHTXT" "")
 (setq p1 (list 129.50 1608.00) p2 (list 0.00 0.00))
 (command "TEXT" "J" "ML" p1   0.75  0.00 "DRK GRY FIRECLAY")
 (command "LAYER" "S" "CGBCMNT" "")
 (setq p1 (list 149.75 1608.00) p2 (list 0.00 0.00))
 (command "TEXT" "J" "ML" p1   0.75  0.00 "BRKN W/ SLX")
 (command "LAYER" "S" "CGBMAIN" "")
 (setq p1 (list 107.00 1607.03) p2 (list 113.00 1607.03) p3 (list 113.00 1606.31) p4 (list 107.00 1606.31))
 (command "PLINE" p1 p2 p3 p4 "c")
 (command "HATCH" "ZIGZAG" 5.00 0.00 "L" "")
 (command "COLOR" "BYLAYER")
 (command "LAYER" "S" "CGBLITHCD" "")
 (setq p1 (list 113.00 1606.67) p2 (list 114.35 1606.67))
 (command "LINE" p1 p2 "")
 (setq p1 (list 114.50 1606.30) p2 (list 0.00 0.00))
 (command "TEXT" "J" "ML" p1   0.75  0.00 "224")
 (command "LAYER" "S" "CGBTHK" "")
 (setq p1 (list 119.00 1606.30) p2 (list 0.00 0.00))
 (command "TEXT" "J" "ML" p1   0.75  0.00 "0.72")
 (command "LAYER" "S" "CGBHZID" "")
 (setq p1 (list 123.50 1606.30) p2 (list 0.00 0.00))
 (command "TEXT" "J" "ML" p1   0.75  0.00 "")
 (setq p1 (list 125.75 1606.30) p2 (list 0.00 0.00))
 (command "TEXT" "J" "ML" p1   0.75  0.00 "7451")
 (command "LAYER" "S" "CGBLITHTXT" "")
 (setq p1 (list 129.50 1606.30) p2 (list 0.00 0.00))
 (command "TEXT" "J" "ML" p1   0.75  0.00 "DRK GRY SH W/LS NODS")
 (command "LAYER" "S" "CGBCMNT" "")
 (setq p1 (list 149.75 1606.30) p2 (list 0.00 0.00))
 (command "TEXT" "J" "ML" p1   0.75  0.00 "VEINS & NODS")
 (command "LAYER" "S" "CGBMAIN" "")
 (setq p1 (list 107.00 1606.31) p2 (list 113.00 1606.31) p3 (list 113.00 1605.05) p4 (list 107.00 1605.05))
 (command "PLINE" p1 p2 p3 p4 "c")
 (command "HATCH" "ZIGZAG" 5.00 0.00 "L" "")
 (command "COLOR" "BYLAYER")
 (command "LAYER" "S" "CGBLITHCD" "")
 (setq p1 (list 113.00 1605.68) p2 (list 114.35 1604.43))
 (command "LINE" p1 p2 "")
 (setq p1 (list 114.50 1604.06) p2 (list 0.00 0.00))
 (command "TEXT" "J" "ML" p1   0.75  0.00 "224")
 (command "LAYER" "S" "CGBTHK" "")
 (setq p1 (list 119.00 1604.06) p2 (list 0.00 0.00))
 (command "TEXT" "J" "ML" p1   0.75  0.00 "1.26")
 (command "LAYER" "S" "CGBHZID" "")
 (setq p1 (list 123.50 1604.06) p2 (list 0.00 0.00))
 (command "TEXT" "J" "ML" p1   0.75  0.00 "")
 (setq p1 (list 125.75 1604.06) p2 (list 0.00 0.00))
 (command "TEXT" "J" "ML" p1   0.75  0.00 "7451")
 (command "LAYER" "S" "CGBLITHTXT" "")
 (setq p1 (list 129.50 1604.06) p2 (list 0.00 0.00))
 (command "TEXT" "J" "ML" p1   0.75  0.00 "DRK GRY SH W/LS NODS")
 (command "LAYER" "S" "CGBCMNT" "")
 (setq p1 (list 149.75 1604.06) p2 (list 0.00 0.00))
 (command "TEXT" "J" "ML" p1   0.75  0.00 "V SFT, MTTLD")
 (command "LAYER" "S" "CGBMAIN" "")
 (setq p1 (list 107.00 1605.05) p2 (list 113.00 1605.05) p3 (list 113.00 1600.30) p4 (list 107.00 1600.30))
 (command "PLINE" p1 p2 p3 p4 "c")
 (command "HATCH" "ZIGZAG" 5.00 0.00 "L" "")
 (command "COLOR" "BYLAYER")
 (command "LAYER" "S" "CGBLITHCD" "")
 (setq p1 (list 113.00 1602.68) p2 (list 114.35 1602.68))
 (command "LINE" p1 p2 "")
 (setq p1 (list 114.50 1602.30) p2 (list 0.00 0.00))
 (command "TEXT" "J" "ML" p1   0.75  0.00 "224")
 (command "LAYER" "S" "CGBTHK" "")
 (setq p1 (list 119.00 1602.30) p2 (list 0.00 0.00))
 (command "TEXT" "J" "ML" p1   0.75  0.00 "4.75")
 (command "LAYER" "S" "CGBHZID" "")
 (setq p1 (list 123.50 1602.30) p2 (list 0.00 0.00))
 (command "TEXT" "J" "ML" p1   0.75  0.00 "")
 (setq p1 (list 125.75 1602.30) p2 (list 0.00 0.00))
 (command "TEXT" "J" "ML" p1   0.75  0.00 "7451")
 (command "LAYER" "S" "CGBLITHTXT" "")
 (setq p1 (list 129.50 1602.30) p2 (list 0.00 0.00))
 (command "TEXT" "J" "ML" p1   0.75  0.00 "DRK GRY SH W/LS NODS")
 (command "LAYER" "S" "CGBCMNT" "")
 (setq p1 (list 149.75 1602.30) p2 (list 0.00 0.00))
 (command "TEXT" "J" "ML" p1   0.75  0.00 "AS ABOVE")
 (command "LAYER" "S" "CGBMAIN" "")
 (setq p1 (list 107.00 1600.30) p2 (list 113.00 1600.30) p3 (list 113.00 1598.85) p4 (list 107.00 1598.85))
 (command "PLINE" p1 p2 p3 p4 "c")
 (command "HATCH" "ZIGZAG" 5.00 0.00 "L" "")
 (command "COLOR" "BYLAYER")
 (command "LAYER" "S" "CGBLITHCD" "")
 (setq p1 (list 113.00 1599.58) p2 (list 114.35 1599.58))
 (command "LINE" p1 p2 "")
 (setq p1 (list 114.50 1599.20) p2 (list 0.00 0.00))
 (command "TEXT" "J" "ML" p1   0.75  0.00 "254")
 (command "LAYER" "S" "CGBTHK" "")
 (setq p1 (list 119.00 1599.20) p2 (list 0.00 0.00))
 (command "TEXT" "J" "ML" p1   0.75  0.00 "1.45")
 (command "LAYER" "S" "CGBHZID" "")
 (setq p1 (list 123.50 1599.20) p2 (list 0.00 0.00))
 (command "TEXT" "J" "ML" p1   0.75  0.00 "")
 (setq p1 (list 125.75 1599.20) p2 (list 0.00 0.00))
 (command "TEXT" "J" "ML" p1   0.75  0.00 "7451")
 (command "LAYER" "S" "CGBLITHTXT" "")
 (setq p1 (list 129.50 1599.20) p2 (list 0.00 0.00))
 (command "TEXT" "J" "ML" p1   0.75  0.00 "RED+GRN SH W/LS NODS")
 (command "LAYER" "S" "CGBCMNT" "")
 (setq p1 (list 149.75 1599.20) p2 (list 0.00 0.00))
 (command "TEXT" "J" "ML" p1   0.75  0.00 "BRKN W/ SLX")
 (command "LAYER" "S" "CGBMAIN" "")
 (setq p1 (list 107.00 1598.85) p2 (list 113.00 1598.85) p3 (list 113.00 1595.81) p4 (list 107.00 1595.81))
 (command "PLINE" p1 p2 p3 p4 "c")
 (command "HATCH" "ZIGZAG" 3.00 0.00 "L" "")
 (command "COLOR" "BYLAYER")
 (command "LAYER" "S" "CGBLITHCD" "")
 (setq p1 (list 113.00 1597.33) p2 (list 114.35 1597.33))
 (command "LINE" p1 p2 "")
 (setq p1 (list 114.50 1596.96) p2 (list 0.00 0.00))
 (command "TEXT" "J" "ML" p1   0.75  0.00 "157")
 (command "LAYER" "S" "CGBTHK" "")
 (setq p1 (list 119.00 1596.96) p2 (list 0.00 0.00))
 (command "TEXT" "J" "ML" p1   0.75  0.00 "3.04")
 (command "LAYER" "S" "CGBHZID" "")
 (setq p1 (list 123.50 1596.96) p2 (list 0.00 0.00))
 (command "TEXT" "J" "ML" p1   0.75  0.00 "")
 (setq p1 (list 125.75 1596.96) p2 (list 0.00 0.00))
 (command "TEXT" "J" "ML" p1   0.75  0.00 "7451")
 (command "LAYER" "S" "CGBLITHTXT" "")
 (setq p1 (list 129.50 1596.96) p2 (list 0.00 0.00))
 (command "TEXT" "J" "ML" p1   0.75  0.00 "RED+GRN CLYSTN")
 (command "LAYER" "S" "CGBCMNT" "")
 (setq p1 (list 149.75 1596.96) p2 (list 0.00 0.00))
 (command "TEXT" "J" "ML" p1   0.75  0.00 "SLX")
 (command "LAYER" "S" "CGBMAIN" "")
 (setq p1 (list 107.00 1595.81) p2 (list 113.00 1595.81) p3 (list 113.00 1593.05) p4 (list 107.00 1593.05))
 (command "PLINE" p1 p2 p3 p4 "c")
 (command "HATCH" "ZIGZAG" 5.00 0.00 "L" "")
 (command "COLOR" "BYLAYER")
 (command "LAYER" "S" "CGBLITHCD" "")
 (setq p1 (list 113.00 1594.43) p2 (list 114.35 1594.43))
 (command "LINE" p1 p2 "")
 (setq p1 (list 114.50 1594.06) p2 (list 0.00 0.00))
 (command "TEXT" "J" "ML" p1   0.75  0.00 "244")
 (command "LAYER" "S" "CGBTHK" "")
 (setq p1 (list 119.00 1594.06) p2 (list 0.00 0.00))
 (command "TEXT" "J" "ML" p1   0.75  0.00 "2.76")
 (command "LAYER" "S" "CGBHZID" "")
 (setq p1 (list 123.50 1594.06) p2 (list 0.00 0.00))
 (command "TEXT" "J" "ML" p1   0.75  0.00 "")
 (setq p1 (list 125.75 1594.06) p2 (list 0.00 0.00))
 (command "TEXT" "J" "ML" p1   0.75  0.00 "7451")
 (command "LAYER" "S" "CGBLITHTXT" "")
 (setq p1 (list 129.50 1594.06) p2 (list 0.00 0.00))
 (command "TEXT" "J" "ML" p1   0.75  0.00 "GRN SH W/LS NODS")
 (command "LAYER" "S" "CGBCMNT" "")
 (setq p1 (list 149.75 1594.06) p2 (list 0.00 0.00))
 (command "TEXT" "J" "ML" p1   0.75  0.00 "")
 (command "LAYER" "S" "CGBMAIN" "")
 (setq p1 (list 107.00 1593.05) p2 (list 113.00 1593.05) p3 (list 113.00 1591.45) p4 (list 107.00 1591.45))
 (command "PLINE" p1 p2 p3 p4 "c")
 (command "HATCH" "ZIGZAG" 10.00 45.00 "L" "")
 (command "COLOR" "BYLAYER")
 (command "LAYER" "S" "CGBLITHCD" "")
 (setq p1 (list 113.00 1592.25) p2 (list 114.35 1592.25))
 (command "LINE" p1 p2 "")
 (setq p1 (list 114.50 1591.88) p2 (list 0.00 0.00))
 (command "TEXT" "J" "ML" p1   0.75  0.00 "091")
 (command "LAYER" "S" "CGBTHK" "")
 (setq p1 (list 119.00 1591.88) p2 (list 0.00 0.00))
 (command "TEXT" "J" "ML" p1   0.75  0.00 "1.60")
 (command "LAYER" "S" "CGBHZID" "")
 (setq p1 (list 123.50 1591.88) p2 (list 0.00 0.00))
 (command "TEXT" "J" "ML" p1   0.75  0.00 "")
 (setq p1 (list 125.75 1591.88) p2 (list 0.00 0.00))
 (command "TEXT" "J" "ML" p1   0.75  0.00 "7451")
 (command "LAYER" "S" "CGBLITHTXT" "")
 (setq p1 (list 129.50 1591.88) p2 (list 0.00 0.00))
 (command "TEXT" "J" "ML" p1   0.75  0.00 "BRECCIATED FLINT CLAY")
 (command "LAYER" "S" "CGBCMNT" "")
 (setq p1 (list 149.75 1591.88) p2 (list 0.00 0.00))
 (command "TEXT" "J" "ML" p1   0.75  0.00 "")
 (command "LAYER" "S" "CGBMAIN" "")
 (setq p1 (list 107.00 1591.45) p2 (list 113.00 1591.45) p3 (list 113.00 1590.54) p4 (list 107.00 1590.54))
 (command "PLINE" p1 p2 p3 p4 "c")
 (command "HATCH" "ZIGZAG" 0.50 0.00 "L" "")
 (command "COLOR" "BYLAYER")
 (command "LAYER" "S" "CGBLITHCD" "")
 (setq p1 (list 113.00 1591.00) p2 (list 114.35 1591.00))
 (command "LINE" p1 p2 "")
 (setq p1 (list 114.50 1590.62) p2 (list 0.00 0.00))
 (command "TEXT" "J" "ML" p1   0.75  0.00 "804")
 (command "LAYER" "S" "CGBTHK" "")
 (setq p1 (list 119.00 1590.62) p2 (list 0.00 0.00))
 (command "TEXT" "J" "ML" p1   0.75  0.00 "0.91")
 (command "LAYER" "S" "CGBHZID" "")
 (setq p1 (list 123.50 1590.62) p2 (list 0.00 0.00))
 (command "TEXT" "J" "ML" p1   0.75  0.00 "")
 (setq p1 (list 125.75 1590.62) p2 (list 0.00 0.00))
 (command "TEXT" "J" "ML" p1   0.75  0.00 "7451")
 (command "LAYER" "S" "CGBLITHTXT" "")
 (setq p1 (list 129.50 1590.62) p2 (list 0.00 0.00))
 (command "TEXT" "J" "ML" p1   0.75  0.00 "MASS FN GRND SHLY LS")
 (command "LAYER" "S" "CGBCMNT" "")
 (setq p1 (list 149.75 1590.62) p2 (list 0.00 0.00))
 (command "TEXT" "J" "ML" p1   0.75  0.00 "")
 (command "LAYER" "S" "CGBMAIN" "")
 (setq p1 (list 107.00 1590.54) p2 (list 113.00 1590.54) p3 (list 113.00 1588.53) p4 (list 107.00 1588.53))
 (command "PLINE" p1 p2 p3 p4 "c")
 (command "HATCH" "ZIGZAG" 5.00 0.00 "L" "")
 (command "COLOR" "BYLAYER")
 (command "LAYER" "S" "CGBLITHCD" "")
 (setq p1 (list 113.00 1589.54) p2 (list 114.35 1589.54))
 (command "LINE" p1 p2 "")
 (setq p1 (list 114.50 1589.16) p2 (list 0.00 0.00))
 (command "TEXT" "J" "ML" p1   0.75  0.00 "244")
 (command "LAYER" "S" "CGBTHK" "")
 (setq p1 (list 119.00 1589.16) p2 (list 0.00 0.00))
 (command "TEXT" "J" "ML" p1   0.75  0.00 "2.01")
 (command "LAYER" "S" "CGBHZID" "")
 (setq p1 (list 123.50 1589.16) p2 (list 0.00 0.00))
 (command "TEXT" "J" "ML" p1   0.75  0.00 "")
 (setq p1 (list 125.75 1589.16) p2 (list 0.00 0.00))
 (command "TEXT" "J" "ML" p1   0.75  0.00 "7451")
 (command "LAYER" "S" "CGBLITHTXT" "")
 (setq p1 (list 129.50 1589.16) p2 (list 0.00 0.00))
 (command "TEXT" "J" "ML" p1   0.75  0.00 "GRN SH W/LS NODS")
 (command "LAYER" "S" "CGBCMNT" "")
 (setq p1 (list 149.75 1589.16) p2 (list 0.00 0.00))
 (command "TEXT" "J" "ML" p1   0.75  0.00 "VEINS, GB")
 (command "LAYER" "S" "CGBMAIN" "")
 (setq p1 (list 107.00 1588.53) p2 (list 113.00 1588.53) p3 (list 113.00 1585.05) p4 (list 107.00 1585.05))
 (command "PLINE" p1 p2 p3 p4 "c")
 (command "HATCH" "ZIGZAG" 4.00 0.00 "L" "")
 (command "COLOR" "BYLAYER")
 (command "LAYER" "S" "CGBLITHCD" "")
 (setq p1 (list 113.00 1586.79) p2 (list 114.35 1586.79))
 (command "LINE" p1 p2 "")
 (setq p1 (list 114.50 1586.42) p2 (list 0.00 0.00))
 (command "TEXT" "J" "ML" p1   0.75  0.00 "444")
 (command "LAYER" "S" "CGBTHK" "")
 (setq p1 (list 119.00 1586.42) p2 (list 0.00 0.00))
 (command "TEXT" "J" "ML" p1   0.75  0.00 "3.48")
 (command "LAYER" "S" "CGBHZID" "")
 (setq p1 (list 123.50 1586.42) p2 (list 0.00 0.00))
 (command "TEXT" "J" "ML" p1   0.75  0.00 "")
 (setq p1 (list 125.75 1586.42) p2 (list 0.00 0.00))
 (command "TEXT" "J" "ML" p1   0.75  0.00 "7451")
 (command "LAYER" "S" "CGBLITHTXT" "")
 (setq p1 (list 129.50 1586.42) p2 (list 0.00 0.00))
 (command "TEXT" "J" "ML" p1   0.75  0.00 "GRN SDY SH W/LS NODS")
 (command "LAYER" "S" "CGBCMNT" "")
 (setq p1 (list 149.75 1586.42) p2 (list 0.00 0.00))
 (command "TEXT" "J" "ML" p1   0.75  0.00 "")
 (command "LAYER" "S" "CGBMAIN" "")
 (setq p1 (list 107.00 1585.05) p2 (list 113.00 1585.05) p3 (list 113.00 1582.15) p4 (list 107.00 1582.15))
 (command "PLINE" p1 p2 p3 p4 "c")
 (command "HATCH" "ZIGZAG" 4.00 0.00 "L" "")
 (command "COLOR" "BYLAYER")
 (command "LAYER" "S" "CGBLITHCD" "")
 (setq p1 (list 113.00 1583.60) p2 (list 114.35 1583.60))
 (command "LINE" p1 p2 "")
 (setq p1 (list 114.50 1583.23) p2 (list 0.00 0.00))
 (command "TEXT" "J" "ML" p1   0.75  0.00 "444")
 (command "LAYER" "S" "CGBTHK" "")
 (setq p1 (list 119.00 1583.23) p2 (list 0.00 0.00))
 (command "TEXT" "J" "ML" p1   0.75  0.00 "2.90")
 (command "LAYER" "S" "CGBHZID" "")
 (setq p1 (list 123.50 1583.23) p2 (list 0.00 0.00))
 (command "TEXT" "J" "ML" p1   0.75  0.00 "")
 (setq p1 (list 125.75 1583.23) p2 (list 0.00 0.00))
 (command "TEXT" "J" "ML" p1   0.75  0.00 "7451")
 (command "LAYER" "S" "CGBLITHTXT" "")
 (setq p1 (list 129.50 1583.23) p2 (list 0.00 0.00))
 (command "TEXT" "J" "ML" p1   0.75  0.00 "GRN SDY SH W/LS NODS")
 (command "LAYER" "S" "CGBCMNT" "")
 (setq p1 (list 149.75 1583.23) p2 (list 0.00 0.00))
 (command "TEXT" "J" "ML" p1   0.75  0.00 "")
 (command "LAYER" "S" "CGBMAIN" "")
 (setq p1 (list 107.00 1582.15) p2 (list 113.00 1582.15) p3 (list 113.00 1576.05) p4 (list 107.00 1576.05))
 (command "PLINE" p1 p2 p3 p4 "c")
 (command "HATCH" "ZIGZAG" 10.00 45.00 "L" "")
 (command "COLOR" "BYLAYER")
 (command "LAYER" "S" "CGBLITHCD" "")
 (setq p1 (list 113.00 1579.10) p2 (list 114.35 1579.10))
 (command "LINE" p1 p2 "")
 (setq p1 (list 114.50 1578.73) p2 (list 0.00 0.00))
 (command "TEXT" "J" "ML" p1   0.75  0.00 "091")
 (command "LAYER" "S" "CGBTHK" "")
 (setq p1 (list 119.00 1578.73) p2 (list 0.00 0.00))
 (command "TEXT" "J" "ML" p1   0.75  0.00 "6.10")
 (command "LAYER" "S" "CGBHZID" "")
 (setq p1 (list 123.50 1578.73) p2 (list 0.00 0.00))
 (command "TEXT" "J" "ML" p1   0.75  0.00 "")
 (setq p1 (list 125.75 1578.73) p2 (list 0.00 0.00))
 (command "TEXT" "J" "ML" p1   0.75  0.00 "7451")
 (command "LAYER" "S" "CGBLITHTXT" "")
 (setq p1 (list 129.50 1578.73) p2 (list 0.00 0.00))
 (command "TEXT" "J" "ML" p1   0.75  0.00 "BRECCIATED FLINT CLAY")
 (command "LAYER" "S" "CGBCMNT" "")
 (setq p1 (list 149.75 1578.73) p2 (list 0.00 0.00))
 (command "TEXT" "J" "ML" p1   0.75  0.00 "RED & GRN")
 (command "LAYER" "S" "CGBMAIN" "")
 (setq p1 (list 107.00 1576.05) p2 (list 113.00 1576.05) p3 (list 113.00 1574.47) p4 (list 107.00 1574.47))
 (command "PLINE" p1 p2 p3 p4 "c")
 (command "HATCH" "ZIGZAG" 4.00 0.00 "L" "")
 (command "COLOR" "BYLAYER")
 (command "LAYER" "S" "CGBLITHCD" "")
 (setq p1 (list 113.00 1575.26) p2 (list 114.35 1575.26))
 (command "LINE" p1 p2 "")
 (setq p1 (list 114.50 1574.89) p2 (list 0.00 0.00))
 (command "TEXT" "J" "ML" p1   0.75  0.00 "125")
 (command "LAYER" "S" "CGBTHK" "")
 (setq p1 (list 119.00 1574.89) p2 (list 0.00 0.00))
 (command "TEXT" "J" "ML" p1   0.75  0.00 "1.58")
 (command "LAYER" "S" "CGBHZID" "")
 (setq p1 (list 123.50 1574.89) p2 (list 0.00 0.00))
 (command "TEXT" "J" "ML" p1   0.75  0.00 "")
 (setq p1 (list 125.75 1574.89) p2 (list 0.00 0.00))
 (command "TEXT" "J" "ML" p1   0.75  0.00 "7451")
 (command "LAYER" "S" "CGBLITHTXT" "")
 (setq p1 (list 129.50 1574.89) p2 (list 0.00 0.00))
 (command "TEXT" "J" "ML" p1   0.75  0.00 "DRK GRY CHRND SH")
 (command "LAYER" "S" "CGBCMNT" "")
 (setq p1 (list 149.75 1574.89) p2 (list 0.00 0.00))
 (command "TEXT" "J" "ML" p1   0.75  0.00 "MTTLD W/SLX")
 (command "LAYER" "S" "CGBMAIN" "")
 (setq p1 (list 107.00 1574.47) p2 (list 113.00 1574.47) p3 (list 113.00 1573.05) p4 (list 107.00 1573.05))
 (command "PLINE" p1 p2 p3 p4 "c")
 (command "HATCH" "ZIGZAG" 3.00 0.00 "L" "")
 (command "COLOR" "BYLAYER")
 (command "LAYER" "S" "CGBLITHCD" "")
 (setq p1 (list 113.00 1573.76) p2 (list 114.35 1573.76))
 (command "LINE" p1 p2 "")
 (setq p1 (list 114.50 1573.39) p2 (list 0.00 0.00))
 (command "TEXT" "J" "ML" p1   0.75  0.00 "157")
 (command "LAYER" "S" "CGBTHK" "")
 (setq p1 (list 119.00 1573.39) p2 (list 0.00 0.00))
 (command "TEXT" "J" "ML" p1   0.75  0.00 "1.42")
 (command "LAYER" "S" "CGBHZID" "")
 (setq p1 (list 123.50 1573.39) p2 (list 0.00 0.00))
 (command "TEXT" "J" "ML" p1   0.75  0.00 "")
 (setq p1 (list 125.75 1573.39) p2 (list 0.00 0.00))
 (command "TEXT" "J" "ML" p1   0.75  0.00 "7451")
 (command "LAYER" "S" "CGBLITHTXT" "")
 (setq p1 (list 129.50 1573.39) p2 (list 0.00 0.00))
 (command "TEXT" "J" "ML" p1   0.75  0.00 "RED+GRN CLYSTN")
 (command "LAYER" "S" "CGBCMNT" "")
 (setq p1 (list 149.75 1573.39) p2 (list 0.00 0.00))
 (command "TEXT" "J" "ML" p1   0.75  0.00 "SLX")
 (command "LAYER" "S" "CGBMAIN" "")
 (setq p1 (list 107.00 1573.05) p2 (list 113.00 1573.05) p3 (list 113.00 1570.40) p4 (list 107.00 1570.40))
 (command "PLINE" p1 p2 p3 p4 "c")
 (command "HATCH" "ZIGZAG" 5.00 0.00 "L" "")
 (command "COLOR" "BYLAYER")
 (command "LAYER" "S" "CGBLITHCD" "")
 (setq p1 (list 113.00 1571.73) p2 (list 114.35 1571.73))
 (command "LINE" p1 p2 "")
 (setq p1 (list 114.50 1571.35) p2 (list 0.00 0.00))
 (command "TEXT" "J" "ML" p1   0.75  0.00 "227")
 (command "LAYER" "S" "CGBTHK" "")
 (setq p1 (list 119.00 1571.35) p2 (list 0.00 0.00))
 (command "TEXT" "J" "ML" p1   0.75  0.00 "2.65")
 (command "LAYER" "S" "CGBHZID" "")
 (setq p1 (list 123.50 1571.35) p2 (list 0.00 0.00))
 (command "TEXT" "J" "ML" p1   0.75  0.00 "")
 (setq p1 (list 125.75 1571.35) p2 (list 0.00 0.00))
 (command "TEXT" "J" "ML" p1   0.75  0.00 "7451")
 (command "LAYER" "S" "CGBLITHTXT" "")
 (setq p1 (list 129.50 1571.35) p2 (list 0.00 0.00))
 (command "TEXT" "J" "ML" p1   0.75  0.00 "DRK GRY FIRECLAY W/LS NOD")
 (command "LAYER" "S" "CGBCMNT" "")
 (setq p1 (list 149.75 1571.35) p2 (list 0.00 0.00))
 (command "TEXT" "J" "ML" p1   0.75  0.00 "SLX")
 (command "LAYER" "S" "CGBMAIN" "")
 (setq p1 (list 107.00 1570.40) p2 (list 113.00 1570.40) p3 (list 113.00 1568.85) p4 (list 107.00 1568.85))
 (command "PLINE" p1 p2 p3 p4 "c")
 (command "HATCH" "ZIGZAG" 0.25 0.00 "L" "")
 (command "COLOR" "BYLAYER")
 (command "LAYER" "S" "CGBLITHCD" "")
 (setq p1 (list 113.00 1569.63) p2 (list 114.35 1569.63))
 (command "LINE" p1 p2 "")
 (setq p1 (list 114.50 1569.25) p2 (list 0.00 0.00))
 (command "TEXT" "J" "ML" p1   0.75  0.00 "127")
 (command "LAYER" "S" "CGBTHK" "")
 (setq p1 (list 119.00 1569.25) p2 (list 0.00 0.00))
 (command "TEXT" "J" "ML" p1   0.75  0.00 "1.55")
 (command "LAYER" "S" "CGBHZID" "")
 (setq p1 (list 123.50 1569.25) p2 (list 0.00 0.00))
 (command "TEXT" "J" "ML" p1   0.75  0.00 "")
 (setq p1 (list 125.75 1569.25) p2 (list 0.00 0.00))
 (command "TEXT" "J" "ML" p1   0.75  0.00 "7451")
 (command "LAYER" "S" "CGBLITHTXT" "")
 (setq p1 (list 129.50 1569.25) p2 (list 0.00 0.00))
 (command "TEXT" "J" "ML" p1   0.75  0.00 "DRK GRY FIRECLAY")
 (command "LAYER" "S" "CGBCMNT" "")
 (setq p1 (list 149.75 1569.25) p2 (list 0.00 0.00))
 (command "TEXT" "J" "ML" p1   0.75  0.00 "")
 (command "LAYER" "S" "CGBMAIN" "")
 (setq p1 (list 107.00 1568.85) p2 (list 113.00 1568.85) p3 (list 113.00 1568.22) p4 (list 107.00 1568.22))
 (command "PLINE" p1 p2 p3 p4 "c")
 (command "HATCH" "ZIGZAG" 5.00 0.00 "L" "")
 (command "COLOR" "BYLAYER")
 (command "LAYER" "S" "CGBLITHCD" "")
 (setq p1 (list 113.00 1568.54) p2 (list 114.35 1567.29))
 (command "LINE" p1 p2 "")
 (setq p1 (list 114.50 1566.91) p2 (list 0.00 0.00))
 (command "TEXT" "J" "ML" p1   0.75  0.00 "322")
 (command "LAYER" "S" "CGBTHK" "")
 (setq p1 (list 119.00 1566.91) p2 (list 0.00 0.00))
 (command "TEXT" "J" "ML" p1   0.75  0.00 "0.63")
 (command "LAYER" "S" "CGBHZID" "")
 (setq p1 (list 123.50 1566.91) p2 (list 0.00 0.00))
 (command "TEXT" "J" "ML" p1   0.75  0.00 "")
 (setq p1 (list 125.75 1566.91) p2 (list 0.00 0.00))
 (command "TEXT" "J" "ML" p1   0.75  0.00 "7451")
 (command "LAYER" "S" "CGBLITHTXT" "")
 (setq p1 (list 129.50 1566.91) p2 (list 0.00 0.00))
 (command "TEXT" "J" "ML" p1   0.75  0.00 "DRK GRY SH+INTERBED SS")
 (command "LAYER" "S" "CGBCMNT" "")
 (setq p1 (list 149.75 1566.91) p2 (list 0.00 0.00))
 (command "TEXT" "J" "ML" p1   0.75  0.00 "V HRD SS BEDS")
 (command "LAYER" "S" "CGBMAIN" "")
 (setq p1 (list 107.00 1568.22) p2 (list 113.00 1568.22) p3 (list 113.00 1565.65) p4 (list 107.00 1565.65))
 (command "PLINE" p1 p2 p3 p4 "c")
 (command "HATCH" "ZIGZAG" 4.00 0.00 "L" "")
 (command "COLOR" "BYLAYER")
 (command "LAYER" "S" "CGBLITHCD" "")
 (setq p1 (list 113.00 1566.94) p2 (list 114.35 1566.04))
 (command "LINE" p1 p2 "")
 (setq p1 (list 114.50 1565.66) p2 (list 0.00 0.00))
 (command "TEXT" "J" "ML" p1   0.75  0.00 "125")
 (command "LAYER" "S" "CGBTHK" "")
 (setq p1 (list 119.00 1565.66) p2 (list 0.00 0.00))
 (command "TEXT" "J" "ML" p1   0.75  0.00 "2.57")
 (command "LAYER" "S" "CGBHZID" "")
 (setq p1 (list 123.50 1565.66) p2 (list 0.00 0.00))
 (command "TEXT" "J" "ML" p1   0.75  0.00 "")
 (setq p1 (list 125.75 1565.66) p2 (list 0.00 0.00))
 (command "TEXT" "J" "ML" p1   0.75  0.00 "7451")
 (command "LAYER" "S" "CGBLITHTXT" "")
 (setq p1 (list 129.50 1565.66) p2 (list 0.00 0.00))
 (command "TEXT" "J" "ML" p1   0.75  0.00 "DRK GRY CHRND SH")
 (command "LAYER" "S" "CGBCMNT" "")
 (setq p1 (list 149.75 1565.66) p2 (list 0.00 0.00))
 (command "TEXT" "J" "ML" p1   0.75  0.00 "")
 (command "LAYER" "S" "CGBMAIN" "")
 (setq p1 (list 107.00 1565.65) p2 (list 113.00 1565.65) p3 (list 113.00 1565.15) p4 (list 107.00 1565.15))
 (command "PLINE" p1 p2 p3 p4 "c")
 (command "HATCH" "ZIGZAG" 4.00 0.00 "L" "")
 (command "COLOR" "BYLAYER")
 (command "LAYER" "S" "CGBLITHCD" "")
 (setq p1 (list 113.00 1565.40) p2 (list 114.35 1564.79))
 (command "LINE" p1 p2 "")
 (setq p1 (list 114.50 1564.41) p2 (list 0.00 0.00))
 (command "TEXT" "J" "ML" p1   0.75  0.00 "124")
 (command "LAYER" "S" "CGBTHK" "")
 (setq p1 (list 119.00 1564.41) p2 (list 0.00 0.00))
 (command "TEXT" "J" "ML" p1   0.75  0.00 "0.50")
 (command "LAYER" "S" "CGBHZID" "")
 (setq p1 (list 123.50 1564.41) p2 (list 0.00 0.00))
 (command "TEXT" "J" "ML" p1   0.75  0.00 "")
 (setq p1 (list 125.75 1564.41) p2 (list 0.00 0.00))
 (command "TEXT" "J" "ML" p1   0.75  0.00 "7451")
 (command "LAYER" "S" "CGBLITHTXT" "")
 (setq p1 (list 129.50 1564.41) p2 (list 0.00 0.00))
 (command "TEXT" "J" "ML" p1   0.75  0.00 "DRK GRY SH")
 (command "LAYER" "S" "CGBCMNT" "")
 (setq p1 (list 149.75 1564.41) p2 (list 0.00 0.00))
 (command "TEXT" "J" "ML" p1   0.75  0.00 "")
 (command "LAYER" "S" "CGBMAIN" "")
 (setq p1 (list 107.00 1565.15) p2 (list 113.00 1565.15) p3 (list 113.00 1564.55) p4 (list 107.00 1564.55))
 (command "PLINE" p1 p2 p3 p4 "c")
 (command "HATCH" "ZIGZAG" 4.00 0.00 "L" "")
 (command "COLOR" "BYLAYER")
 (command "LAYER" "S" "CGBLITHCD" "")
 (setq p1 (list 113.00 1564.85) p2 (list 114.35 1563.54))
 (command "LINE" p1 p2 "")
 (setq p1 (list 114.50 1563.16) p2 (list 0.00 0.00))
 (command "TEXT" "J" "ML" p1   0.75  0.00 "124")
 (command "LAYER" "S" "CGBTHK" "")
 (setq p1 (list 119.00 1563.16) p2 (list 0.00 0.00))
 (command "TEXT" "J" "ML" p1   0.75  0.00 "0.60")
 (command "LAYER" "S" "CGBHZID" "")
 (setq p1 (list 123.50 1563.16) p2 (list 0.00 0.00))
 (command "TEXT" "J" "ML" p1   0.75  0.00 "")
 (setq p1 (list 125.75 1563.16) p2 (list 0.00 0.00))
 (command "TEXT" "J" "ML" p1   0.75  0.00 "7451")
 (command "LAYER" "S" "CGBLITHTXT" "")
 (setq p1 (list 129.50 1563.16) p2 (list 0.00 0.00))
 (command "TEXT" "J" "ML" p1   0.75  0.00 "DRK GRY SH")
 (command "LAYER" "S" "CGBCMNT" "")
 (setq p1 (list 149.75 1563.16) p2 (list 0.00 0.00))
 (command "TEXT" "J" "ML" p1   0.75  0.00 "GB")
 (command "LAYER" "S" "CGBMAIN" "")
 (setq p1 (list 107.00 1564.55) p2 (list 113.00 1564.55) p3 (list 113.00 1563.67) p4 (list 107.00 1563.67))
 (command "PLINE" p1 p2 p3 p4 "c")
 (command "HATCH" "ZIGZAG" 5.00 0.00 "L" "")
 (command "COLOR" "BYLAYER")
 (command "LAYER" "S" "CGBLITHCD" "")
 (setq p1 (list 113.00 1564.11) p2 (list 114.35 1562.29))
 (command "LINE" p1 p2 "")
 (setq p1 (list 114.50 1561.91) p2 (list 0.00 0.00))
 (command "TEXT" "J" "ML" p1   0.75  0.00 "322")
 (command "LAYER" "S" "CGBTHK" "")
 (setq p1 (list 119.00 1561.91) p2 (list 0.00 0.00))
 (command "TEXT" "J" "ML" p1   0.75  0.00 "0.88")
 (command "LAYER" "S" "CGBHZID" "")
 (setq p1 (list 123.50 1561.91) p2 (list 0.00 0.00))
 (command "TEXT" "J" "ML" p1   0.75  0.00 "")
 (setq p1 (list 125.75 1561.91) p2 (list 0.00 0.00))
 (command "TEXT" "J" "ML" p1   0.75  0.00 "7451")
 (command "LAYER" "S" "CGBLITHTXT" "")
 (setq p1 (list 129.50 1561.91) p2 (list 0.00 0.00))
 (command "TEXT" "J" "ML" p1   0.75  0.00 "DRK GRY SH+INTERBED SS")
 (command "LAYER" "S" "CGBCMNT" "")
 (setq p1 (list 149.75 1561.91) p2 (list 0.00 0.00))
 (command "TEXT" "J" "ML" p1   0.75  0.00 "")
 (command "LAYER" "S" "CGBMAIN" "")
 (setq p1 (list 107.00 1563.67) p2 (list 113.00 1563.67) p3 (list 113.00 1562.29) p4 (list 107.00 1562.29))
 (command "PLINE" p1 p2 p3 p4 "c")
 (command "HATCH" "ZIGZAG" 0.25 0.00 "L" "")
 (command "COLOR" "BYLAYER")
 (command "LAYER" "S" "CGBLITHCD" "")
 (setq p1 (list 113.00 1562.98) p2 (list 114.35 1561.04))
 (command "LINE" p1 p2 "")
 (setq p1 (list 114.50 1560.66) p2 (list 0.00 0.00))
 (command "TEXT" "J" "ML" p1   0.75  0.00 "127")
 (command "LAYER" "S" "CGBTHK" "")
 (setq p1 (list 119.00 1560.66) p2 (list 0.00 0.00))
 (command "TEXT" "J" "ML" p1   0.75  0.00 "1.38")
 (command "LAYER" "S" "CGBHZID" "")
 (setq p1 (list 123.50 1560.66) p2 (list 0.00 0.00))
 (command "TEXT" "J" "ML" p1   0.75  0.00 "")
 (setq p1 (list 125.75 1560.66) p2 (list 0.00 0.00))
 (command "TEXT" "J" "ML" p1   0.75  0.00 "7451")
 (command "LAYER" "S" "CGBLITHTXT" "")
 (setq p1 (list 129.50 1560.66) p2 (list 0.00 0.00))
 (command "TEXT" "J" "ML" p1   0.75  0.00 "DRK GRY FIRECLAY")
 (command "LAYER" "S" "CGBCMNT" "")
 (setq p1 (list 149.75 1560.66) p2 (list 0.00 0.00))
 (command "TEXT" "J" "ML" p1   0.75  0.00 "")
 (command "LAYER" "S" "CGBMAIN" "")
 (setq p1 (list 107.00 1562.29) p2 (list 113.00 1562.29) p3 (list 113.00 1561.79) p4 (list 107.00 1561.79))
 (command "PLINE" p1 p2 p3 p4 "c")
 (command "HATCH" "ZIGZAG" 0.50 0.00 "L" "")
 (command "COLOR" "BYLAYER")
 (command "LAYER" "S" "CGBLITHCD" "")
 (setq p1 (list 113.00 1562.04) p2 (list 114.35 1559.79))
 (command "LINE" p1 p2 "")
 (setq p1 (list 114.50 1559.41) p2 (list 0.00 0.00))
 (command "TEXT" "J" "ML" p1   0.75  0.00 "806")
 (command "LAYER" "S" "CGBTHK" "")
 (setq p1 (list 119.00 1559.41) p2 (list 0.00 0.00))
 (command "TEXT" "J" "ML" p1   0.75  0.00 "0.50")
 (command "LAYER" "S" "CGBHZID" "")
 (setq p1 (list 123.50 1559.41) p2 (list 0.00 0.00))
 (command "TEXT" "J" "ML" p1   0.75  0.00 "")
 (setq p1 (list 125.75 1559.41) p2 (list 0.00 0.00))
 (command "TEXT" "J" "ML" p1   0.75  0.00 "7451")
 (command "LAYER" "S" "CGBLITHTXT" "")
 (setq p1 (list 129.50 1559.41) p2 (list 0.00 0.00))
 (command "TEXT" "J" "ML" p1   0.75  0.00 "FN GRND SHLY LS W/LS NODS")
 (command "LAYER" "S" "CGBCMNT" "")
 (setq p1 (list 149.75 1559.41) p2 (list 0.00 0.00))
 (command "TEXT" "J" "ML" p1   0.75  0.00 "")
 (command "LAYER" "S" "CGBMAIN" "")
 (setq p1 (list 107.00 1561.79) p2 (list 113.00 1561.79) p3 (list 113.00 1560.27) p4 (list 107.00 1560.27))
 (command "PLINE" p1 p2 p3 p4 "c")
 (command "HATCH" "ZIGZAG" 5.00 0.00 "L" "")
 (command "COLOR" "BYLAYER")
 (command "LAYER" "S" "CGBLITHCD" "")
 (setq p1 (list 113.00 1561.03) p2 (list 114.35 1558.54))
 (command "LINE" p1 p2 "")
 (setq p1 (list 114.50 1558.16) p2 (list 0.00 0.00))
 (command "TEXT" "J" "ML" p1   0.75  0.00 "322")
 (command "LAYER" "S" "CGBTHK" "")
 (setq p1 (list 119.00 1558.16) p2 (list 0.00 0.00))
 (command "TEXT" "J" "ML" p1   0.75  0.00 "1.52")
 (command "LAYER" "S" "CGBHZID" "")
 (setq p1 (list 123.50 1558.16) p2 (list 0.00 0.00))
 (command "TEXT" "J" "ML" p1   0.75  0.00 "")
 (setq p1 (list 125.75 1558.16) p2 (list 0.00 0.00))
 (command "TEXT" "J" "ML" p1   0.75  0.00 "7451")
 (command "LAYER" "S" "CGBLITHTXT" "")
 (setq p1 (list 129.50 1558.16) p2 (list 0.00 0.00))
 (command "TEXT" "J" "ML" p1   0.75  0.00 "DRK GRY SH+INTERBED SS")
 (command "LAYER" "S" "CGBCMNT" "")
 (setq p1 (list 149.75 1558.16) p2 (list 0.00 0.00))
 (command "TEXT" "J" "ML" p1   0.75  0.00 "ROOTS")
 (command "LAYER" "S" "CGBMAIN" "")
 (setq p1 (list 107.00 1560.27) p2 (list 113.00 1560.27) p3 (list 113.00 1559.57) p4 (list 107.00 1559.57))
 (command "PLINE" p1 p2 p3 p4 "c")
 (command "HATCH" "ZIGZAG" 4.00 0.00 "L" "")
 (command "COLOR" "BYLAYER")
 (command "LAYER" "S" "CGBLITHCD" "")
 (setq p1 (list 113.00 1559.92) p2 (list 114.35 1557.29))
 (command "LINE" p1 p2 "")
 (setq p1 (list 114.50 1556.91) p2 (list 0.00 0.00))
 (command "TEXT" "J" "ML" p1   0.75  0.00 "564")
 (command "LAYER" "S" "CGBTHK" "")
 (setq p1 (list 119.00 1556.91) p2 (list 0.00 0.00))
 (command "TEXT" "J" "ML" p1   0.75  0.00 "0.70")
 (command "LAYER" "S" "CGBHZID" "")
 (setq p1 (list 123.50 1556.91) p2 (list 0.00 0.00))
 (command "TEXT" "J" "ML" p1   0.75  0.00 "")
 (setq p1 (list 125.75 1556.91) p2 (list 0.00 0.00))
 (command "TEXT" "J" "ML" p1   0.75  0.00 "7451")
 (command "LAYER" "S" "CGBLITHTXT" "")
 (setq p1 (list 129.50 1556.91) p2 (list 0.00 0.00))
 (command "TEXT" "J" "ML" p1   0.75  0.00 "HARD MASS SS")
 (command "LAYER" "S" "CGBCMNT" "")
 (setq p1 (list 149.75 1556.91) p2 (list 0.00 0.00))
 (command "TEXT" "J" "ML" p1   0.75  0.00 "WHITE, SLC")
 (command "LAYER" "S" "CGBMAIN" "")
 (setq p1 (list 107.00 1559.57) p2 (list 113.00 1559.57) p3 (list 113.00 1559.35) p4 (list 107.00 1559.35))
 (command "PLINE" p1 p2 p3 p4 "c")
 (command "HATCH" "ZIGZAG" 5.00 0.00 "L" "")
 (command "COLOR" "BYLAYER")
 (command "LAYER" "S" "CGBLITHCD" "")
 (setq p1 (list 113.00 1559.46) p2 (list 114.35 1556.04))
 (command "LINE" p1 p2 "")
 (setq p1 (list 114.50 1555.66) p2 (list 0.00 0.00))
 (command "TEXT" "J" "ML" p1   0.75  0.00 "322")
 (command "LAYER" "S" "CGBTHK" "")
 (setq p1 (list 119.00 1555.66) p2 (list 0.00 0.00))
 (command "TEXT" "J" "ML" p1   0.75  0.00 "0.22")
 (command "LAYER" "S" "CGBHZID" "")
 (setq p1 (list 123.50 1555.66) p2 (list 0.00 0.00))
 (command "TEXT" "J" "ML" p1   0.75  0.00 "")
 (setq p1 (list 125.75 1555.66) p2 (list 0.00 0.00))
 (command "TEXT" "J" "ML" p1   0.75  0.00 "7451")
 (command "LAYER" "S" "CGBLITHTXT" "")
 (setq p1 (list 129.50 1555.66) p2 (list 0.00 0.00))
 (command "TEXT" "J" "ML" p1   0.75  0.00 "DRK GRY SH+INTERBED SS")
 (command "LAYER" "S" "CGBCMNT" "")
 (setq p1 (list 149.75 1555.66) p2 (list 0.00 0.00))
 (command "TEXT" "J" "ML" p1   0.75  0.00 "")
 (command "LAYER" "S" "CGBMAIN" "")
 (command "LAYER" "S" "CGBLITHCD" "")
 (setq p1 (list 113.00 1559.35) p2 (list 114.35 1554.79))
 (command "LINE" p1 p2 "")
 (setq p1 (list 114.50 1554.41) p2 (list 0.00 0.00))
 (command "TEXT" "J" "ML" p1   0.75  0.00 "020")
 (command "LAYER" "S" "CGBTHK" "")
 (setq p1 (list 119.00 1554.41) p2 (list 0.00 0.00))
 (command "TEXT" "J" "ML" p1   0.75  0.00 "0.00")
 (command "LAYER" "S" "CGBHZID" "")
 (setq p1 (list 123.50 1554.41) p2 (list 0.00 0.00))
 (command "TEXT" "J" "ML" p1   0.75  0.00 "")
 (setq p1 (list 125.75 1554.41) p2 (list 0.00 0.00))
 (command "TEXT" "J" "ML" p1   0.75  0.00 "7000")
 (command "LAYER" "S" "CGBLITHTXT" "")
 (setq p1 (list 129.50 1554.41) p2 (list 0.00 0.00))
 (command "TEXT" "J" "ML" p1   0.75  0.00 "COAL")
 (command "LAYER" "S" "CGBCMNT" "")
 (setq p1 (list 149.75 1554.41) p2 (list 0.00 0.00))
 (command "TEXT" "J" "ML" p1   0.75  0.00 "MAH HRZN")
 (command "LAYER" "S" "CGBMAIN" "")
 (setq p1 (list 107.00 1559.35) p2 (list 113.00 1559.35) p3 (list 113.00 1556.21) p4 (list 107.00 1556.21))
 (command "PLINE" p1 p2 p3 p4 "c")
 (command "HATCH" "ZIGZAG" 0.25 0.00 "L" "")
 (command "COLOR" "BYLAYER")
 (command "LAYER" "S" "CGBLITHCD" "")
 (setq p1 (list 113.00 1557.78) p2 (list 114.35 1553.54))
 (command "LINE" p1 p2 "")
 (setq p1 (list 114.50 1553.16) p2 (list 0.00 0.00))
 (command "TEXT" "J" "ML" p1   0.75  0.00 "127")
 (command "LAYER" "S" "CGBTHK" "")
 (setq p1 (list 119.00 1553.16) p2 (list 0.00 0.00))
 (command "TEXT" "J" "ML" p1   0.75  0.00 "3.14")
 (command "LAYER" "S" "CGBHZID" "")
 (setq p1 (list 123.50 1553.16) p2 (list 0.00 0.00))
 (command "TEXT" "J" "ML" p1   0.75  0.00 "")
 (setq p1 (list 125.75 1553.16) p2 (list 0.00 0.00))
 (command "TEXT" "J" "ML" p1   0.75  0.00 "6951")
 (command "LAYER" "S" "CGBLITHTXT" "")
 (setq p1 (list 129.50 1553.16) p2 (list 0.00 0.00))
 (command "TEXT" "J" "ML" p1   0.75  0.00 "DRK GRY FIRECLAY")
 (command "LAYER" "S" "CGBCMNT" "")
 (setq p1 (list 149.75 1553.16) p2 (list 0.00 0.00))
 (command "TEXT" "J" "ML" p1   0.75  0.00 "SLX, CRB LAYR")
 (command "LAYER" "S" "CGBMAIN" "")
 (setq p1 (list 107.00 1556.21) p2 (list 113.00 1556.21) p3 (list 113.00 1555.01) p4 (list 107.00 1555.01))
 (command "PLINE" p1 p2 p3 p4 "c")
 (command "HATCH" "ZIGZAG" 5.00 0.00 "L" "")
 (command "COLOR" "BYLAYER")
 (command "LAYER" "S" "CGBLITHCD" "")
 (setq p1 (list 113.00 1555.61) p2 (list 114.35 1552.29))
 (command "LINE" p1 p2 "")
 (setq p1 (list 114.50 1551.91) p2 (list 0.00 0.00))
 (command "TEXT" "J" "ML" p1   0.75  0.00 "234")
 (command "LAYER" "S" "CGBTHK" "")
 (setq p1 (list 119.00 1551.91) p2 (list 0.00 0.00))
 (command "TEXT" "J" "ML" p1   0.75  0.00 "1.20")
 (command "LAYER" "S" "CGBHZID" "")
 (setq p1 (list 123.50 1551.91) p2 (list 0.00 0.00))
 (command "TEXT" "J" "ML" p1   0.75  0.00 "")
 (setq p1 (list 125.75 1551.91) p2 (list 0.00 0.00))
 (command "TEXT" "J" "ML" p1   0.75  0.00 "6951")
 (command "LAYER" "S" "CGBLITHTXT" "")
 (setq p1 (list 129.50 1551.91) p2 (list 0.00 0.00))
 (command "TEXT" "J" "ML" p1   0.75  0.00 "LT GRY GRN SH W/LS NODS")
 (command "LAYER" "S" "CGBCMNT" "")
 (setq p1 (list 149.75 1551.91) p2 (list 0.00 0.00))
 (command "TEXT" "J" "ML" p1   0.75  0.00 "")
 (command "LAYER" "S" "CGBMAIN" "")
 (setq p1 (list 107.00 1555.01) p2 (list 113.00 1555.01) p3 (list 113.00 1554.45) p4 (list 107.00 1554.45))
 (command "PLINE" p1 p2 p3 p4 "c")
 (command "HATCH" "ZIGZAG" 10.00 45.00 "L" "")
 (command "COLOR" "BYLAYER")
 (command "LAYER" "S" "CGBLITHCD" "")
 (setq p1 (list 113.00 1554.73) p2 (list 114.35 1551.04))
 (command "LINE" p1 p2 "")
 (setq p1 (list 114.50 1550.66) p2 (list 0.00 0.00))
 (command "TEXT" "J" "ML" p1   0.75  0.00 "096")
 (command "LAYER" "S" "CGBTHK" "")
 (setq p1 (list 119.00 1550.66) p2 (list 0.00 0.00))
 (command "TEXT" "J" "ML" p1   0.75  0.00 "0.56")
 (command "LAYER" "S" "CGBHZID" "")
 (setq p1 (list 123.50 1550.66) p2 (list 0.00 0.00))
 (command "TEXT" "J" "ML" p1   0.75  0.00 "")
 (setq p1 (list 125.75 1550.66) p2 (list 0.00 0.00))
 (command "TEXT" "J" "ML" p1   0.75  0.00 "6951")
 (command "LAYER" "S" "CGBLITHTXT" "")
 (setq p1 (list 129.50 1550.66) p2 (list 0.00 0.00))
 (command "TEXT" "J" "ML" p1   0.75  0.00 "NODULAR FLINT CLAY")
 (command "LAYER" "S" "CGBCMNT" "")
 (setq p1 (list 149.75 1550.66) p2 (list 0.00 0.00))
 (command "TEXT" "J" "ML" p1   0.75  0.00 "")
 (command "LAYER" "S" "CGBMAIN" "")
 (setq p1 (list 107.00 1554.45) p2 (list 113.00 1554.45) p3 (list 113.00 1544.85) p4 (list 107.00 1544.85))
 (command "PLINE" p1 p2 p3 p4 "c")
 (command "HATCH" "ZIGZAG" 5.00 0.00 "L" "")
 (command "COLOR" "BYLAYER")
 (command "LAYER" "S" "CGBLITHCD" "")
 (setq p1 (list 113.00 1549.65) p2 (list 114.35 1549.65))
 (command "LINE" p1 p2 "")
 (setq p1 (list 114.50 1549.28) p2 (list 0.00 0.00))
 (command "TEXT" "J" "ML" p1   0.75  0.00 "274")
 (command "LAYER" "S" "CGBTHK" "")
 (setq p1 (list 119.00 1549.28) p2 (list 0.00 0.00))
 (command "TEXT" "J" "ML" p1   0.75  0.00 "9.60")
 (command "LAYER" "S" "CGBHZID" "")
 (setq p1 (list 123.50 1549.28) p2 (list 0.00 0.00))
 (command "TEXT" "J" "ML" p1   0.75  0.00 "")
 (setq p1 (list 125.75 1549.28) p2 (list 0.00 0.00))
 (command "TEXT" "J" "ML" p1   0.75  0.00 "6951")
 (command "LAYER" "S" "CGBLITHTXT" "")
 (setq p1 (list 129.50 1549.28) p2 (list 0.00 0.00))
 (command "TEXT" "J" "ML" p1   0.75  0.00 "GRY/GRN SH W/LS NODS")
 (command "LAYER" "S" "CGBCMNT" "")
 (setq p1 (list 149.75 1549.28) p2 (list 0.00 0.00))
 (command "TEXT" "J" "ML" p1   0.75  0.00 "")
 (command "LAYER" "S" "CGBMAIN" "")
 (setq p1 (list 107.00 1544.85) p2 (list 113.00 1544.85) p3 (list 113.00 1544.05) p4 (list 107.00 1544.05))
 (command "PLINE" p1 p2 p3 p4 "c")
 (command "HATCH" "ZIGZAG" 5.00 0.00 "L" "")
 (command "COLOR" "BYLAYER")
 (command "LAYER" "S" "CGBLITHCD" "")
 (setq p1 (list 113.00 1544.45) p2 (list 114.35 1544.45))
 (command "LINE" p1 p2 "")
 (setq p1 (list 114.50 1544.08) p2 (list 0.00 0.00))
 (command "TEXT" "J" "ML" p1   0.75  0.00 "274")
 (command "LAYER" "S" "CGBTHK" "")
 (setq p1 (list 119.00 1544.08) p2 (list 0.00 0.00))
 (command "TEXT" "J" "ML" p1   0.75  0.00 "0.80")
 (command "LAYER" "S" "CGBHZID" "")
 (setq p1 (list 123.50 1544.08) p2 (list 0.00 0.00))
 (command "TEXT" "J" "ML" p1   0.75  0.00 "")
 (setq p1 (list 125.75 1544.08) p2 (list 0.00 0.00))
 (command "TEXT" "J" "ML" p1   0.75  0.00 "6951")
 (command "LAYER" "S" "CGBLITHTXT" "")
 (setq p1 (list 129.50 1544.08) p2 (list 0.00 0.00))
 (command "TEXT" "J" "ML" p1   0.75  0.00 "GRY/GRN SH W/LS NODS")
 (command "LAYER" "S" "CGBCMNT" "")
 (setq p1 (list 149.75 1544.08) p2 (list 0.00 0.00))
 (command "TEXT" "J" "ML" p1   0.75  0.00 "GB")
 (command "LAYER" "S" "CGBMAIN" "")
 (setq p1 (list 107.00 1544.05) p2 (list 113.00 1544.05) p3 (list 113.00 1541.65) p4 (list 107.00 1541.65))
 (command "PLINE" p1 p2 p3 p4 "c")
 (command "HATCH" "ZIGZAG" 5.00 0.00 "L" "")
 (command "COLOR" "BYLAYER")
 (command "LAYER" "S" "CGBLITHCD" "")
 (setq p1 (list 113.00 1542.85) p2 (list 114.35 1542.85))
 (command "LINE" p1 p2 "")
 (setq p1 (list 114.50 1542.48) p2 (list 0.00 0.00))
 (command "TEXT" "J" "ML" p1   0.75  0.00 "322")
 (command "LAYER" "S" "CGBTHK" "")
 (setq p1 (list 119.00 1542.48) p2 (list 0.00 0.00))
 (command "TEXT" "J" "ML" p1   0.75  0.00 "2.40")
 (command "LAYER" "S" "CGBHZID" "")
 (setq p1 (list 123.50 1542.48) p2 (list 0.00 0.00))
 (command "TEXT" "J" "ML" p1   0.75  0.00 "")
 (setq p1 (list 125.75 1542.48) p2 (list 0.00 0.00))
 (command "TEXT" "J" "ML" p1   0.75  0.00 "6951")
 (command "LAYER" "S" "CGBLITHTXT" "")
 (setq p1 (list 129.50 1542.48) p2 (list 0.00 0.00))
 (command "TEXT" "J" "ML" p1   0.75  0.00 "DRK GRY SH+INTERBED SS")
 (command "LAYER" "S" "CGBCMNT" "")
 (setq p1 (list 149.75 1542.48) p2 (list 0.00 0.00))
 (command "TEXT" "J" "ML" p1   0.75  0.00 "")
 (command "LAYER" "S" "CGBMAIN" "")
 (setq p1 (list 107.00 1541.65) p2 (list 113.00 1541.65) p3 (list 113.00 1540.20) p4 (list 107.00 1540.20))
 (command "PLINE" p1 p2 p3 p4 "c")
 (command "HATCH" "ZIGZAG" 4.00 0.00 "L" "")
 (command "COLOR" "BYLAYER")
 (command "LAYER" "S" "CGBLITHCD" "")
 (setq p1 (list 113.00 1540.93) p2 (list 114.35 1540.93))
 (command "LINE" p1 p2 "")
 (setq p1 (list 114.50 1540.55) p2 (list 0.00 0.00))
 (command "TEXT" "J" "ML" p1   0.75  0.00 "563")
 (command "LAYER" "S" "CGBTHK" "")
 (setq p1 (list 119.00 1540.55) p2 (list 0.00 0.00))
 (command "TEXT" "J" "ML" p1   0.75  0.00 "1.45")
 (command "LAYER" "S" "CGBHZID" "")
 (setq p1 (list 123.50 1540.55) p2 (list 0.00 0.00))
 (command "TEXT" "J" "ML" p1   0.75  0.00 "")
 (setq p1 (list 125.75 1540.55) p2 (list 0.00 0.00))
 (command "TEXT" "J" "ML" p1   0.75  0.00 "6700")
 (command "LAYER" "S" "CGBLITHTXT" "")
 (setq p1 (list 129.50 1540.55) p2 (list 0.00 0.00))
 (command "TEXT" "J" "ML" p1   0.75  0.00 "HARD SS W/SH STKS")
 (command "LAYER" "S" "CGBCMNT" "")
 (setq p1 (list 149.75 1540.55) p2 (list 0.00 0.00))
 (command "TEXT" "J" "ML" p1   0.75  0.00 "SLC")
 (command "LAYER" "S" "CGBMAIN" "")
 (setq p1 (list 107.00 1540.20) p2 (list 113.00 1540.20) p3 (list 113.00 1534.65) p4 (list 107.00 1534.65))
 (command "PLINE" p1 p2 p3 p4 "c")
 (command "HATCH" "ZIGZAG" 5.00 0.00 "L" "")
 (command "COLOR" "BYLAYER")
 (command "LAYER" "S" "CGBLITHCD" "")
 (setq p1 (list 113.00 1537.43) p2 (list 114.35 1537.43))
 (command "LINE" p1 p2 "")
 (setq p1 (list 114.50 1537.05) p2 (list 0.00 0.00))
 (command "TEXT" "J" "ML" p1   0.75  0.00 "322")
 (command "LAYER" "S" "CGBTHK" "")
 (setq p1 (list 119.00 1537.05) p2 (list 0.00 0.00))
 (command "TEXT" "J" "ML" p1   0.75  0.00 "5.55")
 (command "LAYER" "S" "CGBHZID" "")
 (setq p1 (list 123.50 1537.05) p2 (list 0.00 0.00))
 (command "TEXT" "J" "ML" p1   0.75  0.00 "")
 (setq p1 (list 125.75 1537.05) p2 (list 0.00 0.00))
 (command "TEXT" "J" "ML" p1   0.75  0.00 "6651")
 (command "LAYER" "S" "CGBLITHTXT" "")
 (setq p1 (list 129.50 1537.05) p2 (list 0.00 0.00))
 (command "TEXT" "J" "ML" p1   0.75  0.00 "DRK GRY SH+INTERBED SS")
 (command "LAYER" "S" "CGBCMNT" "")
 (setq p1 (list 149.75 1537.05) p2 (list 0.00 0.00))
 (command "TEXT" "J" "ML" p1   0.75  0.00 "V HRD SS BEDS")
 (command "LAYER" "S" "CGBMAIN" "")
 (setq p1 (list 107.00 1534.65) p2 (list 113.00 1534.65) p3 (list 113.00 1531.92) p4 (list 107.00 1531.92))
 (command "PLINE" p1 p2 p3 p4 "c")
 (command "HATCH" "ZIGZAG" 5.00 0.00 "L" "")
 (command "COLOR" "BYLAYER")
 (command "LAYER" "S" "CGBLITHCD" "")
 (setq p1 (list 113.00 1533.29) p2 (list 114.35 1533.29))
 (command "LINE" p1 p2 "")
 (setq p1 (list 114.50 1532.91) p2 (list 0.00 0.00))
 (command "TEXT" "J" "ML" p1   0.75  0.00 "322")
 (command "LAYER" "S" "CGBTHK" "")
 (setq p1 (list 119.00 1532.91) p2 (list 0.00 0.00))
 (command "TEXT" "J" "ML" p1   0.75  0.00 "2.73")
 (command "LAYER" "S" "CGBHZID" "")
 (setq p1 (list 123.50 1532.91) p2 (list 0.00 0.00))
 (command "TEXT" "J" "ML" p1   0.75  0.00 "")
 (setq p1 (list 125.75 1532.91) p2 (list 0.00 0.00))
 (command "TEXT" "J" "ML" p1   0.75  0.00 "6651")
 (command "LAYER" "S" "CGBLITHTXT" "")
 (setq p1 (list 129.50 1532.91) p2 (list 0.00 0.00))
 (command "TEXT" "J" "ML" p1   0.75  0.00 "DRK GRY SH+INTERBED SS")
 (command "LAYER" "S" "CGBCMNT" "")
 (setq p1 (list 149.75 1532.91) p2 (list 0.00 0.00))
 (command "TEXT" "J" "ML" p1   0.75  0.00 "BRKN ALONG BE")
 (command "LAYER" "S" "CGBMAIN" "")
 (command "LAYER" "S" "CGBLITHCD" "")
 (setq p1 (list 113.00 1531.92) p2 (list 114.35 1531.92))
 (command "LINE" p1 p2 "")
 (setq p1 (list 114.50 1531.55) p2 (list 0.00 0.00))
 (command "TEXT" "J" "ML" p1   0.75  0.00 "540")
 (command "LAYER" "S" "CGBTHK" "")
 (setq p1 (list 119.00 1531.55) p2 (list 0.00 0.00))
 (command "TEXT" "J" "ML" p1   0.75  0.00 "0.00")
 (command "LAYER" "S" "CGBHZID" "")
 (setq p1 (list 123.50 1531.55) p2 (list 0.00 0.00))
 (command "TEXT" "J" "ML" p1   0.75  0.00 "")
 (setq p1 (list 125.75 1531.55) p2 (list 0.00 0.00))
 (command "TEXT" "J" "ML" p1   0.75  0.00 "6400")
 (command "LAYER" "S" "CGBLITHTXT" "")
 (setq p1 (list 129.50 1531.55) p2 (list 0.00 0.00))
 (command "TEXT" "J" "ML" p1   0.75  0.00 "GRY SS")
 (command "LAYER" "S" "CGBCMNT" "")
 (setq p1 (list 149.75 1531.55) p2 (list 0.00 0.00))
 (command "TEXT" "J" "ML" p1   0.75  0.00 "TOP LMH SS??")
 (command "LAYER" "S" "CGBMAIN" "")
 (setq p1 (list 107.00 1531.92) p2 (list 113.00 1531.92) p3 (list 113.00 1531.50) p4 (list 107.00 1531.50))
 (command "PLINE" p1 p2 p3 p4 "c")
 (command "HATCH" "ZIGZAG" 4.00 0.00 "L" "")
 (command "COLOR" "BYLAYER")
 (command "LAYER" "S" "CGBLITHCD" "")
 (setq p1 (list 113.00 1531.71) p2 (list 114.35 1530.46))
 (command "LINE" p1 p2 "")
 (setq p1 (list 114.50 1530.09) p2 (list 0.00 0.00))
 (command "TEXT" "J" "ML" p1   0.75  0.00 "564")
 (command "LAYER" "S" "CGBTHK" "")
 (setq p1 (list 119.00 1530.09) p2 (list 0.00 0.00))
 (command "TEXT" "J" "ML" p1   0.75  0.00 "0.42")
 (command "LAYER" "S" "CGBHZID" "")
 (setq p1 (list 123.50 1530.09) p2 (list 0.00 0.00))
 (command "TEXT" "J" "ML" p1   0.75  0.00 "")
 (setq p1 (list 125.75 1530.09) p2 (list 0.00 0.00))
 (command "TEXT" "J" "ML" p1   0.75  0.00 "6400")
 (command "LAYER" "S" "CGBLITHTXT" "")
 (setq p1 (list 129.50 1530.09) p2 (list 0.00 0.00))
 (command "TEXT" "J" "ML" p1   0.75  0.00 "HARD MASS SS")
 (command "LAYER" "S" "CGBCMNT" "")
 (setq p1 (list 149.75 1530.09) p2 (list 0.00 0.00))
 (command "TEXT" "J" "ML" p1   0.75  0.00 "SLC")
 (command "LAYER" "S" "CGBMAIN" "")
 (setq p1 (list 107.00 1531.50) p2 (list 113.00 1531.50) p3 (list 113.00 1530.57) p4 (list 107.00 1530.57))
 (command "PLINE" p1 p2 p3 p4 "c")
 (command "HATCH" "ZIGZAG" 4.00 0.00 "L" "")
 (command "COLOR" "BYLAYER")
 (command "LAYER" "S" "CGBLITHCD" "")
 (setq p1 (list 113.00 1531.04) p2 (list 114.35 1529.21))
 (command "LINE" p1 p2 "")
 (setq p1 (list 114.50 1528.84) p2 (list 0.00 0.00))
 (command "TEXT" "J" "ML" p1   0.75  0.00 "124")
 (command "LAYER" "S" "CGBTHK" "")
 (setq p1 (list 119.00 1528.84) p2 (list 0.00 0.00))
 (command "TEXT" "J" "ML" p1   0.75  0.00 "0.93")
 (command "LAYER" "S" "CGBHZID" "")
 (setq p1 (list 123.50 1528.84) p2 (list 0.00 0.00))
 (command "TEXT" "J" "ML" p1   0.75  0.00 "")
 (setq p1 (list 125.75 1528.84) p2 (list 0.00 0.00))
 (command "TEXT" "J" "ML" p1   0.75  0.00 "6400")
 (command "LAYER" "S" "CGBLITHTXT" "")
 (setq p1 (list 129.50 1528.84) p2 (list 0.00 0.00))
 (command "TEXT" "J" "ML" p1   0.75  0.00 "DRK GRY SH")
 (command "LAYER" "S" "CGBCMNT" "")
 (setq p1 (list 149.75 1528.84) p2 (list 0.00 0.00))
 (command "TEXT" "J" "ML" p1   0.75  0.00 "FEW CLEAN SS")
 (command "LAYER" "S" "CGBMAIN" "")
 (setq p1 (list 107.00 1530.57) p2 (list 113.00 1530.57) p3 (list 113.00 1523.91) p4 (list 107.00 1523.91))
 (command "PLINE" p1 p2 p3 p4 "c")
 (command "HATCH" "ZIGZAG" 4.00 0.00 "L" "")
 (command "COLOR" "BYLAYER")
 (command "LAYER" "S" "CGBLITHCD" "")
 (setq p1 (list 113.00 1527.24) p2 (list 114.35 1527.24))
 (command "LINE" p1 p2 "")
 (setq p1 (list 114.50 1526.87) p2 (list 0.00 0.00))
 (command "TEXT" "J" "ML" p1   0.75  0.00 "561")
 (command "LAYER" "S" "CGBTHK" "")
 (setq p1 (list 119.00 1526.87) p2 (list 0.00 0.00))
 (command "TEXT" "J" "ML" p1   0.75  0.00 "6.66")
 (command "LAYER" "S" "CGBHZID" "")
 (setq p1 (list 123.50 1526.87) p2 (list 0.00 0.00))
 (command "TEXT" "J" "ML" p1   0.75  0.00 "")
 (setq p1 (list 125.75 1526.87) p2 (list 0.00 0.00))
 (command "TEXT" "J" "ML" p1   0.75  0.00 "6400")
 (command "LAYER" "S" "CGBLITHTXT" "")
 (setq p1 (list 129.50 1526.87) p2 (list 0.00 0.00))
 (command "TEXT" "J" "ML" p1   0.75  0.00 "HARD CROSSBED SS")
 (command "LAYER" "S" "CGBCMNT" "")
 (setq p1 (list 149.75 1526.87) p2 (list 0.00 0.00))
 (command "TEXT" "J" "ML" p1   0.75  0.00 "F GR DRK, SLC")
 (command "LAYER" "S" "CGBMAIN" "")
 (setq p1 (list 107.00 1523.91) p2 (list 113.00 1523.91) p3 (list 113.00 1523.62) p4 (list 107.00 1523.62))
 (command "PLINE" p1 p2 p3 p4 "c")
 (command "HATCH" "ZIGZAG" 4.00 22.50 "L" "")
 (command "COLOR" "BYLAYER")
 (command "LAYER" "S" "CGBLITHCD" "")
 (setq p1 (list 113.00 1523.77) p2 (list 114.35 1523.77))
 (command "LINE" p1 p2 "")
 (setq p1 (list 114.50 1523.39) p2 (list 0.00 0.00))
 (command "TEXT" "J" "ML" p1   0.75  0.00 "134")
 (command "LAYER" "S" "CGBTHK" "")
 (setq p1 (list 119.00 1523.39) p2 (list 0.00 0.00))
 (command "TEXT" "J" "ML" p1   0.75  0.00 "0.29")
 (command "LAYER" "S" "CGBHZID" "")
 (setq p1 (list 123.50 1523.39) p2 (list 0.00 0.00))
 (command "TEXT" "J" "ML" p1   0.75  0.00 "")
 (setq p1 (list 125.75 1523.39) p2 (list 0.00 0.00))
 (command "TEXT" "J" "ML" p1   0.75  0.00 "6400")
 (command "LAYER" "S" "CGBLITHTXT" "")
 (setq p1 (list 129.50 1523.39) p2 (list 0.00 0.00))
 (command "TEXT" "J" "ML" p1   0.75  0.00 "LT GRY GRN SH")
 (command "LAYER" "S" "CGBCMNT" "")
 (setq p1 (list 149.75 1523.39) p2 (list 0.00 0.00))
 (command "TEXT" "J" "ML" p1   0.75  0.00 "SFT")
 (command "LAYER" "S" "CGBMAIN" "")
 (setq p1 (list 107.00 1523.62) p2 (list 113.00 1523.62) p3 (list 113.00 1521.83) p4 (list 107.00 1521.83))
 (command "PLINE" p1 p2 p3 p4 "c")
 (command "HATCH" "ZIGZAG" 5.00 0.00 "L" "")
 (command "COLOR" "BYLAYER")
 (command "LAYER" "S" "CGBLITHCD" "")
 (setq p1 (list 113.00 1522.73) p2 (list 114.35 1521.48))
 (command "LINE" p1 p2 "")
 (setq p1 (list 114.50 1521.10) p2 (list 0.00 0.00))
 (command "TEXT" "J" "ML" p1   0.75  0.00 "322")
 (command "LAYER" "S" "CGBTHK" "")
 (setq p1 (list 119.00 1521.10) p2 (list 0.00 0.00))
 (command "TEXT" "J" "ML" p1   0.75  0.00 "1.79")
 (command "LAYER" "S" "CGBHZID" "")
 (setq p1 (list 123.50 1521.10) p2 (list 0.00 0.00))
 (command "TEXT" "J" "ML" p1   0.75  0.00 "")
 (setq p1 (list 125.75 1521.10) p2 (list 0.00 0.00))
 (command "TEXT" "J" "ML" p1   0.75  0.00 "6400")
 (command "LAYER" "S" "CGBLITHTXT" "")
 (setq p1 (list 129.50 1521.10) p2 (list 0.00 0.00))
 (command "TEXT" "J" "ML" p1   0.75  0.00 "DRK GRY SH+INTERBED SS")
 (command "LAYER" "S" "CGBCMNT" "")
 (setq p1 (list 149.75 1521.10) p2 (list 0.00 0.00))
 (command "TEXT" "J" "ML" p1   0.75  0.00 "V HRD LAYRS")
 (command "LAYER" "S" "CGBMAIN" "")
 (setq p1 (list 107.00 1521.83) p2 (list 113.00 1521.83) p3 (list 113.00 1520.75) p4 (list 107.00 1520.75))
 (command "PLINE" p1 p2 p3 p4 "c")
 (command "HATCH" "ZIGZAG" 2.00 45.00 "L" "")
 (command "COLOR" "BYLAYER")
 (command "LAYER" "S" "CGBLITHCD" "")
 (setq p1 (list 113.00 1521.29) p2 (list 114.35 1520.23))
 (command "LINE" p1 p2 "")
 (setq p1 (list 114.50 1519.85) p2 (list 0.00 0.00))
 (command "TEXT" "J" "ML" p1   0.75  0.00 "313")
 (command "LAYER" "S" "CGBTHK" "")
 (setq p1 (list 119.00 1519.85) p2 (list 0.00 0.00))
 (command "TEXT" "J" "ML" p1   0.75  0.00 "1.08")
 (command "LAYER" "S" "CGBHZID" "")
 (setq p1 (list 123.50 1519.85) p2 (list 0.00 0.00))
 (command "TEXT" "J" "ML" p1   0.75  0.00 "")
 (setq p1 (list 125.75 1519.85) p2 (list 0.00 0.00))
 (command "TEXT" "J" "ML" p1   0.75  0.00 "6400")
 (command "LAYER" "S" "CGBLITHTXT" "")
 (setq p1 (list 129.50 1519.85) p2 (list 0.00 0.00))
 (command "TEXT" "J" "ML" p1   0.75  0.00 "BLK SH W/SS STKS")
 (command "LAYER" "S" "CGBCMNT" "")
 (setq p1 (list 149.75 1519.85) p2 (list 0.00 0.00))
 (command "TEXT" "J" "ML" p1   0.75  0.00 "RIP")
 (command "LAYER" "S" "CGBMAIN" "")
 (setq p1 (list 107.00 1520.75) p2 (list 113.00 1520.75) p3 (list 113.00 1515.77) p4 (list 107.00 1515.77))
 (command "PLINE" p1 p2 p3 p4 "c")
 (command "HATCH" "ZIGZAG" 0.25 0.00 "L" "")
 (command "COLOR" "BYLAYER")
 (command "LAYER" "S" "CGBLITHCD" "")
 (setq p1 (list 113.00 1518.26) p2 (list 114.35 1518.26))
 (command "LINE" p1 p2 "")
 (setq p1 (list 114.50 1517.89) p2 (list 0.00 0.00))
 (command "TEXT" "J" "ML" p1   0.75  0.00 "762")
 (command "LAYER" "S" "CGBTHK" "")
 (setq p1 (list 119.00 1517.89) p2 (list 0.00 0.00))
 (command "TEXT" "J" "ML" p1   0.75  0.00 "4.98")
 (command "LAYER" "S" "CGBHZID" "")
 (setq p1 (list 123.50 1517.89) p2 (list 0.00 0.00))
 (command "TEXT" "J" "ML" p1   0.75  0.00 "")
 (setq p1 (list 125.75 1517.89) p2 (list 0.00 0.00))
 (command "TEXT" "J" "ML" p1   0.75  0.00 "6400")
 (command "LAYER" "S" "CGBLITHTXT" "")
 (setq p1 (list 129.50 1517.89) p2 (list 0.00 0.00))
 (command "TEXT" "J" "ML" p1   0.75  0.00 "HARD SH PEB CGL")
 (command "LAYER" "S" "CGBCMNT" "")
 (setq p1 (list 149.75 1517.89) p2 (list 0.00 0.00))
 (command "TEXT" "J" "ML" p1   0.75  0.00 "EROS SLC, SPA")
 (command "LAYER" "S" "CGBMAIN" "")
 (setq p1 (list 107.00 1515.77) p2 (list 113.00 1515.77) p3 (list 113.00 1515.64) p4 (list 107.00 1515.64))
 (command "PLINE" p1 p2 p3 p4 "c")
 (command "HATCH" "ZIGZAG" 4.00 22.50 "L" "")
 (command "COLOR" "BYLAYER")
 (command "LAYER" "S" "CGBLITHCD" "")
 (setq p1 (list 113.00 1515.71) p2 (list 114.35 1515.71))
 (command "LINE" p1 p2 "")
 (setq p1 (list 114.50 1515.33) p2 (list 0.00 0.00))
 (command "TEXT" "J" "ML" p1   0.75  0.00 "114")
 (command "LAYER" "S" "CGBTHK" "")
 (setq p1 (list 119.00 1515.33) p2 (list 0.00 0.00))
 (command "TEXT" "J" "ML" p1   0.75  0.00 "0.13")
 (command "LAYER" "S" "CGBHZID" "")
 (setq p1 (list 123.50 1515.33) p2 (list 0.00 0.00))
 (command "TEXT" "J" "ML" p1   0.75  0.00 "")
 (setq p1 (list 125.75 1515.33) p2 (list 0.00 0.00))
 (command "TEXT" "J" "ML" p1   0.75  0.00 "6400")
 (command "LAYER" "S" "CGBLITHTXT" "")
 (setq p1 (list 129.50 1515.33) p2 (list 0.00 0.00))
 (command "TEXT" "J" "ML" p1   0.75  0.00 "BLK SH")
 (command "LAYER" "S" "CGBCMNT" "")
 (setq p1 (list 149.75 1515.33) p2 (list 0.00 0.00))
 (command "TEXT" "J" "ML" p1   0.75  0.00 "DRK, SH SPAR?")
 (command "LAYER" "S" "CGBMAIN" "")
 (setq p1 (list 107.00 1515.64) p2 (list 113.00 1515.64) p3 (list 113.00 1514.65) p4 (list 107.00 1514.65))
 (command "PLINE" p1 p2 p3 p4 "c")
 (command "HATCH" "ZIGZAG" 4.00 0.00 "L" "")
 (command "COLOR" "BYLAYER")
 (command "LAYER" "S" "CGBLITHCD" "")
 (setq p1 (list 113.00 1515.15) p2 (list 114.35 1513.90))
 (command "LINE" p1 p2 "")
 (setq p1 (list 114.50 1513.52) p2 (list 0.00 0.00))
 (command "TEXT" "J" "ML" p1   0.75  0.00 "564")
 (command "LAYER" "S" "CGBTHK" "")
 (setq p1 (list 119.00 1513.52) p2 (list 0.00 0.00))
 (command "TEXT" "J" "ML" p1   0.75  0.00 "0.99")
 (command "LAYER" "S" "CGBHZID" "")
 (setq p1 (list 123.50 1513.52) p2 (list 0.00 0.00))
 (command "TEXT" "J" "ML" p1   0.75  0.00 "")
 (setq p1 (list 125.75 1513.52) p2 (list 0.00 0.00))
 (command "TEXT" "J" "ML" p1   0.75  0.00 "6400")
 (command "LAYER" "S" "CGBLITHTXT" "")
 (setq p1 (list 129.50 1513.52) p2 (list 0.00 0.00))
 (command "TEXT" "J" "ML" p1   0.75  0.00 "HARD MASS SS")
 (command "LAYER" "S" "CGBCMNT" "")
 (setq p1 (list 149.75 1513.52) p2 (list 0.00 0.00))
 (command "TEXT" "J" "ML" p1   0.75  0.00 "DRK,SUGRY,FRA")
 (command "LAYER" "S" "CGBMAIN" "")
 (setq p1 (list 107.00 1514.65) p2 (list 113.00 1514.65) p3 (list 113.00 1511.75) p4 (list 107.00 1511.75))
 (command "PLINE" p1 p2 p3 p4 "c")
 (command "HATCH" "ZIGZAG" 4.00 0.00 "L" "")
 (command "COLOR" "BYLAYER")
 (command "LAYER" "S" "CGBLITHCD" "")
 (setq p1 (list 113.00 1513.20) p2 (list 114.35 1512.65))
 (command "LINE" p1 p2 "")
 (setq p1 (list 114.50 1512.27) p2 (list 0.00 0.00))
 (command "TEXT" "J" "ML" p1   0.75  0.00 "564")
 (command "LAYER" "S" "CGBTHK" "")
 (setq p1 (list 119.00 1512.27) p2 (list 0.00 0.00))
 (command "TEXT" "J" "ML" p1   0.75  0.00 "2.90")
 (command "LAYER" "S" "CGBHZID" "")
 (setq p1 (list 123.50 1512.27) p2 (list 0.00 0.00))
 (command "TEXT" "J" "ML" p1   0.75  0.00 "")
 (setq p1 (list 125.75 1512.27) p2 (list 0.00 0.00))
 (command "TEXT" "J" "ML" p1   0.75  0.00 "6400")
 (command "LAYER" "S" "CGBLITHTXT" "")
 (setq p1 (list 129.50 1512.27) p2 (list 0.00 0.00))
 (command "TEXT" "J" "ML" p1   0.75  0.00 "HARD MASS SS")
 (command "LAYER" "S" "CGBCMNT" "")
 (setq p1 (list 149.75 1512.27) p2 (list 0.00 0.00))
 (command "TEXT" "J" "ML" p1   0.75  0.00 "DRK, STYL,SLC")
 (command "LAYER" "S" "CGBMAIN" "")
 (setq p1 (list 107.00 1511.75) p2 (list 113.00 1511.75) p3 (list 113.00 1511.62) p4 (list 107.00 1511.62))
 (command "PLINE" p1 p2 p3 p4 "c")
 (command "HATCH" "ZIGZAG" 2.00 45.00 "L" "")
 (command "COLOR" "BYLAYER")
 (command "LAYER" "S" "CGBLITHCD" "")
 (setq p1 (list 113.00 1511.69) p2 (list 114.35 1511.40))
 (command "LINE" p1 p2 "")
 (setq p1 (list 114.50 1511.02) p2 (list 0.00 0.00))
 (command "TEXT" "J" "ML" p1   0.75  0.00 "313")
 (command "LAYER" "S" "CGBTHK" "")
 (setq p1 (list 119.00 1511.02) p2 (list 0.00 0.00))
 (command "TEXT" "J" "ML" p1   0.75  0.00 "0.13")
 (command "LAYER" "S" "CGBHZID" "")
 (setq p1 (list 123.50 1511.02) p2 (list 0.00 0.00))
 (command "TEXT" "J" "ML" p1   0.75  0.00 "")
 (setq p1 (list 125.75 1511.02) p2 (list 0.00 0.00))
 (command "TEXT" "J" "ML" p1   0.75  0.00 "6400")
 (command "LAYER" "S" "CGBLITHTXT" "")
 (setq p1 (list 129.50 1511.02) p2 (list 0.00 0.00))
 (command "TEXT" "J" "ML" p1   0.75  0.00 "BLK SH W/SS STKS")
 (command "LAYER" "S" "CGBCMNT" "")
 (setq p1 (list 149.75 1511.02) p2 (list 0.00 0.00))
 (command "TEXT" "J" "ML" p1   0.75  0.00 "BURRS??")
 (command "LAYER" "S" "CGBMAIN" "")
 (setq p1 (list 107.00 1511.62) p2 (list 113.00 1511.62) p3 (list 113.00 1511.17) p4 (list 107.00 1511.17))
 (command "PLINE" p1 p2 p3 p4 "c")
 (command "HATCH" "ZIGZAG" 4.00 0.00 "L" "")
 (command "COLOR" "BYLAYER")
 (command "LAYER" "S" "CGBLITHCD" "")
 (setq p1 (list 113.00 1511.40) p2 (list 114.35 1510.15))
 (command "LINE" p1 p2 "")
 (setq p1 (list 114.50 1509.77) p2 (list 0.00 0.00))
 (command "TEXT" "J" "ML" p1   0.75  0.00 "563")
 (command "LAYER" "S" "CGBTHK" "")
 (setq p1 (list 119.00 1509.77) p2 (list 0.00 0.00))
 (command "TEXT" "J" "ML" p1   0.75  0.00 "0.45")
 (command "LAYER" "S" "CGBHZID" "")
 (setq p1 (list 123.50 1509.77) p2 (list 0.00 0.00))
 (command "TEXT" "J" "ML" p1   0.75  0.00 "")
 (setq p1 (list 125.75 1509.77) p2 (list 0.00 0.00))
 (command "TEXT" "J" "ML" p1   0.75  0.00 "6400")
 (command "LAYER" "S" "CGBLITHTXT" "")
 (setq p1 (list 129.50 1509.77) p2 (list 0.00 0.00))
 (command "TEXT" "J" "ML" p1   0.75  0.00 "HARD SS W/SH STKS")
 (command "LAYER" "S" "CGBCMNT" "")
 (setq p1 (list 149.75 1509.77) p2 (list 0.00 0.00))
 (command "TEXT" "J" "ML" p1   0.75  0.00 "ANG SLC")
 (command "LAYER" "S" "CGBMAIN" "")
 (setq p1 (list 107.00 1511.17) p2 (list 113.00 1511.17) p3 (list 113.00 1510.43) p4 (list 107.00 1510.43))
 (command "PLINE" p1 p2 p3 p4 "c")
 (command "HATCH" "ZIGZAG" 0.50 0.00 "L" "")
 (command "COLOR" "BYLAYER")
 (command "LAYER" "S" "CGBLITHCD" "")
 (setq p1 (list 113.00 1510.80) p2 (list 114.35 1508.90))
 (command "LINE" p1 p2 "")
 (setq p1 (list 114.50 1508.52) p2 (list 0.00 0.00))
 (command "TEXT" "J" "ML" p1   0.75  0.00 "323")
 (command "LAYER" "S" "CGBTHK" "")
 (setq p1 (list 119.00 1508.52) p2 (list 0.00 0.00))
 (command "TEXT" "J" "ML" p1   0.75  0.00 "0.74")
 (command "LAYER" "S" "CGBHZID" "")
 (setq p1 (list 123.50 1508.52) p2 (list 0.00 0.00))
 (command "TEXT" "J" "ML" p1   0.75  0.00 "")
 (setq p1 (list 125.75 1508.52) p2 (list 0.00 0.00))
 (command "TEXT" "J" "ML" p1   0.75  0.00 "6351")
 (command "LAYER" "S" "CGBLITHTXT" "")
 (setq p1 (list 129.50 1508.52) p2 (list 0.00 0.00))
 (command "TEXT" "J" "ML" p1   0.75  0.00 "DRK GRY SH W/SS STKS")
 (command "LAYER" "S" "CGBCMNT" "")
 (setq p1 (list 149.75 1508.52) p2 (list 0.00 0.00))
 (command "TEXT" "J" "ML" p1   0.75  0.00 "ANG BEDS,FLOW")
 (command "LAYER" "S" "CGBMAIN" "")
 (setq p1 (list 107.00 1510.43) p2 (list 113.00 1510.43) p3 (list 113.00 1509.24) p4 (list 107.00 1509.24))
 (command "PLINE" p1 p2 p3 p4 "c")
 (command "HATCH" "ZIGZAG" 4.00 0.00 "L" "")
 (command "COLOR" "BYLAYER")
 (command "LAYER" "S" "CGBLITHCD" "")
 (setq p1 (list 113.00 1509.84) p2 (list 114.35 1507.65))
 (command "LINE" p1 p2 "")
 (setq p1 (list 114.50 1507.27) p2 (list 0.00 0.00))
 (command "TEXT" "J" "ML" p1   0.75  0.00 "122")
 (command "LAYER" "S" "CGBTHK" "")
 (setq p1 (list 119.00 1507.27) p2 (list 0.00 0.00))
 (command "TEXT" "J" "ML" p1   0.75  0.00 "1.19")
 (command "LAYER" "S" "CGBHZID" "")
 (setq p1 (list 123.50 1507.27) p2 (list 0.00 0.00))
 (command "TEXT" "J" "ML" p1   0.75  0.00 "")
 (setq p1 (list 125.75 1507.27) p2 (list 0.00 0.00))
 (command "TEXT" "J" "ML" p1   0.75  0.00 "6351")
 (command "LAYER" "S" "CGBLITHTXT" "")
 (setq p1 (list 129.50 1507.27) p2 (list 0.00 0.00))
 (command "TEXT" "J" "ML" p1   0.75  0.00 "DK GRY LAYERED SH")
 (command "LAYER" "S" "CGBCMNT" "")
 (setq p1 (list 149.75 1507.27) p2 (list 0.00 0.00))
 (command "TEXT" "J" "ML" p1   0.75  0.00 "SIGHT ANG BED")
 (command "LAYER" "S" "CGBMAIN" "")
 (setq p1 (list 107.00 1509.24) p2 (list 113.00 1509.24) p3 (list 113.00 1507.65) p4 (list 107.00 1507.65))
 (command "PLINE" p1 p2 p3 p4 "c")
 (command "HATCH" "ZIGZAG" 4.00 22.50 "L" "")
 (command "COLOR" "BYLAYER")
 (command "LAYER" "S" "CGBLITHCD" "")
 (setq p1 (list 113.00 1508.45) p2 (list 114.35 1506.40))
 (command "LINE" p1 p2 "")
 (setq p1 (list 114.50 1506.02) p2 (list 0.00 0.00))
 (command "TEXT" "J" "ML" p1   0.75  0.00 "114")
 (command "LAYER" "S" "CGBTHK" "")
 (setq p1 (list 119.00 1506.02) p2 (list 0.00 0.00))
 (command "TEXT" "J" "ML" p1   0.75  0.00 "1.59")
 (command "LAYER" "S" "CGBHZID" "")
 (setq p1 (list 123.50 1506.02) p2 (list 0.00 0.00))
 (command "TEXT" "J" "ML" p1   0.75  0.00 "")
 (setq p1 (list 125.75 1506.02) p2 (list 0.00 0.00))
 (command "TEXT" "J" "ML" p1   0.75  0.00 "6351")
 (command "LAYER" "S" "CGBLITHTXT" "")
 (setq p1 (list 129.50 1506.02) p2 (list 0.00 0.00))
 (command "TEXT" "J" "ML" p1   0.75  0.00 "BLK SH")
 (command "LAYER" "S" "CGBCMNT" "")
 (setq p1 (list 149.75 1506.02) p2 (list 0.00 0.00))
 (command "TEXT" "J" "ML" p1   0.75  0.00 "SFT, BRKN, FR")
 (command "LAYER" "S" "CGBMAIN" "")
 (setq p1 (list 107.00 1507.65) p2 (list 113.00 1507.65) p3 (list 113.00 1507.40) p4 (list 107.00 1507.40))
 (command "PLINE" p1 p2 p3 p4 "c")
 (command "HATCH" "ZIGZAG" 0.80 0.00 "L" "")
 (command "COLOR" "BYLAYER")
 (command "LAYER" "S" "CGBLITHCD" "")
 (setq p1 (list 113.00 1507.53) p2 (list 114.35 1505.15))
 (command "LINE" p1 p2 "")
 (setq p1 (list 114.50 1504.77) p2 (list 0.00 0.00))
 (command "TEXT" "J" "ML" p1   0.75  0.00 "029")
 (command "LAYER" "S" "CGBTHK" "")
 (setq p1 (list 119.00 1504.77) p2 (list 0.00 0.00))
 (command "TEXT" "J" "ML" p1   0.75  0.00 "0.25")
 (command "LAYER" "S" "CGBHZID" "")
 (setq p1 (list 123.50 1504.77) p2 (list 0.00 0.00))
 (command "TEXT" "J" "ML" p1   0.75  0.00 "")
 (setq p1 (list 125.75 1504.77) p2 (list 0.00 0.00))
 (command "TEXT" "J" "ML" p1   0.75  0.00 "6000")
 (command "LAYER" "S" "CGBLITHTXT" "")
 (setq p1 (list 129.50 1504.77) p2 (list 0.00 0.00))
 (command "TEXT" "J" "ML" p1   0.75  0.00 "COAL W/PYRITE STKS")
 (command "LAYER" "S" "CGBCMNT" "")
 (setq p1 (list 149.75 1504.77) p2 (list 0.00 0.00))
 (command "TEXT" "J" "ML" p1   0.75  0.00 "VIT W/PYRT")
 (command "LAYER" "S" "CGBMAIN" "")
 (setq p1 (list 107.00 1507.40) p2 (list 113.00 1507.40) p3 (list 113.00 1507.06) p4 (list 107.00 1507.06))
 (command "PLINE" p1 p2 p3 p4 "c")
 (command "COLOR" "BLUE")
 (command "SOLID" p1 p2 p4 p3 "")
 (command "COLOR" "BYLAYER")
 (command "LAYER" "S" "CGBLITHCD" "")
 (setq p1 (list 113.00 1507.23) p2 (list 114.35 1503.90))
 (command "LINE" p1 p2 "")
 (setq p1 (list 114.50 1503.52) p2 (list 0.00 0.00))
 (command "TEXT" "J" "ML" p1   0.75  0.00 "021")
 (command "LAYER" "S" "CGBTHK" "")
 (setq p1 (list 119.00 1503.52) p2 (list 0.00 0.00))
 (command "TEXT" "J" "ML" p1   0.75  0.00 "0.34")
 (command "LAYER" "S" "CGBHZID" "")
 (setq p1 (list 123.50 1503.52) p2 (list 0.00 0.00))
 (command "TEXT" "J" "ML" p1   0.75  0.00 "")
 (setq p1 (list 125.75 1503.52) p2 (list 0.00 0.00))
 (command "TEXT" "J" "ML" p1   0.75  0.00 "6000")
 (command "LAYER" "S" "CGBLITHTXT" "")
 (setq p1 (list 129.50 1503.52) p2 (list 0.00 0.00))
 (command "TEXT" "J" "ML" p1   0.75  0.00 "COMMON BANDED COAL")
 (command "LAYER" "S" "CGBCMNT" "")
 (setq p1 (list 149.75 1503.52) p2 (list 0.00 0.00))
 (command "TEXT" "J" "ML" p1   0.75  0.00 "DULL W/ VIT")
 (command "LAYER" "S" "CGBMAIN" "")
 (setq p1 (list 107.00 1507.06) p2 (list 113.00 1507.06) p3 (list 113.00 1506.63) p4 (list 107.00 1506.63))
 (command "PLINE" p1 p2 p3 p4 "c")
 (command "HATCH" "ZIGZAG" 0.40 45.00 "L" "")
 (command "COLOR" "BYLAYER")
 (command "LAYER" "S" "CGBLITHCD" "")
 (setq p1 (list 113.00 1506.85) p2 (list 114.35 1502.65))
 (command "LINE" p1 p2 "")
 (setq p1 (list 114.50 1502.27) p2 (list 0.00 0.00))
 (command "TEXT" "J" "ML" p1   0.75  0.00 "023")
 (command "LAYER" "S" "CGBTHK" "")
 (setq p1 (list 119.00 1502.27) p2 (list 0.00 0.00))
 (command "TEXT" "J" "ML" p1   0.75  0.00 "0.43")
 (command "LAYER" "S" "CGBHZID" "")
 (setq p1 (list 123.50 1502.27) p2 (list 0.00 0.00))
 (command "TEXT" "J" "ML" p1   0.75  0.00 "")
 (setq p1 (list 125.75 1502.27) p2 (list 0.00 0.00))
 (command "TEXT" "J" "ML" p1   0.75  0.00 "6000")
 (command "LAYER" "S" "CGBLITHTXT" "")
 (setq p1 (list 129.50 1502.27) p2 (list 0.00 0.00))
 (command "TEXT" "J" "ML" p1   0.75  0.00 "COAL W/BONE STKS")
 (command "LAYER" "S" "CGBCMNT" "")
 (setq p1 (list 149.75 1502.27) p2 (list 0.00 0.00))
 (command "TEXT" "J" "ML" p1   0.75  0.00 "")
 (command "LAYER" "S" "CGBMAIN" "")
 (setq p1 (list 107.00 1506.63) p2 (list 113.00 1506.63) p3 (list 113.00 1504.79) p4 (list 107.00 1504.79))
 (command "PLINE" p1 p2 p3 p4 "c")
 (command "COLOR" "BLUE")
 (command "SOLID" p1 p2 p4 p3 "")
 (command "COLOR" "BYLAYER")
 (command "LAYER" "S" "CGBLITHCD" "")
 (setq p1 (list 113.00 1505.71) p2 (list 114.35 1501.40))
 (command "LINE" p1 p2 "")
 (setq p1 (list 114.50 1501.02) p2 (list 0.00 0.00))
 (command "TEXT" "J" "ML" p1   0.75  0.00 "021")
 (command "LAYER" "S" "CGBTHK" "")
 (setq p1 (list 119.00 1501.02) p2 (list 0.00 0.00))
 (command "TEXT" "J" "ML" p1   0.75  0.00 "1.84")
 (command "LAYER" "S" "CGBHZID" "")
 (setq p1 (list 123.50 1501.02) p2 (list 0.00 0.00))
 (command "TEXT" "J" "ML" p1   0.75  0.00 "")
 (setq p1 (list 125.75 1501.02) p2 (list 0.00 0.00))
 (command "TEXT" "J" "ML" p1   0.75  0.00 "6000")
 (command "LAYER" "S" "CGBLITHTXT" "")
 (setq p1 (list 129.50 1501.02) p2 (list 0.00 0.00))
 (command "TEXT" "J" "ML" p1   0.75  0.00 "COMMON BANDED COAL")
 (command "LAYER" "S" "CGBCMNT" "")
 (setq p1 (list 149.75 1501.02) p2 (list 0.00 0.00))
 (command "TEXT" "J" "ML" p1   0.75  0.00 "VIT W/PYRT")
 (command "LAYER" "S" "CGBMAIN" "")
 (setq p1 (list 107.00 1504.79) p2 (list 113.00 1504.79) p3 (list 113.00 1504.70) p4 (list 107.00 1504.70))
 (command "PLINE" p1 p2 p3 p4 "c")
 (command "HATCH" "ZIGZAG" 5.00 0.00 "L" "")
 (command "COLOR" "BYLAYER")
 (command "LAYER" "S" "CGBLITHCD" "")
 (setq p1 (list 113.00 1504.75) p2 (list 114.35 1500.15))
 (command "LINE" p1 p2 "")
 (setq p1 (list 114.50 1499.77) p2 (list 0.00 0.00))
 (command "TEXT" "J" "ML" p1   0.75  0.00 "037")
 (command "LAYER" "S" "CGBTHK" "")
 (setq p1 (list 119.00 1499.77) p2 (list 0.00 0.00))
 (command "TEXT" "J" "ML" p1   0.75  0.00 "0.09")
 (command "LAYER" "S" "CGBHZID" "")
 (setq p1 (list 123.50 1499.77) p2 (list 0.00 0.00))
 (command "TEXT" "J" "ML" p1   0.75  0.00 "")
 (setq p1 (list 125.75 1499.77) p2 (list 0.00 0.00))
 (command "TEXT" "J" "ML" p1   0.75  0.00 "5951")
 (command "LAYER" "S" "CGBLITHTXT" "")
 (setq p1 (list 129.50 1499.77) p2 (list 0.00 0.00))
 (command "TEXT" "J" "ML" p1   0.75  0.00 "BONE W/SH LAYERS")
 (command "LAYER" "S" "CGBCMNT" "")
 (setq p1 (list 149.75 1499.77) p2 (list 0.00 0.00))
 (command "TEXT" "J" "ML" p1   0.75  0.00 "DULL")
 (command "LAYER" "S" "CGBMAIN" "")
 (setq p1 (list 107.00 1504.70) p2 (list 113.00 1504.70) p3 (list 113.00 1504.03) p4 (list 107.00 1504.03))
 (command "PLINE" p1 p2 p3 p4 "c")
 (command "HATCH" "ZIGZAG" 4.00 0.00 "L" "")
 (command "COLOR" "BYLAYER")
 (command "LAYER" "S" "CGBLITHCD" "")
 (setq p1 (list 113.00 1504.37) p2 (list 114.35 1498.90))
 (command "LINE" p1 p2 "")
 (setq p1 (list 114.50 1498.52) p2 (list 0.00 0.00))
 (command "TEXT" "J" "ML" p1   0.75  0.00 "123")
 (command "LAYER" "S" "CGBTHK" "")
 (setq p1 (list 119.00 1498.52) p2 (list 0.00 0.00))
 (command "TEXT" "J" "ML" p1   0.75  0.00 "0.67")
 (command "LAYER" "S" "CGBHZID" "")
 (setq p1 (list 123.50 1498.52) p2 (list 0.00 0.00))
 (command "TEXT" "J" "ML" p1   0.75  0.00 "")
 (setq p1 (list 125.75 1498.52) p2 (list 0.00 0.00))
 (command "TEXT" "J" "ML" p1   0.75  0.00 "5951")
 (command "LAYER" "S" "CGBLITHTXT" "")
 (setq p1 (list 129.50 1498.52) p2 (list 0.00 0.00))
 (command "TEXT" "J" "ML" p1   0.75  0.00 "DRK GRY SH W/COAL STKS")
 (command "LAYER" "S" "CGBCMNT" "")
 (setq p1 (list 149.75 1498.52) p2 (list 0.00 0.00))
 (command "TEXT" "J" "ML" p1   0.75  0.00 "FEW COAL BNDS")
 (command "LAYER" "S" "CGBMAIN" "")
 (setq p1 (list 107.00 1504.03) p2 (list 113.00 1504.03) p3 (list 113.00 1503.58) p4 (list 107.00 1503.58))
 (command "PLINE" p1 p2 p3 p4 "c")
 (command "COLOR" "BLUE")
 (command "SOLID" p1 p2 p4 p3 "")
 (command "COLOR" "BYLAYER")
 (command "LAYER" "S" "CGBLITHCD" "")
 (setq p1 (list 113.00 1503.81) p2 (list 114.35 1497.65))
 (command "LINE" p1 p2 "")
 (setq p1 (list 114.50 1497.27) p2 (list 0.00 0.00))
 (command "TEXT" "J" "ML" p1   0.75  0.00 "021")
 (command "LAYER" "S" "CGBTHK" "")
 (setq p1 (list 119.00 1497.27) p2 (list 0.00 0.00))
 (command "TEXT" "J" "ML" p1   0.75  0.00 "0.45")
 (command "LAYER" "S" "CGBHZID" "")
 (setq p1 (list 123.50 1497.27) p2 (list 0.00 0.00))
 (command "TEXT" "J" "ML" p1   0.75  0.00 "")
 (setq p1 (list 125.75 1497.27) p2 (list 0.00 0.00))
 (command "TEXT" "J" "ML" p1   0.75  0.00 "5500")
 (command "LAYER" "S" "CGBLITHTXT" "")
 (setq p1 (list 129.50 1497.27) p2 (list 0.00 0.00))
 (command "TEXT" "J" "ML" p1   0.75  0.00 "COMMON BANDED COAL")
 (command "LAYER" "S" "CGBCMNT" "")
 (setq p1 (list 149.75 1497.27) p2 (list 0.00 0.00))
 (command "TEXT" "J" "ML" p1   0.75  0.00 "VIT W/ PYRT")
 (command "LAYER" "S" "CGBMAIN" "")
 (setq p1 (list 107.00 1503.58) p2 (list 113.00 1503.58) p3 (list 113.00 1503.12) p4 (list 107.00 1503.12))
 (command "PLINE" p1 p2 p3 p4 "c")
 (command "HATCH" "ZIGZAG" 0.40 45.00 "L" "")
 (command "COLOR" "BYLAYER")
 (command "LAYER" "S" "CGBLITHCD" "")
 (setq p1 (list 113.00 1503.35) p2 (list 114.35 1496.40))
 (command "LINE" p1 p2 "")
 (setq p1 (list 114.50 1496.02) p2 (list 0.00 0.00))
 (command "TEXT" "J" "ML" p1   0.75  0.00 "022")
 (command "LAYER" "S" "CGBTHK" "")
 (setq p1 (list 119.00 1496.02) p2 (list 0.00 0.00))
 (command "TEXT" "J" "ML" p1   0.75  0.00 "0.46")
 (command "LAYER" "S" "CGBHZID" "")
 (setq p1 (list 123.50 1496.02) p2 (list 0.00 0.00))
 (command "TEXT" "J" "ML" p1   0.75  0.00 "")
 (setq p1 (list 125.75 1496.02) p2 (list 0.00 0.00))
 (command "TEXT" "J" "ML" p1   0.75  0.00 "5500")
 (command "LAYER" "S" "CGBLITHTXT" "")
 (setq p1 (list 129.50 1496.02) p2 (list 0.00 0.00))
 (command "TEXT" "J" "ML" p1   0.75  0.00 "COAL W/BONE LAYERS")
 (command "LAYER" "S" "CGBCMNT" "")
 (setq p1 (list 149.75 1496.02) p2 (list 0.00 0.00))
 (command "TEXT" "J" "ML" p1   0.75  0.00 "DULL W/ VIT")
 (command "LAYER" "S" "CGBMAIN" "")
 (setq p1 (list 107.00 1503.12) p2 (list 113.00 1503.12) p3 (list 113.00 1501.98) p4 (list 107.00 1501.98))
 (command "PLINE" p1 p2 p3 p4 "c")
 (command "HATCH" "ZIGZAG" 0.40 45.00 "L" "")
 (command "COLOR" "BYLAYER")
 (command "LAYER" "S" "CGBLITHCD" "")
 (setq p1 (list 113.00 1502.55) p2 (list 114.35 1495.15))
 (command "LINE" p1 p2 "")
 (setq p1 (list 114.50 1494.77) p2 (list 0.00 0.00))
 (command "TEXT" "J" "ML" p1   0.75  0.00 "023")
 (command "LAYER" "S" "CGBTHK" "")
 (setq p1 (list 119.00 1494.77) p2 (list 0.00 0.00))
 (command "TEXT" "J" "ML" p1   0.75  0.00 "1.14")
 (command "LAYER" "S" "CGBHZID" "")
 (setq p1 (list 123.50 1494.77) p2 (list 0.00 0.00))
 (command "TEXT" "J" "ML" p1   0.75  0.00 "")
 (setq p1 (list 125.75 1494.77) p2 (list 0.00 0.00))
 (command "TEXT" "J" "ML" p1   0.75  0.00 "5500")
 (command "LAYER" "S" "CGBLITHTXT" "")
 (setq p1 (list 129.50 1494.77) p2 (list 0.00 0.00))
 (command "TEXT" "J" "ML" p1   0.75  0.00 "COAL W/BONE STKS")
 (command "LAYER" "S" "CGBCMNT" "")
 (setq p1 (list 149.75 1494.77) p2 (list 0.00 0.00))
 (command "TEXT" "J" "ML" p1   0.75  0.00 "BRIGHT W/BONE")
 (command "LAYER" "S" "CGBMAIN" "")
 (setq p1 (list 107.00 1501.98) p2 (list 113.00 1501.98) p3 (list 113.00 1501.83) p4 (list 107.00 1501.83))
 (command "PLINE" p1 p2 p3 p4 "c")
 (command "HATCH" "ZIGZAG" 5.00 0.00 "L" "")
 (command "COLOR" "BYLAYER")
 (command "LAYER" "S" "CGBLITHCD" "")
 (setq p1 (list 113.00 1501.91) p2 (list 114.35 1493.90))
 (command "LINE" p1 p2 "")
 (setq p1 (list 114.50 1493.52) p2 (list 0.00 0.00))
 (command "TEXT" "J" "ML" p1   0.75  0.00 "032")
 (command "LAYER" "S" "CGBTHK" "")
 (setq p1 (list 119.00 1493.52) p2 (list 0.00 0.00))
 (command "TEXT" "J" "ML" p1   0.75  0.00 "0.15")
 (command "LAYER" "S" "CGBHZID" "")
 (setq p1 (list 123.50 1493.52) p2 (list 0.00 0.00))
 (command "TEXT" "J" "ML" p1   0.75  0.00 "")
 (setq p1 (list 125.75 1493.52) p2 (list 0.00 0.00))
 (command "TEXT" "J" "ML" p1   0.75  0.00 "5500")
 (command "LAYER" "S" "CGBLITHTXT" "")
 (setq p1 (list 129.50 1493.52) p2 (list 0.00 0.00))
 (command "TEXT" "J" "ML" p1   0.75  0.00 "BONE W/COAL LAYERS")
 (command "LAYER" "S" "CGBCMNT" "")
 (setq p1 (list 149.75 1493.52) p2 (list 0.00 0.00))
 (command "TEXT" "J" "ML" p1   0.75  0.00 "DULL W/ VIT")
 (command "LAYER" "S" "CGBMAIN" "")
 (setq p1 (list 107.00 1501.83) p2 (list 113.00 1501.83) p3 (list 113.00 1501.05) p4 (list 107.00 1501.05))
 (command "PLINE" p1 p2 p3 p4 "c")
 (command "COLOR" "BLUE")
 (command "SOLID" p1 p2 p4 p3 "")
 (command "COLOR" "BYLAYER")
 (command "LAYER" "S" "CGBLITHCD" "")
 (setq p1 (list 113.00 1501.44) p2 (list 114.35 1492.65))
 (command "LINE" p1 p2 "")
 (setq p1 (list 114.50 1492.27) p2 (list 0.00 0.00))
 (command "TEXT" "J" "ML" p1   0.75  0.00 "021")
 (command "LAYER" "S" "CGBTHK" "")
 (setq p1 (list 119.00 1492.27) p2 (list 0.00 0.00))
 (command "TEXT" "J" "ML" p1   0.75  0.00 "0.78")
 (command "LAYER" "S" "CGBHZID" "")
 (setq p1 (list 123.50 1492.27) p2 (list 0.00 0.00))
 (command "TEXT" "J" "ML" p1   0.75  0.00 "")
 (setq p1 (list 125.75 1492.27) p2 (list 0.00 0.00))
 (command "TEXT" "J" "ML" p1   0.75  0.00 "5500")
 (command "LAYER" "S" "CGBLITHTXT" "")
 (setq p1 (list 129.50 1492.27) p2 (list 0.00 0.00))
 (command "TEXT" "J" "ML" p1   0.75  0.00 "COMMON BANDED COAL")
 (command "LAYER" "S" "CGBCMNT" "")
 (setq p1 (list 149.75 1492.27) p2 (list 0.00 0.00))
 (command "TEXT" "J" "ML" p1   0.75  0.00 "BONEY @ BASE")
 (command "LAYER" "S" "CGBMAIN" "")
 (setq p1 (list 107.00 1501.05) p2 (list 113.00 1501.05) p3 (list 113.00 1500.00) p4 (list 107.00 1500.00))
 (command "PLINE" p1 p2 p3 p4 "c")
 (command "HATCH" "ZIGZAG" 0.80 0.00 "L" "")
 (command "COLOR" "BYLAYER")
 (command "LAYER" "S" "CGBLITHCD" "")
 (setq p1 (list 113.00 1500.53) p2 (list 114.35 1491.40))
 (command "LINE" p1 p2 "")
 (setq p1 (list 114.50 1491.02) p2 (list 0.00 0.00))
 (command "TEXT" "J" "ML" p1   0.75  0.00 "029")
 (command "LAYER" "S" "CGBTHK" "")
 (setq p1 (list 119.00 1491.02) p2 (list 0.00 0.00))
 (command "TEXT" "J" "ML" p1   0.75  0.00 "1.05")
 (command "LAYER" "S" "CGBHZID" "")
 (setq p1 (list 123.50 1491.02) p2 (list 0.00 0.00))
 (command "TEXT" "J" "ML" p1   0.75  0.00 "")
 (setq p1 (list 125.75 1491.02) p2 (list 0.00 0.00))
 (command "TEXT" "J" "ML" p1   0.75  0.00 "5500")
 (command "LAYER" "S" "CGBLITHTXT" "")
 (setq p1 (list 129.50 1491.02) p2 (list 0.00 0.00))
 (command "TEXT" "J" "ML" p1   0.75  0.00 "COAL W/PYRITE STKS")
 (command "LAYER" "S" "CGBCMNT" "")
 (setq p1 (list 149.75 1491.02) p2 (list 0.00 0.00))
 (command "TEXT" "J" "ML" p1   0.75  0.00 "PYRT @ BASE")
 (command "LAYER" "S" "CGBMAIN" "")
 (setq p1 (list 107.00 1500.00) p2 (list 113.00 1500.00) p3 (list 113.00 1499.80) p4 (list 107.00 1499.80))
 (command "PLINE" p1 p2 p3 p4 "c")
 (command "HATCH" "ZIGZAG" 0.25 0.00 "L" "")
 (command "COLOR" "BYLAYER")
 (command "LAYER" "S" "CGBLITHCD" "")
 (setq p1 (list 113.00 1499.90) p2 (list 114.35 1490.15))
 (command "LINE" p1 p2 "")
 (setq p1 (list 114.50 1489.77) p2 (list 0.00 0.00))
 (command "TEXT" "J" "ML" p1   0.75  0.00 "117")
 (command "LAYER" "S" "CGBTHK" "")
 (setq p1 (list 119.00 1489.77) p2 (list 0.00 0.00))
 (command "TEXT" "J" "ML" p1   0.75  0.00 "0.20")
 (command "LAYER" "S" "CGBHZID" "")
 (setq p1 (list 123.50 1489.77) p2 (list 0.00 0.00))
 (command "TEXT" "J" "ML" p1   0.75  0.00 "")
 (setq p1 (list 125.75 1489.77) p2 (list 0.00 0.00))
 (command "TEXT" "J" "ML" p1   0.75  0.00 "5451")
 (command "LAYER" "S" "CGBLITHTXT" "")
 (setq p1 (list 129.50 1489.77) p2 (list 0.00 0.00))
 (command "TEXT" "J" "ML" p1   0.75  0.00 "BLK FIRECLAY")
 (command "LAYER" "S" "CGBCMNT" "")
 (setq p1 (list 149.75 1489.77) p2 (list 0.00 0.00))
 (command "TEXT" "J" "ML" p1   0.75  0.00 "M SFT")
 (command "LAYER" "S" "CGBMAIN" "")
 (setq p1 (list 107.00 1499.80) p2 (list 113.00 1499.80) p3 (list 113.00 1499.60) p4 (list 107.00 1499.60))
 (command "PLINE" p1 p2 p3 p4 "c")
 (command "HATCH" "ZIGZAG" 0.25 0.00 "L" "")
 (command "COLOR" "BYLAYER")
 (command "LAYER" "S" "CGBLITHCD" "")
 (setq p1 (list 113.00 1499.70) p2 (list 114.35 1488.90))
 (command "LINE" p1 p2 "")
 (setq p1 (list 114.50 1488.52) p2 (list 0.00 0.00))
 (command "TEXT" "J" "ML" p1   0.75  0.00 "117")
 (command "LAYER" "S" "CGBTHK" "")
 (setq p1 (list 119.00 1488.52) p2 (list 0.00 0.00))
 (command "TEXT" "J" "ML" p1   0.75  0.00 "0.20")
 (command "LAYER" "S" "CGBHZID" "")
 (setq p1 (list 123.50 1488.52) p2 (list 0.00 0.00))
 (command "TEXT" "J" "ML" p1   0.75  0.00 "")
 (setq p1 (list 125.75 1488.52) p2 (list 0.00 0.00))
 (command "TEXT" "J" "ML" p1   0.75  0.00 "5451")
 (command "LAYER" "S" "CGBLITHTXT" "")
 (setq p1 (list 129.50 1488.52) p2 (list 0.00 0.00))
 (command "TEXT" "J" "ML" p1   0.75  0.00 "BLK FIRECLAY")
 (command "LAYER" "S" "CGBCMNT" "")
 (setq p1 (list 149.75 1488.52) p2 (list 0.00 0.00))
 (command "TEXT" "J" "ML" p1   0.75  0.00 "M SFT")
 (command "LAYER" "S" "CGBMAIN" "")
 (setq p1 (list 107.00 1499.60) p2 (list 113.00 1499.60) p3 (list 113.00 1499.50) p4 (list 107.00 1499.50))
 (command "PLINE" p1 p2 p3 p4 "c")
 (command "HATCH" "ZIGZAG" 5.00 0.00 "L" "")
 (command "COLOR" "BYLAYER")
 (command "LAYER" "S" "CGBLITHCD" "")
 (setq p1 (list 113.00 1499.55) p2 (list 114.35 1487.65))
 (command "LINE" p1 p2 "")
 (setq p1 (list 114.50 1487.27) p2 (list 0.00 0.00))
 (command "TEXT" "J" "ML" p1   0.75  0.00 "137")
 (command "LAYER" "S" "CGBTHK" "")
 (setq p1 (list 119.00 1487.27) p2 (list 0.00 0.00))
 (command "TEXT" "J" "ML" p1   0.75  0.00 "0.10")
 (command "LAYER" "S" "CGBHZID" "")
 (setq p1 (list 123.50 1487.27) p2 (list 0.00 0.00))
 (command "TEXT" "J" "ML" p1   0.75  0.00 "")
 (setq p1 (list 125.75 1487.27) p2 (list 0.00 0.00))
 (command "TEXT" "J" "ML" p1   0.75  0.00 "5451")
 (command "LAYER" "S" "CGBLITHTXT" "")
 (setq p1 (list 129.50 1487.27) p2 (list 0.00 0.00))
 (command "TEXT" "J" "ML" p1   0.75  0.00 "LT GRY GRN FIRECLAY")
 (command "LAYER" "S" "CGBCMNT" "")
 (setq p1 (list 149.75 1487.27) p2 (list 0.00 0.00))
 (command "TEXT" "J" "ML" p1   0.75  0.00 "V SFT")
 (command "LAYER" "S" "CGBMAIN" "")
 (setq p1 (list 107.00 1499.50) p2 (list 113.00 1499.50) p3 (list 113.00 1499.40) p4 (list 107.00 1499.40))
 (command "PLINE" p1 p2 p3 p4 "c")
 (command "HATCH" "ZIGZAG" 0.25 0.00 "L" "")
 (command "COLOR" "BYLAYER")
 (command "LAYER" "S" "CGBLITHCD" "")
 (setq p1 (list 113.00 1499.45) p2 (list 114.35 1486.40))
 (command "LINE" p1 p2 "")
 (setq p1 (list 114.50 1486.02) p2 (list 0.00 0.00))
 (command "TEXT" "J" "ML" p1   0.75  0.00 "127")
 (command "LAYER" "S" "CGBTHK" "")
 (setq p1 (list 119.00 1486.02) p2 (list 0.00 0.00))
 (command "TEXT" "J" "ML" p1   0.75  0.00 "0.10")
 (command "LAYER" "S" "CGBHZID" "")
 (setq p1 (list 123.50 1486.02) p2 (list 0.00 0.00))
 (command "TEXT" "J" "ML" p1   0.75  0.00 "")
 (setq p1 (list 125.75 1486.02) p2 (list 0.00 0.00))
 (command "TEXT" "J" "ML" p1   0.75  0.00 "5451")
 (command "LAYER" "S" "CGBLITHTXT" "")
 (setq p1 (list 129.50 1486.02) p2 (list 0.00 0.00))
 (command "TEXT" "J" "ML" p1   0.75  0.00 "DRK GRY FIRECLAY")
 (command "LAYER" "S" "CGBCMNT" "")
 (setq p1 (list 149.75 1486.02) p2 (list 0.00 0.00))
 (command "TEXT" "J" "ML" p1   0.75  0.00 "SFT, DRK")
 (command "LAYER" "S" "CGBMAIN" "")
 (setq p1 (list 107.00 1499.40) p2 (list 113.00 1499.40) p3 (list 113.00 1499.10) p4 (list 107.00 1499.10))
 (command "PLINE" p1 p2 p3 p4 "c")
 (command "HATCH" "ZIGZAG" 0.25 0.00 "L" "")
 (command "COLOR" "BYLAYER")
 (command "LAYER" "S" "CGBLITHCD" "")
 (setq p1 (list 113.00 1499.25) p2 (list 114.35 1485.15))
 (command "LINE" p1 p2 "")
 (setq p1 (list 114.50 1484.77) p2 (list 0.00 0.00))
 (command "TEXT" "J" "ML" p1   0.75  0.00 "127")
 (command "LAYER" "S" "CGBTHK" "")
 (setq p1 (list 119.00 1484.77) p2 (list 0.00 0.00))
 (command "TEXT" "J" "ML" p1   0.75  0.00 "0.30")
 (command "LAYER" "S" "CGBHZID" "")
 (setq p1 (list 123.50 1484.77) p2 (list 0.00 0.00))
 (command "TEXT" "J" "ML" p1   0.75  0.00 "")
 (setq p1 (list 125.75 1484.77) p2 (list 0.00 0.00))
 (command "TEXT" "J" "ML" p1   0.75  0.00 "5451")
 (command "LAYER" "S" "CGBLITHTXT" "")
 (setq p1 (list 129.50 1484.77) p2 (list 0.00 0.00))
 (command "TEXT" "J" "ML" p1   0.75  0.00 "DRK GRY FIRECLAY")
 (command "LAYER" "S" "CGBCMNT" "")
 (setq p1 (list 149.75 1484.77) p2 (list 0.00 0.00))
 (command "TEXT" "J" "ML" p1   0.75  0.00 "M SFT")
 (command "LAYER" "S" "CGBMAIN" "")
 (setq p1 (list 107.00 1499.10) p2 (list 113.00 1499.10) p3 (list 113.00 1496.80) p4 (list 107.00 1496.80))
 (command "PLINE" p1 p2 p3 p4 "c")
 (command "HATCH" "ZIGZAG" 0.25 0.00 "L" "")
 (command "COLOR" "BYLAYER")
 (command "LAYER" "S" "CGBLITHCD" "")
 (setq p1 (list 113.00 1497.95) p2 (list 114.35 1483.90))
 (command "LINE" p1 p2 "")
 (setq p1 (list 114.50 1483.52) p2 (list 0.00 0.00))
 (command "TEXT" "J" "ML" p1   0.75  0.00 "127")
 (command "LAYER" "S" "CGBTHK" "")
 (setq p1 (list 119.00 1483.52) p2 (list 0.00 0.00))
 (command "TEXT" "J" "ML" p1   0.75  0.00 "2.30")
 (command "LAYER" "S" "CGBHZID" "")
 (setq p1 (list 123.50 1483.52) p2 (list 0.00 0.00))
 (command "TEXT" "J" "ML" p1   0.75  0.00 "")
 (setq p1 (list 125.75 1483.52) p2 (list 0.00 0.00))
 (command "TEXT" "J" "ML" p1   0.75  0.00 "5451")
 (command "LAYER" "S" "CGBLITHTXT" "")
 (setq p1 (list 129.50 1483.52) p2 (list 0.00 0.00))
 (command "TEXT" "J" "ML" p1   0.75  0.00 "DRK GRY FIRECLAY")
 (command "LAYER" "S" "CGBCMNT" "")
 (setq p1 (list 149.75 1483.52) p2 (list 0.00 0.00))
 (command "TEXT" "J" "ML" p1   0.75  0.00 "")
 (command "LAYER" "S" "CGBMAIN" "")
 (setq p1 (list 107.00 1496.80) p2 (list 113.00 1496.80) p3 (list 113.00 1496.50) p4 (list 107.00 1496.50))
 (command "PLINE" p1 p2 p3 p4 "c")
 (command "HATCH" "ZIGZAG" 4.00 0.00 "L" "")
 (command "COLOR" "BYLAYER")
 (command "LAYER" "S" "CGBLITHCD" "")
 (setq p1 (list 113.00 1496.65) p2 (list 114.35 1482.65))
 (command "LINE" p1 p2 "")
 (setq p1 (list 114.50 1482.27) p2 (list 0.00 0.00))
 (command "TEXT" "J" "ML" p1   0.75  0.00 "115")
 (command "LAYER" "S" "CGBTHK" "")
 (setq p1 (list 119.00 1482.27) p2 (list 0.00 0.00))
 (command "TEXT" "J" "ML" p1   0.75  0.00 "0.30")
 (command "LAYER" "S" "CGBHZID" "")
 (setq p1 (list 123.50 1482.27) p2 (list 0.00 0.00))
 (command "TEXT" "J" "ML" p1   0.75  0.00 "")
 (setq p1 (list 125.75 1482.27) p2 (list 0.00 0.00))
 (command "TEXT" "J" "ML" p1   0.75  0.00 "5451")
 (command "LAYER" "S" "CGBLITHTXT" "")
 (setq p1 (list 129.50 1482.27) p2 (list 0.00 0.00))
 (command "TEXT" "J" "ML" p1   0.75  0.00 "BLK CHRND SH")
 (command "LAYER" "S" "CGBCMNT" "")
 (setq p1 (list 149.75 1482.27) p2 (list 0.00 0.00))
 (command "TEXT" "J" "ML" p1   0.75  0.00 "DRK W/LT SH N")
 (command "LAYER" "S" "CGBMAIN" "")
 (setq p1 (list 107.00 1496.50) p2 (list 113.00 1496.50) p3 (list 113.00 1496.08) p4 (list 107.00 1496.08))
 (command "PLINE" p1 p2 p3 p4 "c")
 (command "HATCH" "ZIGZAG" 2.50 90.00 "L" "")
 (command "COLOR" "BYLAYER")
 (command "LAYER" "S" "CGBLITHCD" "")
 (setq p1 (list 113.00 1496.29) p2 (list 114.35 1481.40))
 (command "LINE" p1 p2 "")
 (setq p1 (list 114.50 1481.02) p2 (list 0.00 0.00))
 (command "TEXT" "J" "ML" p1   0.75  0.00 "325")
 (command "LAYER" "S" "CGBTHK" "")
 (setq p1 (list 119.00 1481.02) p2 (list 0.00 0.00))
 (command "TEXT" "J" "ML" p1   0.75  0.00 "0.42")
 (command "LAYER" "S" "CGBHZID" "")
 (setq p1 (list 123.50 1481.02) p2 (list 0.00 0.00))
 (command "TEXT" "J" "ML" p1   0.75  0.00 "")
 (setq p1 (list 125.75 1481.02) p2 (list 0.00 0.00))
 (command "TEXT" "J" "ML" p1   0.75  0.00 "5451")
 (command "LAYER" "S" "CGBLITHTXT" "")
 (setq p1 (list 129.50 1481.02) p2 (list 0.00 0.00))
 (command "TEXT" "J" "ML" p1   0.75  0.00 "DRK GRY MASS CHRND SDY SH")
 (command "LAYER" "S" "CGBCMNT" "")
 (setq p1 (list 149.75 1481.02) p2 (list 0.00 0.00))
 (command "TEXT" "J" "ML" p1   0.75  0.00 "FLTCLAYISH")
 (command "LAYER" "S" "CGBMAIN" "")
 (setq p1 (list 107.00 1496.08) p2 (list 113.00 1496.08) p3 (list 113.00 1488.50) p4 (list 107.00 1488.50))
 (command "PLINE" p1 p2 p3 p4 "c")
 (command "HATCH" "ZIGZAG" 0.25 0.00 "L" "")
 (command "COLOR" "BYLAYER")
 (command "LAYER" "S" "CGBLITHCD" "")
 (setq p1 (list 113.00 1492.29) p2 (list 114.35 1480.15))
 (command "LINE" p1 p2 "")
 (setq p1 (list 114.50 1479.77) p2 (list 0.00 0.00))
 (command "TEXT" "J" "ML" p1   0.75  0.00 "762")
 (command "LAYER" "S" "CGBTHK" "")
 (setq p1 (list 119.00 1479.77) p2 (list 0.00 0.00))
 (command "TEXT" "J" "ML" p1   0.75  0.00 "7.58")
 (command "LAYER" "S" "CGBHZID" "")
 (setq p1 (list 123.50 1479.77) p2 (list 0.00 0.00))
 (command "TEXT" "J" "ML" p1   0.75  0.00 "")
 (setq p1 (list 125.75 1479.77) p2 (list 0.00 0.00))
 (command "TEXT" "J" "ML" p1   0.75  0.00 "5451")
 (command "LAYER" "S" "CGBLITHTXT" "")
 (setq p1 (list 129.50 1479.77) p2 (list 0.00 0.00))
 (command "TEXT" "J" "ML" p1   0.75  0.00 "HARD SH PEB CGL")
 (command "LAYER" "S" "CGBCMNT" "")
 (setq p1 (list 149.75 1479.77) p2 (list 0.00 0.00))
 (command "TEXT" "J" "ML" p1   0.75  0.00 "V HRD, FRACS")
 (command "LAYER" "S" "CGBMAIN" "")
 (setq p1 (list 107.00 1488.50) p2 (list 113.00 1488.50) p3 (list 113.00 1487.65) p4 (list 107.00 1487.65))
 (command "PLINE" p1 p2 p3 p4 "c")
 (command "HATCH" "ZIGZAG" 4.00 0.00 "L" "")
 (command "COLOR" "BYLAYER")
 (command "LAYER" "S" "CGBLITHCD" "")
 (setq p1 (list 113.00 1488.08) p2 (list 114.35 1478.90))
 (command "LINE" p1 p2 "")
 (setq p1 (list 114.50 1478.52) p2 (list 0.00 0.00))
 (command "TEXT" "J" "ML" p1   0.75  0.00 "563")
 (command "LAYER" "S" "CGBTHK" "")
 (setq p1 (list 119.00 1478.52) p2 (list 0.00 0.00))
 (command "TEXT" "J" "ML" p1   0.75  0.00 "0.85")
 (command "LAYER" "S" "CGBHZID" "")
 (setq p1 (list 123.50 1478.52) p2 (list 0.00 0.00))
 (command "TEXT" "J" "ML" p1   0.75  0.00 "")
 (setq p1 (list 125.75 1478.52) p2 (list 0.00 0.00))
 (command "TEXT" "J" "ML" p1   0.75  0.00 "5451")
 (command "LAYER" "S" "CGBLITHTXT" "")
 (setq p1 (list 129.50 1478.52) p2 (list 0.00 0.00))
 (command "TEXT" "J" "ML" p1   0.75  0.00 "HARD SS W/SH STKS")
 (command "LAYER" "S" "CGBCMNT" "")
 (setq p1 (list 149.75 1478.52) p2 (list 0.00 0.00))
 (command "TEXT" "J" "ML" p1   0.75  0.00 "V HRD, AND BE")
 (command "LAYER" "S" "CGBMAIN" "")
 (setq p1 (list 107.00 1487.65) p2 (list 113.00 1487.65) p3 (list 113.00 1479.45) p4 (list 107.00 1479.45))
 (command "PLINE" p1 p2 p3 p4 "c")
 (command "HATCH" "ZIGZAG" 4.00 0.00 "L" "")
 (command "COLOR" "BYLAYER")
 (command "LAYER" "S" "CGBLITHCD" "")
 (setq p1 (list 113.00 1483.55) p2 (list 114.35 1477.65))
 (command "LINE" p1 p2 "")
 (setq p1 (list 114.50 1477.27) p2 (list 0.00 0.00))
 (command "TEXT" "J" "ML" p1   0.75  0.00 "563")
 (command "LAYER" "S" "CGBTHK" "")
 (setq p1 (list 119.00 1477.27) p2 (list 0.00 0.00))
 (command "TEXT" "J" "ML" p1   0.75  0.00 "8.20")
 (command "LAYER" "S" "CGBHZID" "")
 (setq p1 (list 123.50 1477.27) p2 (list 0.00 0.00))
 (command "TEXT" "J" "ML" p1   0.75  0.00 "")
 (setq p1 (list 125.75 1477.27) p2 (list 0.00 0.00))
 (command "TEXT" "J" "ML" p1   0.75  0.00 "5451")
 (command "LAYER" "S" "CGBLITHTXT" "")
 (setq p1 (list 129.50 1477.27) p2 (list 0.00 0.00))
 (command "TEXT" "J" "ML" p1   0.75  0.00 "HARD SS W/SH STKS")
 (command "LAYER" "S" "CGBCMNT" "")
 (setq p1 (list 149.75 1477.27) p2 (list 0.00 0.00))
 (command "TEXT" "J" "ML" p1   0.75  0.00 "DRK SUGARY,F")
 (command "LAYER" "S" "CGBMAIN" "")
 (setq p1 (list 107.00 1479.45) p2 (list 113.00 1479.45) p3 (list 113.00 1475.95) p4 (list 107.00 1475.95))
 (command "PLINE" p1 p2 p3 p4 "c")
 (command "HATCH" "ZIGZAG" 0.25 0.00 "L" "")
 (command "COLOR" "BYLAYER")
 (command "LAYER" "S" "CGBLITHCD" "")
 (setq p1 (list 113.00 1477.70) p2 (list 114.35 1476.40))
 (command "LINE" p1 p2 "")
 (setq p1 (list 114.50 1476.02) p2 (list 0.00 0.00))
 (command "TEXT" "J" "ML" p1   0.75  0.00 "762")
 (command "LAYER" "S" "CGBTHK" "")
 (setq p1 (list 119.00 1476.02) p2 (list 0.00 0.00))
 (command "TEXT" "J" "ML" p1   0.75  0.00 "3.50")
 (command "LAYER" "S" "CGBHZID" "")
 (setq p1 (list 123.50 1476.02) p2 (list 0.00 0.00))
 (command "TEXT" "J" "ML" p1   0.75  0.00 "")
 (setq p1 (list 125.75 1476.02) p2 (list 0.00 0.00))
 (command "TEXT" "J" "ML" p1   0.75  0.00 "5451")
 (command "LAYER" "S" "CGBLITHTXT" "")
 (setq p1 (list 129.50 1476.02) p2 (list 0.00 0.00))
 (command "TEXT" "J" "ML" p1   0.75  0.00 "HARD SH PEB CGL")
 (command "LAYER" "S" "CGBCMNT" "")
 (setq p1 (list 149.75 1476.02) p2 (list 0.00 0.00))
 (command "TEXT" "J" "ML" p1   0.75  0.00 "STLYS, DRK")
 (command "LAYER" "S" "CGBMAIN" "")
 (setq p1 (list 107.00 1475.95) p2 (list 113.00 1475.95) p3 (list 113.00 1469.75) p4 (list 107.00 1469.75))
 (command "PLINE" p1 p2 p3 p4 "c")
 (command "HATCH" "ZIGZAG" 4.00 0.00 "L" "")
 (command "COLOR" "BYLAYER")
 (command "LAYER" "S" "CGBLITHCD" "")
 (setq p1 (list 113.00 1472.85) p2 (list 114.35 1472.85))
 (command "LINE" p1 p2 "")
 (setq p1 (list 114.50 1472.48) p2 (list 0.00 0.00))
 (command "TEXT" "J" "ML" p1   0.75  0.00 "564")
 (command "LAYER" "S" "CGBTHK" "")
 (setq p1 (list 119.00 1472.48) p2 (list 0.00 0.00))
 (command "TEXT" "J" "ML" p1   0.75  0.00 "6.20")
 (command "LAYER" "S" "CGBHZID" "")
 (setq p1 (list 123.50 1472.48) p2 (list 0.00 0.00))
 (command "TEXT" "J" "ML" p1   0.75  0.00 "")
 (setq p1 (list 125.75 1472.48) p2 (list 0.00 0.00))
 (command "TEXT" "J" "ML" p1   0.75  0.00 "5451")
 (command "LAYER" "S" "CGBLITHTXT" "")
 (setq p1 (list 129.50 1472.48) p2 (list 0.00 0.00))
 (command "TEXT" "J" "ML" p1   0.75  0.00 "HARD MASS SS")
 (command "LAYER" "S" "CGBCMNT" "")
 (setq p1 (list 149.75 1472.48) p2 (list 0.00 0.00))
 (command "TEXT" "J" "ML" p1   0.75  0.00 "")
 (command "LAYER" "S" "CGBMAIN" "")
 (setq p1 (list 106.50 1953.25) p2 (list 107.00 1953.25))
 (command "LINE" p1 p2 "")
 (setq p1 (list 106.13 1953.25) p2 (list 0.00 0.00))
 (command "TEXT" "J" "MR" p1   0.75  0.00 "0.00")
 (setq p1 (list 106.13 1952.13) p2 (list 0.00 0.00))
 (command "TEXT" "J" "MR" p1   0.75  0.00 "3096.37")
 (setq p1 (list 106.50 1943.25) p2 (list 107.00 1943.25))
 (command "LINE" p1 p2 "")
 (setq p1 (list 106.13 1943.25) p2 (list 0.00 0.00))
 (command "TEXT" "J" "MR" p1   0.75  0.00 "10.00")
 (setq p1 (list 106.13 1942.13) p2 (list 0.00 0.00))
 (command "TEXT" "J" "MR" p1   0.75  0.00 "3086.37")
 (setq p1 (list 106.50 1933.25) p2 (list 107.00 1933.25))
 (command "LINE" p1 p2 "")
 (setq p1 (list 106.13 1933.25) p2 (list 0.00 0.00))
 (command "TEXT" "J" "MR" p1   0.75  0.00 "20.00")
 (setq p1 (list 106.13 1932.13) p2 (list 0.00 0.00))
 (command "TEXT" "J" "MR" p1   0.75  0.00 "3076.37")
 (setq p1 (list 106.50 1923.25) p2 (list 107.00 1923.25))
 (command "LINE" p1 p2 "")
 (setq p1 (list 106.13 1923.25) p2 (list 0.00 0.00))
 (command "TEXT" "J" "MR" p1   0.75  0.00 "30.00")
 (setq p1 (list 106.13 1922.13) p2 (list 0.00 0.00))
 (command "TEXT" "J" "MR" p1   0.75  0.00 "3066.37")
 (setq p1 (list 106.50 1913.25) p2 (list 107.00 1913.25))
 (command "LINE" p1 p2 "")
 (setq p1 (list 106.13 1913.25) p2 (list 0.00 0.00))
 (command "TEXT" "J" "MR" p1   0.75  0.00 "40.00")
 (setq p1 (list 106.13 1912.13) p2 (list 0.00 0.00))
 (command "TEXT" "J" "MR" p1   0.75  0.00 "3056.37")
 (setq p1 (list 106.50 1903.25) p2 (list 107.00 1903.25))
 (command "LINE" p1 p2 "")
 (setq p1 (list 106.13 1903.25) p2 (list 0.00 0.00))
 (command "TEXT" "J" "MR" p1   0.75  0.00 "50.00")
 (setq p1 (list 106.13 1902.13) p2 (list 0.00 0.00))
 (command "TEXT" "J" "MR" p1   0.75  0.00 "3046.37")
 (setq p1 (list 106.50 1893.25) p2 (list 107.00 1893.25))
 (command "LINE" p1 p2 "")
 (setq p1 (list 106.13 1893.25) p2 (list 0.00 0.00))
 (command "TEXT" "J" "MR" p1   0.75  0.00 "60.00")
 (setq p1 (list 106.13 1892.13) p2 (list 0.00 0.00))
 (command "TEXT" "J" "MR" p1   0.75  0.00 "3036.37")
 (setq p1 (list 106.50 1883.25) p2 (list 107.00 1883.25))
 (command "LINE" p1 p2 "")
 (setq p1 (list 106.13 1883.25) p2 (list 0.00 0.00))
 (command "TEXT" "J" "MR" p1   0.75  0.00 "70.00")
 (setq p1 (list 106.13 1882.13) p2 (list 0.00 0.00))
 (command "TEXT" "J" "MR" p1   0.75  0.00 "3026.37")
 (setq p1 (list 106.50 1873.25) p2 (list 107.00 1873.25))
 (command "LINE" p1 p2 "")
 (setq p1 (list 106.13 1873.25) p2 (list 0.00 0.00))
 (command "TEXT" "J" "MR" p1   0.75  0.00 "80.00")
 (setq p1 (list 106.13 1872.13) p2 (list 0.00 0.00))
 (command "TEXT" "J" "MR" p1   0.75  0.00 "3016.37")
 (setq p1 (list 106.50 1863.25) p2 (list 107.00 1863.25))
 (command "LINE" p1 p2 "")
 (setq p1 (list 106.13 1863.25) p2 (list 0.00 0.00))
 (command "TEXT" "J" "MR" p1   0.75  0.00 "90.00")
 (setq p1 (list 106.13 1862.13) p2 (list 0.00 0.00))
 (command "TEXT" "J" "MR" p1   0.75  0.00 "3006.37")
 (setq p1 (list 106.50 1853.25) p2 (list 107.00 1853.25))
 (command "LINE" p1 p2 "")
 (setq p1 (list 106.13 1853.25) p2 (list 0.00 0.00))
 (command "TEXT" "J" "MR" p1   0.75  0.00 "100.00")
 (setq p1 (list 106.13 1852.13) p2 (list 0.00 0.00))
 (command "TEXT" "J" "MR" p1   0.75  0.00 "2996.37")
 (setq p1 (list 106.50 1843.25) p2 (list 107.00 1843.25))
 (command "LINE" p1 p2 "")
 (setq p1 (list 106.13 1843.25) p2 (list 0.00 0.00))
 (command "TEXT" "J" "MR" p1   0.75  0.00 "110.00")
 (setq p1 (list 106.13 1842.13) p2 (list 0.00 0.00))
 (command "TEXT" "J" "MR" p1   0.75  0.00 "2986.37")
 (setq p1 (list 106.50 1833.25) p2 (list 107.00 1833.25))
 (command "LINE" p1 p2 "")
 (setq p1 (list 106.13 1833.25) p2 (list 0.00 0.00))
 (command "TEXT" "J" "MR" p1   0.75  0.00 "120.00")
 (setq p1 (list 106.13 1832.13) p2 (list 0.00 0.00))
 (command "TEXT" "J" "MR" p1   0.75  0.00 "2976.37")
 (setq p1 (list 106.50 1823.25) p2 (list 107.00 1823.25))
 (command "LINE" p1 p2 "")
 (setq p1 (list 106.13 1823.25) p2 (list 0.00 0.00))
 (command "TEXT" "J" "MR" p1   0.75  0.00 "130.00")
 (setq p1 (list 106.13 1822.13) p2 (list 0.00 0.00))
 (command "TEXT" "J" "MR" p1   0.75  0.00 "2966.37")
 (setq p1 (list 106.50 1813.25) p2 (list 107.00 1813.25))
 (command "LINE" p1 p2 "")
 (setq p1 (list 106.13 1813.25) p2 (list 0.00 0.00))
 (command "TEXT" "J" "MR" p1   0.75  0.00 "140.00")
 (setq p1 (list 106.13 1812.13) p2 (list 0.00 0.00))
 (command "TEXT" "J" "MR" p1   0.75  0.00 "2956.37")
 (setq p1 (list 106.50 1803.25) p2 (list 107.00 1803.25))
 (command "LINE" p1 p2 "")
 (setq p1 (list 106.13 1803.25) p2 (list 0.00 0.00))
 (command "TEXT" "J" "MR" p1   0.75  0.00 "150.00")
 (setq p1 (list 106.13 1802.13) p2 (list 0.00 0.00))
 (command "TEXT" "J" "MR" p1   0.75  0.00 "2946.37")
 (setq p1 (list 106.50 1793.25) p2 (list 107.00 1793.25))
 (command "LINE" p1 p2 "")
 (setq p1 (list 106.13 1793.25) p2 (list 0.00 0.00))
 (command "TEXT" "J" "MR" p1   0.75  0.00 "160.00")
 (setq p1 (list 106.13 1792.13) p2 (list 0.00 0.00))
 (command "TEXT" "J" "MR" p1   0.75  0.00 "2936.37")
 (setq p1 (list 106.50 1783.25) p2 (list 107.00 1783.25))
 (command "LINE" p1 p2 "")
 (setq p1 (list 106.13 1783.25) p2 (list 0.00 0.00))
 (command "TEXT" "J" "MR" p1   0.75  0.00 "170.00")
 (setq p1 (list 106.13 1782.13) p2 (list 0.00 0.00))
 (command "TEXT" "J" "MR" p1   0.75  0.00 "2926.37")
 (setq p1 (list 106.50 1773.25) p2 (list 107.00 1773.25))
 (command "LINE" p1 p2 "")
 (setq p1 (list 106.13 1773.25) p2 (list 0.00 0.00))
 (command "TEXT" "J" "MR" p1   0.75  0.00 "180.00")
 (setq p1 (list 106.13 1772.13) p2 (list 0.00 0.00))
 (command "TEXT" "J" "MR" p1   0.75  0.00 "2916.37")
 (setq p1 (list 106.50 1763.25) p2 (list 107.00 1763.25))
 (command "LINE" p1 p2 "")
 (setq p1 (list 106.13 1763.25) p2 (list 0.00 0.00))
 (command "TEXT" "J" "MR" p1   0.75  0.00 "190.00")
 (setq p1 (list 106.13 1762.13) p2 (list 0.00 0.00))
 (command "TEXT" "J" "MR" p1   0.75  0.00 "2906.37")
 (setq p1 (list 106.50 1753.25) p2 (list 107.00 1753.25))
 (command "LINE" p1 p2 "")
 (setq p1 (list 106.13 1753.25) p2 (list 0.00 0.00))
 (command "TEXT" "J" "MR" p1   0.75  0.00 "200.00")
 (setq p1 (list 106.13 1752.13) p2 (list 0.00 0.00))
 (command "TEXT" "J" "MR" p1   0.75  0.00 "2896.37")
 (setq p1 (list 106.50 1743.25) p2 (list 107.00 1743.25))
 (command "LINE" p1 p2 "")
 (setq p1 (list 106.13 1743.25) p2 (list 0.00 0.00))
 (command "TEXT" "J" "MR" p1   0.75  0.00 "210.00")
 (setq p1 (list 106.13 1742.13) p2 (list 0.00 0.00))
 (command "TEXT" "J" "MR" p1   0.75  0.00 "2886.37")
 (setq p1 (list 106.50 1733.25) p2 (list 107.00 1733.25))
 (command "LINE" p1 p2 "")
 (setq p1 (list 106.13 1733.25) p2 (list 0.00 0.00))
 (command "TEXT" "J" "MR" p1   0.75  0.00 "220.00")
 (setq p1 (list 106.13 1732.13) p2 (list 0.00 0.00))
 (command "TEXT" "J" "MR" p1   0.75  0.00 "2876.37")
 (setq p1 (list 106.50 1723.25) p2 (list 107.00 1723.25))
 (command "LINE" p1 p2 "")
 (setq p1 (list 106.13 1723.25) p2 (list 0.00 0.00))
 (command "TEXT" "J" "MR" p1   0.75  0.00 "230.00")
 (setq p1 (list 106.13 1722.13) p2 (list 0.00 0.00))
 (command "TEXT" "J" "MR" p1   0.75  0.00 "2866.37")
 (setq p1 (list 106.50 1713.25) p2 (list 107.00 1713.25))
 (command "LINE" p1 p2 "")
 (setq p1 (list 106.13 1713.25) p2 (list 0.00 0.00))
 (command "TEXT" "J" "MR" p1   0.75  0.00 "240.00")
 (setq p1 (list 106.13 1712.13) p2 (list 0.00 0.00))
 (command "TEXT" "J" "MR" p1   0.75  0.00 "2856.37")
 (setq p1 (list 106.50 1703.25) p2 (list 107.00 1703.25))
 (command "LINE" p1 p2 "")
 (setq p1 (list 106.13 1703.25) p2 (list 0.00 0.00))
 (command "TEXT" "J" "MR" p1   0.75  0.00 "250.00")
 (setq p1 (list 106.13 1702.13) p2 (list 0.00 0.00))
 (command "TEXT" "J" "MR" p1   0.75  0.00 "2846.37")
 (setq p1 (list 106.50 1693.25) p2 (list 107.00 1693.25))
 (command "LINE" p1 p2 "")
 (setq p1 (list 106.13 1693.25) p2 (list 0.00 0.00))
 (command "TEXT" "J" "MR" p1   0.75  0.00 "260.00")
 (setq p1 (list 106.13 1692.13) p2 (list 0.00 0.00))
 (command "TEXT" "J" "MR" p1   0.75  0.00 "2836.37")
 (setq p1 (list 106.50 1683.25) p2 (list 107.00 1683.25))
 (command "LINE" p1 p2 "")
 (setq p1 (list 106.13 1683.25) p2 (list 0.00 0.00))
 (command "TEXT" "J" "MR" p1   0.75  0.00 "270.00")
 (setq p1 (list 106.13 1682.13) p2 (list 0.00 0.00))
 (command "TEXT" "J" "MR" p1   0.75  0.00 "2826.37")
 (setq p1 (list 106.50 1673.25) p2 (list 107.00 1673.25))
 (command "LINE" p1 p2 "")
 (setq p1 (list 106.13 1673.25) p2 (list 0.00 0.00))
 (command "TEXT" "J" "MR" p1   0.75  0.00 "280.00")
 (setq p1 (list 106.13 1672.13) p2 (list 0.00 0.00))
 (command "TEXT" "J" "MR" p1   0.75  0.00 "2816.37")
 (setq p1 (list 106.50 1663.25) p2 (list 107.00 1663.25))
 (command "LINE" p1 p2 "")
 (setq p1 (list 106.13 1663.25) p2 (list 0.00 0.00))
 (command "TEXT" "J" "MR" p1   0.75  0.00 "290.00")
 (setq p1 (list 106.13 1662.13) p2 (list 0.00 0.00))
 (command "TEXT" "J" "MR" p1   0.75  0.00 "2806.37")
 (setq p1 (list 106.50 1653.25) p2 (list 107.00 1653.25))
 (command "LINE" p1 p2 "")
 (setq p1 (list 106.13 1653.25) p2 (list 0.00 0.00))
 (command "TEXT" "J" "MR" p1   0.75  0.00 "300.00")
 (setq p1 (list 106.13 1652.13) p2 (list 0.00 0.00))
 (command "TEXT" "J" "MR" p1   0.75  0.00 "2796.37")
 (setq p1 (list 106.50 1643.25) p2 (list 107.00 1643.25))
 (command "LINE" p1 p2 "")
 (setq p1 (list 106.13 1643.25) p2 (list 0.00 0.00))
 (command "TEXT" "J" "MR" p1   0.75  0.00 "310.00")
 (setq p1 (list 106.13 1642.13) p2 (list 0.00 0.00))
 (command "TEXT" "J" "MR" p1   0.75  0.00 "2786.37")
 (setq p1 (list 106.50 1633.25) p2 (list 107.00 1633.25))
 (command "LINE" p1 p2 "")
 (setq p1 (list 106.13 1633.25) p2 (list 0.00 0.00))
 (command "TEXT" "J" "MR" p1   0.75  0.00 "320.00")
 (setq p1 (list 106.13 1632.13) p2 (list 0.00 0.00))
 (command "TEXT" "J" "MR" p1   0.75  0.00 "2776.37")
 (setq p1 (list 106.50 1623.25) p2 (list 107.00 1623.25))
 (command "LINE" p1 p2 "")
 (setq p1 (list 106.13 1623.25) p2 (list 0.00 0.00))
 (command "TEXT" "J" "MR" p1   0.75  0.00 "330.00")
 (setq p1 (list 106.13 1622.13) p2 (list 0.00 0.00))
 (command "TEXT" "J" "MR" p1   0.75  0.00 "2766.37")
 (setq p1 (list 106.50 1613.25) p2 (list 107.00 1613.25))
 (command "LINE" p1 p2 "")
 (setq p1 (list 106.13 1613.25) p2 (list 0.00 0.00))
 (command "TEXT" "J" "MR" p1   0.75  0.00 "340.00")
 (setq p1 (list 106.13 1612.13) p2 (list 0.00 0.00))
 (command "TEXT" "J" "MR" p1   0.75  0.00 "2756.37")
 (setq p1 (list 106.50 1603.25) p2 (list 107.00 1603.25))
 (command "LINE" p1 p2 "")
 (setq p1 (list 106.13 1603.25) p2 (list 0.00 0.00))
 (command "TEXT" "J" "MR" p1   0.75  0.00 "350.00")
 (setq p1 (list 106.13 1602.13) p2 (list 0.00 0.00))
 (command "TEXT" "J" "MR" p1   0.75  0.00 "2746.37")
 (setq p1 (list 106.50 1593.25) p2 (list 107.00 1593.25))
 (command "LINE" p1 p2 "")
 (setq p1 (list 106.13 1593.25) p2 (list 0.00 0.00))
 (command "TEXT" "J" "MR" p1   0.75  0.00 "360.00")
 (setq p1 (list 106.13 1592.13) p2 (list 0.00 0.00))
 (command "TEXT" "J" "MR" p1   0.75  0.00 "2736.37")
 (setq p1 (list 106.50 1583.25) p2 (list 107.00 1583.25))
 (command "LINE" p1 p2 "")
 (setq p1 (list 106.13 1583.25) p2 (list 0.00 0.00))
 (command "TEXT" "J" "MR" p1   0.75  0.00 "370.00")
 (setq p1 (list 106.13 1582.13) p2 (list 0.00 0.00))
 (command "TEXT" "J" "MR" p1   0.75  0.00 "2726.37")
 (setq p1 (list 106.50 1573.25) p2 (list 107.00 1573.25))
 (command "LINE" p1 p2 "")
 (setq p1 (list 106.13 1573.25) p2 (list 0.00 0.00))
 (command "TEXT" "J" "MR" p1   0.75  0.00 "380.00")
 (setq p1 (list 106.13 1572.13) p2 (list 0.00 0.00))
 (command "TEXT" "J" "MR" p1   0.75  0.00 "2716.37")
 (setq p1 (list 106.50 1563.25) p2 (list 107.00 1563.25))
 (command "LINE" p1 p2 "")
 (setq p1 (list 106.13 1563.25) p2 (list 0.00 0.00))
 (command "TEXT" "J" "MR" p1   0.75  0.00 "390.00")
 (setq p1 (list 106.13 1562.13) p2 (list 0.00 0.00))
 (command "TEXT" "J" "MR" p1   0.75  0.00 "2706.37")
 (setq p1 (list 106.50 1553.25) p2 (list 107.00 1553.25))
 (command "LINE" p1 p2 "")
 (setq p1 (list 106.13 1553.25) p2 (list 0.00 0.00))
 (command "TEXT" "J" "MR" p1   0.75  0.00 "400.00")
 (setq p1 (list 106.13 1552.13) p2 (list 0.00 0.00))
 (command "TEXT" "J" "MR" p1   0.75  0.00 "2696.37")
 (setq p1 (list 106.50 1543.25) p2 (list 107.00 1543.25))
 (command "LINE" p1 p2 "")
 (setq p1 (list 106.13 1543.25) p2 (list 0.00 0.00))
 (command "TEXT" "J" "MR" p1   0.75  0.00 "410.00")
 (setq p1 (list 106.13 1542.13) p2 (list 0.00 0.00))
 (command "TEXT" "J" "MR" p1   0.75  0.00 "2686.37")
 (setq p1 (list 106.50 1533.25) p2 (list 107.00 1533.25))
 (command "LINE" p1 p2 "")
 (setq p1 (list 106.13 1533.25) p2 (list 0.00 0.00))
 (command "TEXT" "J" "MR" p1   0.75  0.00 "420.00")
 (setq p1 (list 106.13 1532.13) p2 (list 0.00 0.00))
 (command "TEXT" "J" "MR" p1   0.75  0.00 "2676.37")
 (setq p1 (list 106.50 1523.25) p2 (list 107.00 1523.25))
 (command "LINE" p1 p2 "")
 (setq p1 (list 106.13 1523.25) p2 (list 0.00 0.00))
 (command "TEXT" "J" "MR" p1   0.75  0.00 "430.00")
 (setq p1 (list 106.13 1522.13) p2 (list 0.00 0.00))
 (command "TEXT" "J" "MR" p1   0.75  0.00 "2666.37")
 (setq p1 (list 106.50 1513.25) p2 (list 107.00 1513.25))
 (command "LINE" p1 p2 "")
 (setq p1 (list 106.13 1513.25) p2 (list 0.00 0.00))
 (command "TEXT" "J" "MR" p1   0.75  0.00 "440.00")
 (setq p1 (list 106.13 1512.13) p2 (list 0.00 0.00))
 (command "TEXT" "J" "MR" p1   0.75  0.00 "2656.37")
 (setq p1 (list 106.50 1503.25) p2 (list 107.00 1503.25))
 (command "LINE" p1 p2 "")
 (setq p1 (list 106.13 1503.25) p2 (list 0.00 0.00))
 (command "TEXT" "J" "MR" p1   0.75  0.00 "450.00")
 (setq p1 (list 106.13 1502.13) p2 (list 0.00 0.00))
 (command "TEXT" "J" "MR" p1   0.75  0.00 "2646.37")
 (setq p1 (list 106.50 1493.25) p2 (list 107.00 1493.25))
 (command "LINE" p1 p2 "")
 (setq p1 (list 106.13 1493.25) p2 (list 0.00 0.00))
 (command "TEXT" "J" "MR" p1   0.75  0.00 "460.00")
 (setq p1 (list 106.13 1492.13) p2 (list 0.00 0.00))
 (command "TEXT" "J" "MR" p1   0.75  0.00 "2636.37")
 (setq p1 (list 106.50 1483.25) p2 (list 107.00 1483.25))
 (command "LINE" p1 p2 "")
 (setq p1 (list 106.13 1483.25) p2 (list 0.00 0.00))
 (command "TEXT" "J" "MR" p1   0.75  0.00 "470.00")
 (setq p1 (list 106.13 1482.13) p2 (list 0.00 0.00))
 (command "TEXT" "J" "MR" p1   0.75  0.00 "2626.37")
 (setq p1 (list 106.50 1469.75) p2 (list 107.00 1469.75))
 (command "LINE" p1 p2 "")
 (setq p1 (list 106.13 1469.75) p2 (list 0.00 0.00))
 (command "TEXT" "J" "MR" p1   0.75  0.00 "483.50")
 (setq p1 (list 106.13 1468.63) p2 (list 0.00 0.00))
 (command "TEXT" "J" "MR" p1   0.75  0.00 "2612.87")
 (command "LAYER" "S" "CGBHLHDR" "")
 (setq p1 (list 100.00 1964.75) p2 (list 100.00 1954.75) p3 (list 120.00 1954.75) p4 (list 120.00 1964.75))
 (command "LINE" p1 p2 p3 p4 "c")
 (setq p1 (list 100.50 1963.00) p2 (list 0.00 0.00))
 (command "TEXT" "J" "ML" p1   1.13  0.00 "Hole:")
 (setq p1 (list 100.50 1960.75) p2 (list 0.00 0.00))
 (command "TEXT" "J" "ML" p1   0.83  0.00 "Easting:")
 (setq p1 (list 100.50 1959.00) p2 (list 0.00 0.00))
 (command "TEXT" "J" "ML" p1   0.83  0.00 "Northing:")
 (setq p1 (list 100.50 1957.25) p2 (list 0.00 0.00))
 (command "TEXT" "J" "ML" p1   0.83  0.00 "Collar Elev:")
 (setq p1 (list 100.50 1955.50) p2 (list 0.00 0.00))
 (command "TEXT" "J" "ML" p1   0.83  0.00 "Drill Depth:")
 (setq p1 (list 119.50 1963.00) p2 (list 0.00 0.00))
 (command "TEXT" "J" "MR" p1   1.13  0.00 "XY-32")
 (setq p1 (list 119.50 1960.75) p2 (list 0.00 0.00))
 (command "TEXT" "J" "MR" p1   0.83  0.00 "4032200.63")
 (setq p1 (list 119.50 1959.00) p2 (list 0.00 0.00))
 (command "TEXT" "J" "MR" p1   0.83  0.00 "263139.25")
 (setq p1 (list 119.50 1957.25) p2 (list 0.00 0.00))
 (command "TEXT" "J" "MR" p1   0.83  0.00 "3096.37")
 (setq p1 (list 119.50 1955.50) p2 (list 0.00 0.00))
 (command "TEXT" "J" "MR" p1   0.83  0.00 "485.00")
 (setq p1 (list 110.00 1954.75) p2 (list 110.00 1953.25))
 (command "LINE" p1 p2 "")
 (command "LAYER" "S" "CGBMAIN" "")
 (setq p1 (list 214.00 1886.94) p2 (list 220.00 1886.94) p3 (list 220.00 1861.94) p4 (list 214.00 1861.94))
 (command "PLINE" p1 p2 p3 p4 "c")
 (command "LINE" p1 p3 "")
 (command "LINE" p2 p4 "")
 (command "COLOR" "BYLAYER")
 (command "LAYER" "S" "CGBLITHCD" "")
 (setq p1 (list 220.00 1874.44) p2 (list 221.35 1874.44))
 (command "LINE" p1 p2 "")
 (setq p1 (list 221.50 1874.07) p2 (list 0.00 0.00))
 (command "TEXT" "J" "ML" p1   0.75  0.00 "001")
 (command "LAYER" "S" "CGBTHK" "")
 (setq p1 (list 226.00 1874.07) p2 (list 0.00 0.00))
 (command "TEXT" "J" "ML" p1   0.75  0.00 "25.00")
 (command "LAYER" "S" "CGBHZID" "")
 (setq p1 (list 230.50 1874.07) p2 (list 0.00 0.00))
 (command "TEXT" "J" "ML" p1   0.75  0.00 "")
 (setq p1 (list 232.75 1874.07) p2 (list 0.00 0.00))
 (command "TEXT" "J" "ML" p1   0.75  0.00 "9990")
 (command "LAYER" "S" "CGBLITHTXT" "")
 (setq p1 (list 236.50 1874.07) p2 (list 0.00 0.00))
 (command "TEXT" "J" "ML" p1   0.75  0.00 "CASING")
 (command "LAYER" "S" "CGBCMNT" "")
 (setq p1 (list 256.75 1874.07) p2 (list 0.00 0.00))
 (command "TEXT" "J" "ML" p1   0.75  0.00 "")
 (command "LAYER" "S" "CGBMAIN" "")
 (setq p1 (list 214.00 1861.94) p2 (list 220.00 1861.94) p3 (list 220.00 1860.16) p4 (list 214.00 1860.16))
 (command "PLINE" p1 p2 p3 p4 "c")
 (command "HATCH" "ZIGZAG" 2.00 0.00 "L" "")
 (command "COLOR" "BYLAYER")
 (command "LAYER" "S" "CGBLITHCD" "")
 (setq p1 (list 220.00 1861.05) p2 (list 221.35 1861.05))
 (command "LINE" p1 p2 "")
 (setq p1 (list 221.50 1860.68) p2 (list 0.00 0.00))
 (command "TEXT" "J" "ML" p1   0.75  0.00 "100")
 (command "LAYER" "S" "CGBTHK" "")
 (setq p1 (list 226.00 1860.68) p2 (list 0.00 0.00))
 (command "TEXT" "J" "ML" p1   0.75  0.00 "1.78")
 (command "LAYER" "S" "CGBHZID" "")
 (setq p1 (list 230.50 1860.68) p2 (list 0.00 0.00))
 (command "TEXT" "J" "ML" p1   0.75  0.00 "")
 (setq p1 (list 232.75 1860.68) p2 (list 0.00 0.00))
 (command "TEXT" "J" "ML" p1   0.75  0.00 "9990")
 (command "LAYER" "S" "CGBLITHTXT" "")
 (setq p1 (list 236.50 1860.68) p2 (list 0.00 0.00))
 (command "TEXT" "J" "ML" p1   0.75  0.00 "SH (UNDIF)")
 (command "LAYER" "S" "CGBCMNT" "")
 (setq p1 (list 256.75 1860.68) p2 (list 0.00 0.00))
 (command "TEXT" "J" "ML" p1   0.75  0.00 "SFT,GRY-BRWN")
 (command "LAYER" "S" "CGBMAIN" "")
 (setq p1 (list 214.00 1860.16) p2 (list 220.00 1860.16) p3 (list 220.00 1850.94) p4 (list 214.00 1850.94))
 (command "PLINE" p1 p2 p3 p4 "c")
 (command "HATCH" "ZIGZAG" 4.00 0.00 "L" "")
 (command "COLOR" "BYLAYER")
 (command "LAYER" "S" "CGBLITHCD" "")
 (setq p1 (list 220.00 1855.55) p2 (list 221.35 1855.55))
 (command "LINE" p1 p2 "")
 (setq p1 (list 221.50 1855.18) p2 (list 0.00 0.00))
 (command "TEXT" "J" "ML" p1   0.75  0.00 "544")
 (command "LAYER" "S" "CGBTHK" "")
 (setq p1 (list 226.00 1855.18) p2 (list 0.00 0.00))
 (command "TEXT" "J" "ML" p1   0.75  0.00 "9.22")
 (command "LAYER" "S" "CGBHZID" "")
 (setq p1 (list 230.50 1855.18) p2 (list 0.00 0.00))
 (command "TEXT" "J" "ML" p1   0.75  0.00 "")
 (setq p1 (list 232.75 1855.18) p2 (list 0.00 0.00))
 (command "TEXT" "J" "ML" p1   0.75  0.00 "9990")
 (command "LAYER" "S" "CGBLITHTXT" "")
 (setq p1 (list 236.50 1855.18) p2 (list 0.00 0.00))
 (command "TEXT" "J" "ML" p1   0.75  0.00 "GRY MASS SS")
 (command "LAYER" "S" "CGBCMNT" "")
 (setq p1 (list 256.75 1855.18) p2 (list 0.00 0.00))
 (command "TEXT" "J" "ML" p1   0.75  0.00 "FRACS@ 30.5,3")
 (command "LAYER" "S" "CGBMAIN" "")
 (setq p1 (list 214.00 1850.94) p2 (list 220.00 1850.94) p3 (list 220.00 1840.77) p4 (list 214.00 1840.77))
 (command "PLINE" p1 p2 p3 p4 "c")
 (command "HATCH" "ZIGZAG" 4.00 0.00 "L" "")
 (command "COLOR" "BYLAYER")
 (command "LAYER" "S" "CGBLITHCD" "")
 (setq p1 (list 220.00 1845.86) p2 (list 221.35 1845.86))
 (command "LINE" p1 p2 "")
 (setq p1 (list 221.50 1845.48) p2 (list 0.00 0.00))
 (command "TEXT" "J" "ML" p1   0.75  0.00 "544")
 (command "LAYER" "S" "CGBTHK" "")
 (setq p1 (list 226.00 1845.48) p2 (list 0.00 0.00))
 (command "TEXT" "J" "ML" p1   0.75  0.00 "10.17")
 (command "LAYER" "S" "CGBHZID" "")
 (setq p1 (list 230.50 1845.48) p2 (list 0.00 0.00))
 (command "TEXT" "J" "ML" p1   0.75  0.00 "")
 (setq p1 (list 232.75 1845.48) p2 (list 0.00 0.00))
 (command "TEXT" "J" "ML" p1   0.75  0.00 "9990")
 (command "LAYER" "S" "CGBLITHTXT" "")
 (setq p1 (list 236.50 1845.48) p2 (list 0.00 0.00))
 (command "TEXT" "J" "ML" p1   0.75  0.00 "GRY MASS SS")
 (command "LAYER" "S" "CGBCMNT" "")
 (setq p1 (list 256.75 1845.48) p2 (list 0.00 0.00))
 (command "TEXT" "J" "ML" p1   0.75  0.00 "FRACS,STYLS")
 (command "LAYER" "S" "CGBMAIN" "")
 (setq p1 (list 214.00 1840.77) p2 (list 220.00 1840.77) p3 (list 220.00 1840.62) p4 (list 214.00 1840.62))
 (command "PLINE" p1 p2 p3 p4 "c")
 (command "HATCH" "ZIGZAG" 0.25 0.00 "L" "")
 (command "COLOR" "BYLAYER")
 (command "LAYER" "S" "CGBLITHCD" "")
 (setq p1 (list 220.00 1840.70) p2 (list 221.35 1840.70))
 (command "LINE" p1 p2 "")
 (setq p1 (list 221.50 1840.32) p2 (list 0.00 0.00))
 (command "TEXT" "J" "ML" p1   0.75  0.00 "748")
 (command "LAYER" "S" "CGBTHK" "")
 (setq p1 (list 226.00 1840.32) p2 (list 0.00 0.00))
 (command "TEXT" "J" "ML" p1   0.75  0.00 "0.15")
 (command "LAYER" "S" "CGBHZID" "")
 (setq p1 (list 230.50 1840.32) p2 (list 0.00 0.00))
 (command "TEXT" "J" "ML" p1   0.75  0.00 "")
 (setq p1 (list 232.75 1840.32) p2 (list 0.00 0.00))
 (command "TEXT" "J" "ML" p1   0.75  0.00 "9990")
 (command "LAYER" "S" "CGBLITHTXT" "")
 (setq p1 (list 236.50 1840.32) p2 (list 0.00 0.00))
 (command "TEXT" "J" "ML" p1   0.75  0.00 "GRY SS W/COAL BANDS")
 (command "LAYER" "S" "CGBCMNT" "")
 (setq p1 (list 256.75 1840.32) p2 (list 0.00 0.00))
 (command "TEXT" "J" "ML" p1   0.75  0.00 "")
 (command "LAYER" "S" "CGBMAIN" "")
 (setq p1 (list 214.00 1840.62) p2 (list 220.00 1840.62) p3 (list 220.00 1837.12) p4 (list 214.00 1837.12))
 (command "PLINE" p1 p2 p3 p4 "c")
 (command "HATCH" "ZIGZAG" 4.00 0.00 "L" "")
 (command "COLOR" "BYLAYER")
 (command "LAYER" "S" "CGBLITHCD" "")
 (setq p1 (list 220.00 1838.87) p2 (list 221.35 1838.87))
 (command "LINE" p1 p2 "")
 (setq p1 (list 221.50 1838.50) p2 (list 0.00 0.00))
 (command "TEXT" "J" "ML" p1   0.75  0.00 "544")
 (command "LAYER" "S" "CGBTHK" "")
 (setq p1 (list 226.00 1838.50) p2 (list 0.00 0.00))
 (command "TEXT" "J" "ML" p1   0.75  0.00 "3.50")
 (command "LAYER" "S" "CGBHZID" "")
 (setq p1 (list 230.50 1838.50) p2 (list 0.00 0.00))
 (command "TEXT" "J" "ML" p1   0.75  0.00 "")
 (setq p1 (list 232.75 1838.50) p2 (list 0.00 0.00))
 (command "TEXT" "J" "ML" p1   0.75  0.00 "9990")
 (command "LAYER" "S" "CGBLITHTXT" "")
 (setq p1 (list 236.50 1838.50) p2 (list 0.00 0.00))
 (command "TEXT" "J" "ML" p1   0.75  0.00 "GRY MASS SS")
 (command "LAYER" "S" "CGBCMNT" "")
 (setq p1 (list 256.75 1838.50) p2 (list 0.00 0.00))
 (command "TEXT" "J" "ML" p1   0.75  0.00 "")
 (command "LAYER" "S" "CGBMAIN" "")
 (setq p1 (list 214.00 1837.12) p2 (list 220.00 1837.12) p3 (list 220.00 1832.59) p4 (list 214.00 1832.59))
 (command "PLINE" p1 p2 p3 p4 "c")
 (command "HATCH" "ZIGZAG" 4.00 0.00 "L" "")
 (command "COLOR" "BYLAYER")
 (command "LAYER" "S" "CGBLITHCD" "")
 (setq p1 (list 220.00 1834.86) p2 (list 221.35 1834.86))
 (command "LINE" p1 p2 "")
 (setq p1 (list 221.50 1834.48) p2 (list 0.00 0.00))
 (command "TEXT" "J" "ML" p1   0.75  0.00 "544")
 (command "LAYER" "S" "CGBTHK" "")
 (setq p1 (list 226.00 1834.48) p2 (list 0.00 0.00))
 (command "TEXT" "J" "ML" p1   0.75  0.00 "4.53")
 (command "LAYER" "S" "CGBHZID" "")
 (setq p1 (list 230.50 1834.48) p2 (list 0.00 0.00))
 (command "TEXT" "J" "ML" p1   0.75  0.00 "")
 (setq p1 (list 232.75 1834.48) p2 (list 0.00 0.00))
 (command "TEXT" "J" "ML" p1   0.75  0.00 "9990")
 (command "LAYER" "S" "CGBLITHTXT" "")
 (setq p1 (list 236.50 1834.48) p2 (list 0.00 0.00))
 (command "TEXT" "J" "ML" p1   0.75  0.00 "GRY MASS SS")
 (command "LAYER" "S" "CGBCMNT" "")
 (setq p1 (list 256.75 1834.48) p2 (list 0.00 0.00))
 (command "TEXT" "J" "ML" p1   0.75  0.00 "SLC")
 (command "LAYER" "S" "CGBMAIN" "")
 (setq p1 (list 214.00 1832.59) p2 (list 220.00 1832.59) p3 (list 220.00 1831.33) p4 (list 214.00 1831.33))
 (command "PLINE" p1 p2 p3 p4 "c")
 (command "HATCH" "ZIGZAG" 2.50 90.00 "L" "")
 (command "COLOR" "BYLAYER")
 (command "LAYER" "S" "CGBLITHCD" "")
 (setq p1 (list 220.00 1831.96) p2 (list 221.35 1831.96))
 (command "LINE" p1 p2 "")
 (setq p1 (list 221.50 1831.59) p2 (list 0.00 0.00))
 (command "TEXT" "J" "ML" p1   0.75  0.00 "318")
 (command "LAYER" "S" "CGBTHK" "")
 (setq p1 (list 226.00 1831.59) p2 (list 0.00 0.00))
 (command "TEXT" "J" "ML" p1   0.75  0.00 "1.26")
 (command "LAYER" "S" "CGBHZID" "")
 (setq p1 (list 230.50 1831.59) p2 (list 0.00 0.00))
 (command "TEXT" "J" "ML" p1   0.75  0.00 "")
 (setq p1 (list 232.75 1831.59) p2 (list 0.00 0.00))
 (command "TEXT" "J" "ML" p1   0.75  0.00 "9990")
 (command "LAYER" "S" "CGBLITHTXT" "")
 (setq p1 (list 236.50 1831.59) p2 (list 0.00 0.00))
 (command "TEXT" "J" "ML" p1   0.75  0.00 "BLK BURROWED SDY SH")
 (command "LAYER" "S" "CGBCMNT" "")
 (setq p1 (list 256.75 1831.59) p2 (list 0.00 0.00))
 (command "TEXT" "J" "ML" p1   0.75  0.00 "BRKN @ TOP")
 (command "LAYER" "S" "CGBMAIN" "")
 (setq p1 (list 214.00 1831.33) p2 (list 220.00 1831.33) p3 (list 220.00 1830.35) p4 (list 214.00 1830.35))
 (command "PLINE" p1 p2 p3 p4 "c")
 (command "HATCH" "ZIGZAG" 4.00 0.00 "L" "")
 (command "COLOR" "BYLAYER")
 (command "LAYER" "S" "CGBLITHCD" "")
 (setq p1 (list 220.00 1830.84) p2 (list 221.35 1829.59))
 (command "LINE" p1 p2 "")
 (setq p1 (list 221.50 1829.22) p2 (list 0.00 0.00))
 (command "TEXT" "J" "ML" p1   0.75  0.00 "115")
 (command "LAYER" "S" "CGBTHK" "")
 (setq p1 (list 226.00 1829.22) p2 (list 0.00 0.00))
 (command "TEXT" "J" "ML" p1   0.75  0.00 "0.98")
 (command "LAYER" "S" "CGBHZID" "")
 (setq p1 (list 230.50 1829.22) p2 (list 0.00 0.00))
 (command "TEXT" "J" "ML" p1   0.75  0.00 "")
 (setq p1 (list 232.75 1829.22) p2 (list 0.00 0.00))
 (command "TEXT" "J" "ML" p1   0.75  0.00 "9990")
 (command "LAYER" "S" "CGBLITHTXT" "")
 (setq p1 (list 236.50 1829.22) p2 (list 0.00 0.00))
 (command "TEXT" "J" "ML" p1   0.75  0.00 "BLK CHRND SH")
 (command "LAYER" "S" "CGBCMNT" "")
 (setq p1 (list 256.75 1829.22) p2 (list 0.00 0.00))
 (command "TEXT" "J" "ML" p1   0.75  0.00 "V SFT,MTTLD")
 (command "LAYER" "S" "CGBMAIN" "")
 (setq p1 (list 214.00 1830.35) p2 (list 220.00 1830.35) p3 (list 220.00 1829.00) p4 (list 214.00 1829.00))
 (command "PLINE" p1 p2 p3 p4 "c")
 (command "HATCH" "ZIGZAG" 4.00 22.50 "L" "")
 (command "COLOR" "BYLAYER")
 (command "LAYER" "S" "CGBLITHCD" "")
 (setq p1 (list 220.00 1829.68) p2 (list 221.35 1828.34))
 (command "LINE" p1 p2 "")
 (setq p1 (list 221.50 1827.97) p2 (list 0.00 0.00))
 (command "TEXT" "J" "ML" p1   0.75  0.00 "114")
 (command "LAYER" "S" "CGBTHK" "")
 (setq p1 (list 226.00 1827.97) p2 (list 0.00 0.00))
 (command "TEXT" "J" "ML" p1   0.75  0.00 "1.35")
 (command "LAYER" "S" "CGBHZID" "")
 (setq p1 (list 230.50 1827.97) p2 (list 0.00 0.00))
 (command "TEXT" "J" "ML" p1   0.75  0.00 "")
 (setq p1 (list 232.75 1827.97) p2 (list 0.00 0.00))
 (command "TEXT" "J" "ML" p1   0.75  0.00 "9990")
 (command "LAYER" "S" "CGBLITHTXT" "")
 (setq p1 (list 236.50 1827.97) p2 (list 0.00 0.00))
 (command "TEXT" "J" "ML" p1   0.75  0.00 "BLK SH")
 (command "LAYER" "S" "CGBCMNT" "")
 (setq p1 (list 256.75 1827.97) p2 (list 0.00 0.00))
 (command "TEXT" "J" "ML" p1   0.75  0.00 "NODS")
 (command "LAYER" "S" "CGBMAIN" "")
 (setq p1 (list 214.00 1829.00) p2 (list 220.00 1829.00) p3 (list 220.00 1828.55) p4 (list 214.00 1828.55))
 (command "PLINE" p1 p2 p3 p4 "c")
 (command "HATCH" "ZIGZAG" 0.30 22.50 "L" "")
 (command "COLOR" "BYLAYER")
 (command "LAYER" "S" "CGBLITHCD" "")
 (setq p1 (list 220.00 1828.78) p2 (list 221.35 1827.09))
 (command "LINE" p1 p2 "")
 (setq p1 (list 221.50 1826.72) p2 (list 0.00 0.00))
 (command "TEXT" "J" "ML" p1   0.75  0.00 "027")
 (command "LAYER" "S" "CGBTHK" "")
 (setq p1 (list 226.00 1826.72) p2 (list 0.00 0.00))
 (command "TEXT" "J" "ML" p1   0.75  0.00 "0.45")
 (command "LAYER" "S" "CGBHZID" "")
 (setq p1 (list 230.50 1826.72) p2 (list 0.00 0.00))
 (command "TEXT" "J" "ML" p1   0.75  0.00 "")
 (setq p1 (list 232.75 1826.72) p2 (list 0.00 0.00))
 (command "TEXT" "J" "ML" p1   0.75  0.00 "8500")
 (command "LAYER" "S" "CGBLITHTXT" "")
 (setq p1 (list 236.50 1826.72) p2 (list 0.00 0.00))
 (command "TEXT" "J" "ML" p1   0.75  0.00 "COAL W/SH LAYERS")
 (command "LAYER" "S" "CGBCMNT" "")
 (setq p1 (list 256.75 1826.72) p2 (list 0.00 0.00))
 (command "TEXT" "J" "ML" p1   0.75  0.00 "VIT & DUR")
 (command "LAYER" "S" "CGBMAIN" "")
 (setq p1 (list 214.00 1828.55) p2 (list 220.00 1828.55) p3 (list 220.00 1828.12) p4 (list 214.00 1828.12))
 (command "PLINE" p1 p2 p3 p4 "c")
 (command "HATCH" "ZIGZAG" 1.00 45.00 "L" "")
 (command "COLOR" "BYLAYER")
 (command "LAYER" "S" "CGBLITHCD" "")
 (setq p1 (list 220.00 1828.34) p2 (list 221.35 1825.84))
 (command "LINE" p1 p2 "")
 (setq p1 (list 221.50 1825.47) p2 (list 0.00 0.00))
 (command "TEXT" "J" "ML" p1   0.75  0.00 "028")
 (command "LAYER" "S" "CGBTHK" "")
 (setq p1 (list 226.00 1825.47) p2 (list 0.00 0.00))
 (command "TEXT" "J" "ML" p1   0.75  0.00 "0.43")
 (command "LAYER" "S" "CGBHZID" "")
 (setq p1 (list 230.50 1825.47) p2 (list 0.00 0.00))
 (command "TEXT" "J" "ML" p1   0.75  0.00 "")
 (setq p1 (list 232.75 1825.47) p2 (list 0.00 0.00))
 (command "TEXT" "J" "ML" p1   0.75  0.00 "8500")
 (command "LAYER" "S" "CGBLITHTXT" "")
 (setq p1 (list 236.50 1825.47) p2 (list 0.00 0.00))
 (command "TEXT" "J" "ML" p1   0.75  0.00 "COAL W/SH STKS")
 (command "LAYER" "S" "CGBCMNT" "")
 (setq p1 (list 256.75 1825.47) p2 (list 0.00 0.00))
 (command "TEXT" "J" "ML" p1   0.75  0.00 "VIT W/FUS")
 (command "LAYER" "S" "CGBMAIN" "")
 (setq p1 (list 214.00 1828.12) p2 (list 220.00 1828.12) p3 (list 220.00 1827.18) p4 (list 214.00 1827.18))
 (command "PLINE" p1 p2 p3 p4 "c")
 (command "COLOR" "BLUE")
 (command "SOLID" p1 p2 p4 p3 "")
 (command "COLOR" "BYLAYER")
 (command "LAYER" "S" "CGBLITHCD" "")
 (setq p1 (list 220.00 1827.65) p2 (list 221.35 1824.59))
 (command "LINE" p1 p2 "")
 (setq p1 (list 221.50 1824.22) p2 (list 0.00 0.00))
 (command "TEXT" "J" "ML" p1   0.75  0.00 "021")
 (command "LAYER" "S" "CGBTHK" "")
 (setq p1 (list 226.00 1824.22) p2 (list 0.00 0.00))
 (command "TEXT" "J" "ML" p1   0.75  0.00 "0.94")
 (command "LAYER" "S" "CGBHZID" "")
 (setq p1 (list 230.50 1824.22) p2 (list 0.00 0.00))
 (command "TEXT" "J" "ML" p1   0.75  0.00 "")
 (setq p1 (list 232.75 1824.22) p2 (list 0.00 0.00))
 (command "TEXT" "J" "ML" p1   0.75  0.00 "8500")
 (command "LAYER" "S" "CGBLITHTXT" "")
 (setq p1 (list 236.50 1824.22) p2 (list 0.00 0.00))
 (command "TEXT" "J" "ML" p1   0.75  0.00 "COMMON BANDED COAL")
 (command "LAYER" "S" "CGBCMNT" "")
 (setq p1 (list 256.75 1824.22) p2 (list 0.00 0.00))
 (command "TEXT" "J" "ML" p1   0.75  0.00 "VITRAIN")
 (command "LAYER" "S" "CGBMAIN" "")
 (setq p1 (list 214.00 1827.18) p2 (list 220.00 1827.18) p3 (list 220.00 1826.92) p4 (list 214.00 1826.92))
 (command "PLINE" p1 p2 p3 p4 "c")
 (command "HATCH" "ZIGZAG" 0.40 45.00 "L" "")
 (command "COLOR" "BYLAYER")
 (command "LAYER" "S" "CGBLITHCD" "")
 (setq p1 (list 220.00 1827.05) p2 (list 221.35 1823.34))
 (command "LINE" p1 p2 "")
 (setq p1 (list 221.50 1822.97) p2 (list 0.00 0.00))
 (command "TEXT" "J" "ML" p1   0.75  0.00 "023")
 (command "LAYER" "S" "CGBTHK" "")
 (setq p1 (list 226.00 1822.97) p2 (list 0.00 0.00))
 (command "TEXT" "J" "ML" p1   0.75  0.00 "0.26")
 (command "LAYER" "S" "CGBHZID" "")
 (setq p1 (list 230.50 1822.97) p2 (list 0.00 0.00))
 (command "TEXT" "J" "ML" p1   0.75  0.00 "")
 (setq p1 (list 232.75 1822.97) p2 (list 0.00 0.00))
 (command "TEXT" "J" "ML" p1   0.75  0.00 "8500")
 (command "LAYER" "S" "CGBLITHTXT" "")
 (setq p1 (list 236.50 1822.97) p2 (list 0.00 0.00))
 (command "TEXT" "J" "ML" p1   0.75  0.00 "COAL W/BONE STKS")
 (command "LAYER" "S" "CGBCMNT" "")
 (setq p1 (list 256.75 1822.97) p2 (list 0.00 0.00))
 (command "TEXT" "J" "ML" p1   0.75  0.00 "DULL,BONEY")
 (command "LAYER" "S" "CGBMAIN" "")
 (setq p1 (list 214.00 1826.92) p2 (list 220.00 1826.92) p3 (list 220.00 1826.78) p4 (list 214.00 1826.78))
 (command "PLINE" p1 p2 p3 p4 "c")
 (command "HATCH" "ZIGZAG" 6.00 0.00 "L" "")
 (command "COLOR" "BYLAYER")
 (command "LAYER" "S" "CGBLITHCD" "")
 (setq p1 (list 220.00 1826.85) p2 (list 221.35 1822.09))
 (command "LINE" p1 p2 "")
 (setq p1 (list 221.50 1821.72) p2 (list 0.00 0.00))
 (command "TEXT" "J" "ML" p1   0.75  0.00 "113")
 (command "LAYER" "S" "CGBTHK" "")
 (setq p1 (list 226.00 1821.72) p2 (list 0.00 0.00))
 (command "TEXT" "J" "ML" p1   0.75  0.00 "0.14")
 (command "LAYER" "S" "CGBHZID" "")
 (setq p1 (list 230.50 1821.72) p2 (list 0.00 0.00))
 (command "TEXT" "J" "ML" p1   0.75  0.00 "")
 (setq p1 (list 232.75 1821.72) p2 (list 0.00 0.00))
 (command "TEXT" "J" "ML" p1   0.75  0.00 "8451")
 (command "LAYER" "S" "CGBLITHTXT" "")
 (setq p1 (list 236.50 1821.72) p2 (list 0.00 0.00))
 (command "TEXT" "J" "ML" p1   0.75  0.00 "BLK SH W/COAL STKS")
 (command "LAYER" "S" "CGBCMNT" "")
 (setq p1 (list 256.75 1821.72) p2 (list 0.00 0.00))
 (command "TEXT" "J" "ML" p1   0.75  0.00 "")
 (command "LAYER" "S" "CGBMAIN" "")
 (setq p1 (list 214.00 1826.78) p2 (list 220.00 1826.78) p3 (list 220.00 1825.07) p4 (list 214.00 1825.07))
 (command "PLINE" p1 p2 p3 p4 "c")
 (command "HATCH" "ZIGZAG" 0.25 0.00 "L" "")
 (command "COLOR" "BYLAYER")
 (command "LAYER" "S" "CGBLITHCD" "")
 (setq p1 (list 220.00 1825.93) p2 (list 221.35 1820.84))
 (command "LINE" p1 p2 "")
 (setq p1 (list 221.50 1820.47) p2 (list 0.00 0.00))
 (command "TEXT" "J" "ML" p1   0.75  0.00 "117")
 (command "LAYER" "S" "CGBTHK" "")
 (setq p1 (list 226.00 1820.47) p2 (list 0.00 0.00))
 (command "TEXT" "J" "ML" p1   0.75  0.00 "1.71")
 (command "LAYER" "S" "CGBHZID" "")
 (setq p1 (list 230.50 1820.47) p2 (list 0.00 0.00))
 (command "TEXT" "J" "ML" p1   0.75  0.00 "")
 (setq p1 (list 232.75 1820.47) p2 (list 0.00 0.00))
 (command "TEXT" "J" "ML" p1   0.75  0.00 "8451")
 (command "LAYER" "S" "CGBLITHTXT" "")
 (setq p1 (list 236.50 1820.47) p2 (list 0.00 0.00))
 (command "TEXT" "J" "ML" p1   0.75  0.00 "BLK FIRECLAY")
 (command "LAYER" "S" "CGBCMNT" "")
 (setq p1 (list 256.75 1820.47) p2 (list 0.00 0.00))
 (command "TEXT" "J" "ML" p1   0.75  0.00 "BONEY,SLX,BRK")
 (command "LAYER" "S" "CGBMAIN" "")
 (setq p1 (list 214.00 1825.07) p2 (list 220.00 1825.07) p3 (list 220.00 1823.22) p4 (list 214.00 1823.22))
 (command "PLINE" p1 p2 p3 p4 "c")
 (command "HATCH" "ZIGZAG" 5.00 0.00 "L" "")
 (command "COLOR" "BYLAYER")
 (command "LAYER" "S" "CGBLITHCD" "")
 (setq p1 (list 220.00 1824.15) p2 (list 221.35 1819.59))
 (command "LINE" p1 p2 "")
 (setq p1 (list 221.50 1819.22) p2 (list 0.00 0.00))
 (command "TEXT" "J" "ML" p1   0.75  0.00 "137")
 (command "LAYER" "S" "CGBTHK" "")
 (setq p1 (list 226.00 1819.22) p2 (list 0.00 0.00))
 (command "TEXT" "J" "ML" p1   0.75  0.00 "1.85")
 (command "LAYER" "S" "CGBHZID" "")
 (setq p1 (list 230.50 1819.22) p2 (list 0.00 0.00))
 (command "TEXT" "J" "ML" p1   0.75  0.00 "")
 (setq p1 (list 232.75 1819.22) p2 (list 0.00 0.00))
 (command "TEXT" "J" "ML" p1   0.75  0.00 "8451")
 (command "LAYER" "S" "CGBLITHTXT" "")
 (setq p1 (list 236.50 1819.22) p2 (list 0.00 0.00))
 (command "TEXT" "J" "ML" p1   0.75  0.00 "LT GRY GRN FIRECLAY")
 (command "LAYER" "S" "CGBCMNT" "")
 (setq p1 (list 256.75 1819.22) p2 (list 0.00 0.00))
 (command "TEXT" "J" "ML" p1   0.75  0.00 "MTTLD,SLX")
 (command "LAYER" "S" "CGBMAIN" "")
 (setq p1 (list 214.00 1823.22) p2 (list 220.00 1823.22) p3 (list 220.00 1822.12) p4 (list 214.00 1822.12))
 (command "PLINE" p1 p2 p3 p4 "c")
 (command "HATCH" "ZIGZAG" 5.00 0.00 "L" "")
 (command "COLOR" "BYLAYER")
 (command "LAYER" "S" "CGBLITHCD" "")
 (setq p1 (list 220.00 1822.67) p2 (list 221.35 1818.34))
 (command "LINE" p1 p2 "")
 (setq p1 (list 221.50 1817.97) p2 (list 0.00 0.00))
 (command "TEXT" "J" "ML" p1   0.75  0.00 "237")
 (command "LAYER" "S" "CGBTHK" "")
 (setq p1 (list 226.00 1817.97) p2 (list 0.00 0.00))
 (command "TEXT" "J" "ML" p1   0.75  0.00 "1.10")
 (command "LAYER" "S" "CGBHZID" "")
 (setq p1 (list 230.50 1817.97) p2 (list 0.00 0.00))
 (command "TEXT" "J" "ML" p1   0.75  0.00 "")
 (setq p1 (list 232.75 1817.97) p2 (list 0.00 0.00))
 (command "TEXT" "J" "ML" p1   0.75  0.00 "8451")
 (command "LAYER" "S" "CGBLITHTXT" "")
 (setq p1 (list 236.50 1817.97) p2 (list 0.00 0.00))
 (command "TEXT" "J" "ML" p1   0.75  0.00 "LT GRY GRN FIRECLAY W/LS")
 (command "LAYER" "S" "CGBCMNT" "")
 (setq p1 (list 256.75 1817.97) p2 (list 0.00 0.00))
 (command "TEXT" "J" "ML" p1   0.75  0.00 "V SFT")
 (command "LAYER" "S" "CGBMAIN" "")
 (setq p1 (list 214.00 1822.12) p2 (list 220.00 1822.12) p3 (list 220.00 1819.01) p4 (list 214.00 1819.01))
 (command "PLINE" p1 p2 p3 p4 "c")
 (command "HATCH" "ZIGZAG" 5.00 0.00 "L" "")
 (command "COLOR" "BYLAYER")
 (command "LAYER" "S" "CGBLITHCD" "")
 (setq p1 (list 220.00 1820.57) p2 (list 221.35 1817.09))
 (command "LINE" p1 p2 "")
 (setq p1 (list 221.50 1816.72) p2 (list 0.00 0.00))
 (command "TEXT" "J" "ML" p1   0.75  0.00 "137")
 (command "LAYER" "S" "CGBTHK" "")
 (setq p1 (list 226.00 1816.72) p2 (list 0.00 0.00))
 (command "TEXT" "J" "ML" p1   0.75  0.00 "3.11")
 (command "LAYER" "S" "CGBHZID" "")
 (setq p1 (list 230.50 1816.72) p2 (list 0.00 0.00))
 (command "TEXT" "J" "ML" p1   0.75  0.00 "")
 (setq p1 (list 232.75 1816.72) p2 (list 0.00 0.00))
 (command "TEXT" "J" "ML" p1   0.75  0.00 "8451")
 (command "LAYER" "S" "CGBLITHTXT" "")
 (setq p1 (list 236.50 1816.72) p2 (list 0.00 0.00))
 (command "TEXT" "J" "ML" p1   0.75  0.00 "LT GRY GRN FIRECLAY")
 (command "LAYER" "S" "CGBCMNT" "")
 (setq p1 (list 256.75 1816.72) p2 (list 0.00 0.00))
 (command "TEXT" "J" "ML" p1   0.75  0.00 "V SFT,BRKN")
 (command "LAYER" "S" "CGBMAIN" "")
 (setq p1 (list 214.00 1819.01) p2 (list 220.00 1819.01) p3 (list 220.00 1818.04) p4 (list 214.00 1818.04))
 (command "PLINE" p1 p2 p3 p4 "c")
 (command "HATCH" "ZIGZAG" 5.00 0.00 "L" "")
 (command "COLOR" "BYLAYER")
 (command "LAYER" "S" "CGBLITHCD" "")
 (setq p1 (list 220.00 1818.53) p2 (list 221.35 1815.84))
 (command "LINE" p1 p2 "")
 (setq p1 (list 221.50 1815.47) p2 (list 0.00 0.00))
 (command "TEXT" "J" "ML" p1   0.75  0.00 "227")
 (command "LAYER" "S" "CGBTHK" "")
 (setq p1 (list 226.00 1815.47) p2 (list 0.00 0.00))
 (command "TEXT" "J" "ML" p1   0.75  0.00 "0.97")
 (command "LAYER" "S" "CGBHZID" "")
 (setq p1 (list 230.50 1815.47) p2 (list 0.00 0.00))
 (command "TEXT" "J" "ML" p1   0.75  0.00 "")
 (setq p1 (list 232.75 1815.47) p2 (list 0.00 0.00))
 (command "TEXT" "J" "ML" p1   0.75  0.00 "8451")
 (command "LAYER" "S" "CGBLITHTXT" "")
 (setq p1 (list 236.50 1815.47) p2 (list 0.00 0.00))
 (command "TEXT" "J" "ML" p1   0.75  0.00 "DRK GRY FIRECLAY W/LS NOD")
 (command "LAYER" "S" "CGBCMNT" "")
 (setq p1 (list 256.75 1815.47) p2 (list 0.00 0.00))
 (command "TEXT" "J" "ML" p1   0.75  0.00 "MTTLD,SLX")
 (command "LAYER" "S" "CGBMAIN" "")
 (setq p1 (list 214.00 1818.04) p2 (list 220.00 1818.04) p3 (list 220.00 1815.98) p4 (list 214.00 1815.98))
 (command "PLINE" p1 p2 p3 p4 "c")
 (command "HATCH" "ZIGZAG" 4.00 0.00 "L" "")
 (command "COLOR" "BYLAYER")
 (command "LAYER" "S" "CGBLITHCD" "")
 (setq p1 (list 220.00 1817.01) p2 (list 221.35 1814.59))
 (command "LINE" p1 p2 "")
 (setq p1 (list 221.50 1814.22) p2 (list 0.00 0.00))
 (command "TEXT" "J" "ML" p1   0.75  0.00 "125")
 (command "LAYER" "S" "CGBTHK" "")
 (setq p1 (list 226.00 1814.22) p2 (list 0.00 0.00))
 (command "TEXT" "J" "ML" p1   0.75  0.00 "2.06")
 (command "LAYER" "S" "CGBHZID" "")
 (setq p1 (list 230.50 1814.22) p2 (list 0.00 0.00))
 (command "TEXT" "J" "ML" p1   0.75  0.00 "")
 (setq p1 (list 232.75 1814.22) p2 (list 0.00 0.00))
 (command "TEXT" "J" "ML" p1   0.75  0.00 "8451")
 (command "LAYER" "S" "CGBLITHTXT" "")
 (setq p1 (list 236.50 1814.22) p2 (list 0.00 0.00))
 (command "TEXT" "J" "ML" p1   0.75  0.00 "DRK GRY CHRND SH")
 (command "LAYER" "S" "CGBCMNT" "")
 (setq p1 (list 256.75 1814.22) p2 (list 0.00 0.00))
 (command "TEXT" "J" "ML" p1   0.75  0.00 "MTTLD,CRMB")
 (command "LAYER" "S" "CGBMAIN" "")
 (setq p1 (list 214.00 1815.98) p2 (list 220.00 1815.98) p3 (list 220.00 1811.78) p4 (list 214.00 1811.78))
 (command "PLINE" p1 p2 p3 p4 "c")
 (command "HATCH" "ZIGZAG" 5.00 0.00 "L" "")
 (command "COLOR" "BYLAYER")
 (command "LAYER" "S" "CGBLITHCD" "")
 (setq p1 (list 220.00 1813.88) p2 (list 221.35 1813.34))
 (command "LINE" p1 p2 "")
 (setq p1 (list 221.50 1812.97) p2 (list 0.00 0.00))
 (command "TEXT" "J" "ML" p1   0.75  0.00 "174")
 (command "LAYER" "S" "CGBTHK" "")
 (setq p1 (list 226.00 1812.97) p2 (list 0.00 0.00))
 (command "TEXT" "J" "ML" p1   0.75  0.00 "4.20")
 (command "LAYER" "S" "CGBHZID" "")
 (setq p1 (list 230.50 1812.97) p2 (list 0.00 0.00))
 (command "TEXT" "J" "ML" p1   0.75  0.00 "")
 (setq p1 (list 232.75 1812.97) p2 (list 0.00 0.00))
 (command "TEXT" "J" "ML" p1   0.75  0.00 "8451")
 (command "LAYER" "S" "CGBLITHTXT" "")
 (setq p1 (list 236.50 1812.97) p2 (list 0.00 0.00))
 (command "TEXT" "J" "ML" p1   0.75  0.00 "GRY/GRN SH")
 (command "LAYER" "S" "CGBCMNT" "")
 (setq p1 (list 256.75 1812.97) p2 (list 0.00 0.00))
 (command "TEXT" "J" "ML" p1   0.75  0.00 "MTTLD,BRKN")
 (command "LAYER" "S" "CGBMAIN" "")
 (setq p1 (list 214.00 1811.78) p2 (list 220.00 1811.78) p3 (list 220.00 1810.37) p4 (list 214.00 1810.37))
 (command "PLINE" p1 p2 p3 p4 "c")
 (command "HATCH" "ZIGZAG" 4.00 0.00 "L" "")
 (command "COLOR" "BYLAYER")
 (command "LAYER" "S" "CGBLITHCD" "")
 (setq p1 (list 220.00 1811.08) p2 (list 221.35 1811.08))
 (command "LINE" p1 p2 "")
 (setq p1 (list 221.50 1810.70) p2 (list 0.00 0.00))
 (command "TEXT" "J" "ML" p1   0.75  0.00 "474")
 (command "LAYER" "S" "CGBTHK" "")
 (setq p1 (list 226.00 1810.70) p2 (list 0.00 0.00))
 (command "TEXT" "J" "ML" p1   0.75  0.00 "1.41")
 (command "LAYER" "S" "CGBHZID" "")
 (setq p1 (list 230.50 1810.70) p2 (list 0.00 0.00))
 (command "TEXT" "J" "ML" p1   0.75  0.00 "")
 (setq p1 (list 232.75 1810.70) p2 (list 0.00 0.00))
 (command "TEXT" "J" "ML" p1   0.75  0.00 "8451")
 (command "LAYER" "S" "CGBLITHTXT" "")
 (setq p1 (list 236.50 1810.70) p2 (list 0.00 0.00))
 (command "TEXT" "J" "ML" p1   0.75  0.00 "GRY/GRN SDY SH W/LS NODS")
 (command "LAYER" "S" "CGBCMNT" "")
 (setq p1 (list 256.75 1810.70) p2 (list 0.00 0.00))
 (command "TEXT" "J" "ML" p1   0.75  0.00 "")
 (command "LAYER" "S" "CGBMAIN" "")
 (setq p1 (list 214.00 1810.37) p2 (list 220.00 1810.37) p3 (list 220.00 1807.12) p4 (list 214.00 1807.12))
 (command "PLINE" p1 p2 p3 p4 "c")
 (command "HATCH" "ZIGZAG" 4.00 0.00 "L" "")
 (command "COLOR" "BYLAYER")
 (command "LAYER" "S" "CGBLITHCD" "")
 (setq p1 (list 220.00 1808.75) p2 (list 221.35 1808.75))
 (command "LINE" p1 p2 "")
 (setq p1 (list 221.50 1808.37) p2 (list 0.00 0.00))
 (command "TEXT" "J" "ML" p1   0.75  0.00 "474")
 (command "LAYER" "S" "CGBTHK" "")
 (setq p1 (list 226.00 1808.37) p2 (list 0.00 0.00))
 (command "TEXT" "J" "ML" p1   0.75  0.00 "3.25")
 (command "LAYER" "S" "CGBHZID" "")
 (setq p1 (list 230.50 1808.37) p2 (list 0.00 0.00))
 (command "TEXT" "J" "ML" p1   0.75  0.00 "")
 (setq p1 (list 232.75 1808.37) p2 (list 0.00 0.00))
 (command "TEXT" "J" "ML" p1   0.75  0.00 "8451")
 (command "LAYER" "S" "CGBLITHTXT" "")
 (setq p1 (list 236.50 1808.37) p2 (list 0.00 0.00))
 (command "TEXT" "J" "ML" p1   0.75  0.00 "GRY/GRN SDY SH W/LS NODS")
 (command "LAYER" "S" "CGBCMNT" "")
 (setq p1 (list 256.75 1808.37) p2 (list 0.00 0.00))
 (command "TEXT" "J" "ML" p1   0.75  0.00 "RIP W/SS STKS")
 (command "LAYER" "S" "CGBMAIN" "")
 (setq p1 (list 214.00 1807.12) p2 (list 220.00 1807.12) p3 (list 220.00 1802.66) p4 (list 214.00 1802.66))
 (command "PLINE" p1 p2 p3 p4 "c")
 (command "HATCH" "ZIGZAG" 4.00 0.00 "L" "")
 (command "COLOR" "BYLAYER")
 (command "LAYER" "S" "CGBLITHCD" "")
 (setq p1 (list 220.00 1804.89) p2 (list 221.35 1804.89))
 (command "LINE" p1 p2 "")
 (setq p1 (list 221.50 1804.52) p2 (list 0.00 0.00))
 (command "TEXT" "J" "ML" p1   0.75  0.00 "474")
 (command "LAYER" "S" "CGBTHK" "")
 (setq p1 (list 226.00 1804.52) p2 (list 0.00 0.00))
 (command "TEXT" "J" "ML" p1   0.75  0.00 "4.46")
 (command "LAYER" "S" "CGBHZID" "")
 (setq p1 (list 230.50 1804.52) p2 (list 0.00 0.00))
 (command "TEXT" "J" "ML" p1   0.75  0.00 "")
 (setq p1 (list 232.75 1804.52) p2 (list 0.00 0.00))
 (command "TEXT" "J" "ML" p1   0.75  0.00 "8451")
 (command "LAYER" "S" "CGBLITHTXT" "")
 (setq p1 (list 236.50 1804.52) p2 (list 0.00 0.00))
 (command "TEXT" "J" "ML" p1   0.75  0.00 "GRY/GRN SDY SH W/LS NODS")
 (command "LAYER" "S" "CGBCMNT" "")
 (setq p1 (list 256.75 1804.52) p2 (list 0.00 0.00))
 (command "TEXT" "J" "ML" p1   0.75  0.00 "CALC VEINS")
 (command "LAYER" "S" "CGBMAIN" "")
 (setq p1 (list 214.00 1802.66) p2 (list 220.00 1802.66) p3 (list 220.00 1798.10) p4 (list 214.00 1798.10))
 (command "PLINE" p1 p2 p3 p4 "c")
 (command "HATCH" "ZIGZAG" 4.00 0.00 "L" "")
 (command "COLOR" "BYLAYER")
 (command "LAYER" "S" "CGBLITHCD" "")
 (setq p1 (list 220.00 1800.38) p2 (list 221.35 1800.38))
 (command "LINE" p1 p2 "")
 (setq p1 (list 221.50 1800.01) p2 (list 0.00 0.00))
 (command "TEXT" "J" "ML" p1   0.75  0.00 "373")
 (command "LAYER" "S" "CGBTHK" "")
 (setq p1 (list 226.00 1800.01) p2 (list 0.00 0.00))
 (command "TEXT" "J" "ML" p1   0.75  0.00 "4.56")
 (command "LAYER" "S" "CGBHZID" "")
 (setq p1 (list 230.50 1800.01) p2 (list 0.00 0.00))
 (command "TEXT" "J" "ML" p1   0.75  0.00 "")
 (setq p1 (list 232.75 1800.01) p2 (list 0.00 0.00))
 (command "TEXT" "J" "ML" p1   0.75  0.00 "8451")
 (command "LAYER" "S" "CGBLITHTXT" "")
 (setq p1 (list 236.50 1800.01) p2 (list 0.00 0.00))
 (command "TEXT" "J" "ML" p1   0.75  0.00 "GRY/GRN SH W/SS STKS")
 (command "LAYER" "S" "CGBCMNT" "")
 (setq p1 (list 256.75 1800.01) p2 (list 0.00 0.00))
 (command "TEXT" "J" "ML" p1   0.75  0.00 "RIP,CALC")
 (command "LAYER" "S" "CGBMAIN" "")
 (setq p1 (list 214.00 1798.10) p2 (list 220.00 1798.10) p3 (list 220.00 1794.23) p4 (list 214.00 1794.23))
 (command "PLINE" p1 p2 p3 p4 "c")
 (command "HATCH" "ZIGZAG" 4.00 0.00 "L" "")
 (command "COLOR" "BYLAYER")
 (command "LAYER" "S" "CGBLITHCD" "")
 (setq p1 (list 220.00 1796.17) p2 (list 221.35 1796.17))
 (command "LINE" p1 p2 "")
 (setq p1 (list 221.50 1795.79) p2 (list 0.00 0.00))
 (command "TEXT" "J" "ML" p1   0.75  0.00 "373")
 (command "LAYER" "S" "CGBTHK" "")
 (setq p1 (list 226.00 1795.79) p2 (list 0.00 0.00))
 (command "TEXT" "J" "ML" p1   0.75  0.00 "3.87")
 (command "LAYER" "S" "CGBHZID" "")
 (setq p1 (list 230.50 1795.79) p2 (list 0.00 0.00))
 (command "TEXT" "J" "ML" p1   0.75  0.00 "")
 (setq p1 (list 232.75 1795.79) p2 (list 0.00 0.00))
 (command "TEXT" "J" "ML" p1   0.75  0.00 "8451")
 (command "LAYER" "S" "CGBLITHTXT" "")
 (setq p1 (list 236.50 1795.79) p2 (list 0.00 0.00))
 (command "TEXT" "J" "ML" p1   0.75  0.00 "GRY/GRN SH W/SS STKS")
 (command "LAYER" "S" "CGBCMNT" "")
 (setq p1 (list 256.75 1795.79) p2 (list 0.00 0.00))
 (command "TEXT" "J" "ML" p1   0.75  0.00 "BURRS,SLC")
 (command "LAYER" "S" "CGBMAIN" "")
 (setq p1 (list 214.00 1794.23) p2 (list 220.00 1794.23) p3 (list 220.00 1793.88) p4 (list 214.00 1793.88))
 (command "PLINE" p1 p2 p3 p4 "c")
 (command "HATCH" "ZIGZAG" 0.25 0.00 "L" "")
 (command "COLOR" "BYLAYER")
 (command "LAYER" "S" "CGBLITHCD" "")
 (setq p1 (list 220.00 1794.06) p2 (list 221.35 1794.06))
 (command "LINE" p1 p2 "")
 (setq p1 (list 221.50 1793.68) p2 (list 0.00 0.00))
 (command "TEXT" "J" "ML" p1   0.75  0.00 "741")
 (command "LAYER" "S" "CGBTHK" "")
 (setq p1 (list 226.00 1793.68) p2 (list 0.00 0.00))
 (command "TEXT" "J" "ML" p1   0.75  0.00 "0.35")
 (command "LAYER" "S" "CGBHZID" "")
 (setq p1 (list 230.50 1793.68) p2 (list 0.00 0.00))
 (command "TEXT" "J" "ML" p1   0.75  0.00 "")
 (setq p1 (list 232.75 1793.68) p2 (list 0.00 0.00))
 (command "TEXT" "J" "ML" p1   0.75  0.00 "8451")
 (command "LAYER" "S" "CGBLITHTXT" "")
 (setq p1 (list 236.50 1793.68) p2 (list 0.00 0.00))
 (command "TEXT" "J" "ML" p1   0.75  0.00 "GRY SH+/OR IRNSTN PEB CGL")
 (command "LAYER" "S" "CGBCMNT" "")
 (setq p1 (list 256.75 1793.68) p2 (list 0.00 0.00))
 (command "TEXT" "J" "ML" p1   0.75  0.00 "")
 (command "LAYER" "S" "CGBMAIN" "")
 (setq p1 (list 214.00 1793.88) p2 (list 220.00 1793.88) p3 (list 220.00 1791.94) p4 (list 214.00 1791.94))
 (command "PLINE" p1 p2 p3 p4 "c")
 (command "HATCH" "ZIGZAG" 4.00 0.00 "L" "")
 (command "COLOR" "BYLAYER")
 (command "LAYER" "S" "CGBLITHCD" "")
 (setq p1 (list 220.00 1792.91) p2 (list 221.35 1791.66))
 (command "LINE" p1 p2 "")
 (setq p1 (list 221.50 1791.29) p2 (list 0.00 0.00))
 (command "TEXT" "J" "ML" p1   0.75  0.00 "541")
 (command "LAYER" "S" "CGBTHK" "")
 (setq p1 (list 226.00 1791.29) p2 (list 0.00 0.00))
 (command "TEXT" "J" "ML" p1   0.75  0.00 "1.94")
 (command "LAYER" "S" "CGBHZID" "")
 (setq p1 (list 230.50 1791.29) p2 (list 0.00 0.00))
 (command "TEXT" "J" "ML" p1   0.75  0.00 "")
 (setq p1 (list 232.75 1791.29) p2 (list 0.00 0.00))
 (command "TEXT" "J" "ML" p1   0.75  0.00 "8451")
 (command "LAYER" "S" "CGBLITHTXT" "")
 (setq p1 (list 236.50 1791.29) p2 (list 0.00 0.00))
 (command "TEXT" "J" "ML" p1   0.75  0.00 "GRY CROSSBED SS")
 (command "LAYER" "S" "CGBCMNT" "")
 (setq p1 (list 256.75 1791.29) p2 (list 0.00 0.00))
 (command "TEXT" "J" "ML" p1   0.75  0.00 "")
 (command "LAYER" "S" "CGBMAIN" "")
 (setq p1 (list 214.00 1791.94) p2 (list 220.00 1791.94) p3 (list 220.00 1786.94) p4 (list 214.00 1786.94))
 (command "PLINE" p1 p2 p3 p4 "c")
 (command "HATCH" "ZIGZAG" 4.00 0.00 "L" "")
 (command "COLOR" "BYLAYER")
 (command "LAYER" "S" "CGBLITHCD" "")
 (setq p1 (list 220.00 1789.44) p2 (list 221.35 1789.44))
 (command "LINE" p1 p2 "")
 (setq p1 (list 221.50 1789.07) p2 (list 0.00 0.00))
 (command "TEXT" "J" "ML" p1   0.75  0.00 "544")
 (command "LAYER" "S" "CGBTHK" "")
 (setq p1 (list 226.00 1789.07) p2 (list 0.00 0.00))
 (command "TEXT" "J" "ML" p1   0.75  0.00 "5.00")
 (command "LAYER" "S" "CGBHZID" "")
 (setq p1 (list 230.50 1789.07) p2 (list 0.00 0.00))
 (command "TEXT" "J" "ML" p1   0.75  0.00 "")
 (setq p1 (list 232.75 1789.07) p2 (list 0.00 0.00))
 (command "TEXT" "J" "ML" p1   0.75  0.00 "8451")
 (command "LAYER" "S" "CGBLITHTXT" "")
 (setq p1 (list 236.50 1789.07) p2 (list 0.00 0.00))
 (command "TEXT" "J" "ML" p1   0.75  0.00 "GRY MASS SS")
 (command "LAYER" "S" "CGBCMNT" "")
 (setq p1 (list 256.75 1789.07) p2 (list 0.00 0.00))
 (command "TEXT" "J" "ML" p1   0.75  0.00 "SLC")
 (command "LAYER" "S" "CGBMAIN" "")
 (setq p1 (list 214.00 1786.94) p2 (list 220.00 1786.94) p3 (list 220.00 1784.56) p4 (list 214.00 1784.56))
 (command "PLINE" p1 p2 p3 p4 "c")
 (command "HATCH" "ZIGZAG" 4.00 0.00 "L" "")
 (command "COLOR" "BYLAYER")
 (command "LAYER" "S" "CGBLITHCD" "")
 (setq p1 (list 220.00 1785.75) p2 (list 221.35 1785.75))
 (command "LINE" p1 p2 "")
 (setq p1 (list 221.50 1785.38) p2 (list 0.00 0.00))
 (command "TEXT" "J" "ML" p1   0.75  0.00 "374")
 (command "LAYER" "S" "CGBTHK" "")
 (setq p1 (list 226.00 1785.38) p2 (list 0.00 0.00))
 (command "TEXT" "J" "ML" p1   0.75  0.00 "2.38")
 (command "LAYER" "S" "CGBHZID" "")
 (setq p1 (list 230.50 1785.38) p2 (list 0.00 0.00))
 (command "TEXT" "J" "ML" p1   0.75  0.00 "")
 (setq p1 (list 232.75 1785.38) p2 (list 0.00 0.00))
 (command "TEXT" "J" "ML" p1   0.75  0.00 "8451")
 (command "LAYER" "S" "CGBLITHTXT" "")
 (setq p1 (list 236.50 1785.38) p2 (list 0.00 0.00))
 (command "TEXT" "J" "ML" p1   0.75  0.00 "GRY/GRN SDY SH")
 (command "LAYER" "S" "CGBCMNT" "")
 (setq p1 (list 256.75 1785.38) p2 (list 0.00 0.00))
 (command "TEXT" "J" "ML" p1   0.75  0.00 "")
 (command "LAYER" "S" "CGBMAIN" "")
 (setq p1 (list 214.00 1784.56) p2 (list 220.00 1784.56) p3 (list 220.00 1783.00) p4 (list 214.00 1783.00))
 (command "PLINE" p1 p2 p3 p4 "c")
 (command "HATCH" "ZIGZAG" 4.00 0.00 "L" "")
 (command "COLOR" "BYLAYER")
 (command "LAYER" "S" "CGBLITHCD" "")
 (setq p1 (list 220.00 1783.78) p2 (list 221.35 1783.78))
 (command "LINE" p1 p2 "")
 (setq p1 (list 221.50 1783.41) p2 (list 0.00 0.00))
 (command "TEXT" "J" "ML" p1   0.75  0.00 "374")
 (command "LAYER" "S" "CGBTHK" "")
 (setq p1 (list 226.00 1783.41) p2 (list 0.00 0.00))
 (command "TEXT" "J" "ML" p1   0.75  0.00 "1.56")
 (command "LAYER" "S" "CGBHZID" "")
 (setq p1 (list 230.50 1783.41) p2 (list 0.00 0.00))
 (command "TEXT" "J" "ML" p1   0.75  0.00 "")
 (setq p1 (list 232.75 1783.41) p2 (list 0.00 0.00))
 (command "TEXT" "J" "ML" p1   0.75  0.00 "8451")
 (command "LAYER" "S" "CGBLITHTXT" "")
 (setq p1 (list 236.50 1783.41) p2 (list 0.00 0.00))
 (command "TEXT" "J" "ML" p1   0.75  0.00 "GRY/GRN SDY SH")
 (command "LAYER" "S" "CGBCMNT" "")
 (setq p1 (list 256.75 1783.41) p2 (list 0.00 0.00))
 (command "TEXT" "J" "ML" p1   0.75  0.00 "DIST BEDS")
 (command "LAYER" "S" "CGBMAIN" "")
 (setq p1 (list 214.00 1783.00) p2 (list 220.00 1783.00) p3 (list 220.00 1782.51) p4 (list 214.00 1782.51))
 (command "PLINE" p1 p2 p3 p4 "c")
 (command "HATCH" "ZIGZAG" 0.25 0.00 "L" "")
 (command "COLOR" "BYLAYER")
 (command "LAYER" "S" "CGBLITHCD" "")
 (setq p1 (list 220.00 1782.76) p2 (list 221.35 1781.51))
 (command "LINE" p1 p2 "")
 (setq p1 (list 221.50 1781.13) p2 (list 0.00 0.00))
 (command "TEXT" "J" "ML" p1   0.75  0.00 "742")
 (command "LAYER" "S" "CGBTHK" "")
 (setq p1 (list 226.00 1781.13) p2 (list 0.00 0.00))
 (command "TEXT" "J" "ML" p1   0.75  0.00 "0.49")
 (command "LAYER" "S" "CGBHZID" "")
 (setq p1 (list 230.50 1781.13) p2 (list 0.00 0.00))
 (command "TEXT" "J" "ML" p1   0.75  0.00 "")
 (setq p1 (list 232.75 1781.13) p2 (list 0.00 0.00))
 (command "TEXT" "J" "ML" p1   0.75  0.00 "8451")
 (command "LAYER" "S" "CGBLITHTXT" "")
 (setq p1 (list 236.50 1781.13) p2 (list 0.00 0.00))
 (command "TEXT" "J" "ML" p1   0.75  0.00 "GRY SH PEB CGL")
 (command "LAYER" "S" "CGBCMNT" "")
 (setq p1 (list 256.75 1781.13) p2 (list 0.00 0.00))
 (command "TEXT" "J" "ML" p1   0.75  0.00 "SLC")
 (command "LAYER" "S" "CGBMAIN" "")
 (setq p1 (list 214.00 1782.51) p2 (list 220.00 1782.51) p3 (list 220.00 1781.84) p4 (list 214.00 1781.84))
 (command "PLINE" p1 p2 p3 p4 "c")
 (command "HATCH" "ZIGZAG" 4.00 0.00 "L" "")
 (command "COLOR" "BYLAYER")
 (command "LAYER" "S" "CGBLITHCD" "")
 (setq p1 (list 220.00 1782.18) p2 (list 221.35 1780.26))
 (command "LINE" p1 p2 "")
 (setq p1 (list 221.50 1779.88) p2 (list 0.00 0.00))
 (command "TEXT" "J" "ML" p1   0.75  0.00 "125")
 (command "LAYER" "S" "CGBTHK" "")
 (setq p1 (list 226.00 1779.88) p2 (list 0.00 0.00))
 (command "TEXT" "J" "ML" p1   0.75  0.00 "0.67")
 (command "LAYER" "S" "CGBHZID" "")
 (setq p1 (list 230.50 1779.88) p2 (list 0.00 0.00))
 (command "TEXT" "J" "ML" p1   0.75  0.00 "")
 (setq p1 (list 232.75 1779.88) p2 (list 0.00 0.00))
 (command "TEXT" "J" "ML" p1   0.75  0.00 "8451")
 (command "LAYER" "S" "CGBLITHTXT" "")
 (setq p1 (list 236.50 1779.88) p2 (list 0.00 0.00))
 (command "TEXT" "J" "ML" p1   0.75  0.00 "DRK GRY CHRND SH")
 (command "LAYER" "S" "CGBCMNT" "")
 (setq p1 (list 256.75 1779.88) p2 (list 0.00 0.00))
 (command "TEXT" "J" "ML" p1   0.75  0.00 "CRMBLD,SLX")
 (command "LAYER" "S" "CGBMAIN" "")
 (setq p1 (list 214.00 1781.84) p2 (list 220.00 1781.84) p3 (list 220.00 1781.34) p4 (list 214.00 1781.34))
 (command "PLINE" p1 p2 p3 p4 "c")
 (command "HATCH" "ZIGZAG" 5.00 0.00 "L" "")
 (command "COLOR" "BYLAYER")
 (command "LAYER" "S" "CGBLITHCD" "")
 (setq p1 (list 220.00 1781.59) p2 (list 221.35 1779.01))
 (command "LINE" p1 p2 "")
 (setq p1 (list 221.50 1778.63) p2 (list 0.00 0.00))
 (command "TEXT" "J" "ML" p1   0.75  0.00 "244")
 (command "LAYER" "S" "CGBTHK" "")
 (setq p1 (list 226.00 1778.63) p2 (list 0.00 0.00))
 (command "TEXT" "J" "ML" p1   0.75  0.00 "0.50")
 (command "LAYER" "S" "CGBHZID" "")
 (setq p1 (list 230.50 1778.63) p2 (list 0.00 0.00))
 (command "TEXT" "J" "ML" p1   0.75  0.00 "")
 (setq p1 (list 232.75 1778.63) p2 (list 0.00 0.00))
 (command "TEXT" "J" "ML" p1   0.75  0.00 "8451")
 (command "LAYER" "S" "CGBLITHTXT" "")
 (setq p1 (list 236.50 1778.63) p2 (list 0.00 0.00))
 (command "TEXT" "J" "ML" p1   0.75  0.00 "GRN SH W/LS NODS")
 (command "LAYER" "S" "CGBCMNT" "")
 (setq p1 (list 256.75 1778.63) p2 (list 0.00 0.00))
 (command "TEXT" "J" "ML" p1   0.75  0.00 "")
 (command "LAYER" "S" "CGBMAIN" "")
 (setq p1 (list 214.00 1781.34) p2 (list 220.00 1781.34) p3 (list 220.00 1776.94) p4 (list 214.00 1776.94))
 (command "PLINE" p1 p2 p3 p4 "c")
 (command "HATCH" "ZIGZAG" 4.00 0.00 "L" "")
 (command "COLOR" "BYLAYER")
 (command "LAYER" "S" "CGBLITHCD" "")
 (setq p1 (list 220.00 1779.14) p2 (list 221.35 1777.76))
 (command "LINE" p1 p2 "")
 (setq p1 (list 221.50 1777.38) p2 (list 0.00 0.00))
 (command "TEXT" "J" "ML" p1   0.75  0.00 "344")
 (command "LAYER" "S" "CGBTHK" "")
 (setq p1 (list 226.00 1777.38) p2 (list 0.00 0.00))
 (command "TEXT" "J" "ML" p1   0.75  0.00 "4.40")
 (command "LAYER" "S" "CGBHZID" "")
 (setq p1 (list 230.50 1777.38) p2 (list 0.00 0.00))
 (command "TEXT" "J" "ML" p1   0.75  0.00 "")
 (setq p1 (list 232.75 1777.38) p2 (list 0.00 0.00))
 (command "TEXT" "J" "ML" p1   0.75  0.00 "8451")
 (command "LAYER" "S" "CGBLITHTXT" "")
 (setq p1 (list 236.50 1777.38) p2 (list 0.00 0.00))
 (command "TEXT" "J" "ML" p1   0.75  0.00 "GRN MASS SDY SH")
 (command "LAYER" "S" "CGBCMNT" "")
 (setq p1 (list 256.75 1777.38) p2 (list 0.00 0.00))
 (command "TEXT" "J" "ML" p1   0.75  0.00 "")
 (command "LAYER" "S" "CGBMAIN" "")
 (setq p1 (list 214.00 1776.94) p2 (list 220.00 1776.94) p3 (list 220.00 1767.84) p4 (list 214.00 1767.84))
 (command "PLINE" p1 p2 p3 p4 "c")
 (command "HATCH" "ZIGZAG" 4.00 0.00 "L" "")
 (command "COLOR" "BYLAYER")
 (command "LAYER" "S" "CGBLITHCD" "")
 (setq p1 (list 220.00 1772.39) p2 (list 221.35 1772.39))
 (command "LINE" p1 p2 "")
 (setq p1 (list 221.50 1772.02) p2 (list 0.00 0.00))
 (command "TEXT" "J" "ML" p1   0.75  0.00 "344")
 (command "LAYER" "S" "CGBTHK" "")
 (setq p1 (list 226.00 1772.02) p2 (list 0.00 0.00))
 (command "TEXT" "J" "ML" p1   0.75  0.00 "9.10")
 (command "LAYER" "S" "CGBHZID" "")
 (setq p1 (list 230.50 1772.02) p2 (list 0.00 0.00))
 (command "TEXT" "J" "ML" p1   0.75  0.00 "")
 (setq p1 (list 232.75 1772.02) p2 (list 0.00 0.00))
 (command "TEXT" "J" "ML" p1   0.75  0.00 "8451")
 (command "LAYER" "S" "CGBLITHTXT" "")
 (setq p1 (list 236.50 1772.02) p2 (list 0.00 0.00))
 (command "TEXT" "J" "ML" p1   0.75  0.00 "GRN MASS SDY SH")
 (command "LAYER" "S" "CGBCMNT" "")
 (setq p1 (list 256.75 1772.02) p2 (list 0.00 0.00))
 (command "TEXT" "J" "ML" p1   0.75  0.00 "ANG FRACS @ T")
 (command "LAYER" "S" "CGBMAIN" "")
 (setq p1 (list 214.00 1767.84) p2 (list 220.00 1767.84) p3 (list 220.00 1762.19) p4 (list 214.00 1762.19))
 (command "PLINE" p1 p2 p3 p4 "c")
 (command "HATCH" "ZIGZAG" 4.00 0.00 "L" "")
 (command "COLOR" "BYLAYER")
 (command "LAYER" "S" "CGBLITHCD" "")
 (setq p1 (list 220.00 1765.02) p2 (list 221.35 1765.02))
 (command "LINE" p1 p2 "")
 (setq p1 (list 221.50 1764.64) p2 (list 0.00 0.00))
 (command "TEXT" "J" "ML" p1   0.75  0.00 "374")
 (command "LAYER" "S" "CGBTHK" "")
 (setq p1 (list 226.00 1764.64) p2 (list 0.00 0.00))
 (command "TEXT" "J" "ML" p1   0.75  0.00 "5.65")
 (command "LAYER" "S" "CGBHZID" "")
 (setq p1 (list 230.50 1764.64) p2 (list 0.00 0.00))
 (command "TEXT" "J" "ML" p1   0.75  0.00 "")
 (setq p1 (list 232.75 1764.64) p2 (list 0.00 0.00))
 (command "TEXT" "J" "ML" p1   0.75  0.00 "8451")
 (command "LAYER" "S" "CGBLITHTXT" "")
 (setq p1 (list 236.50 1764.64) p2 (list 0.00 0.00))
 (command "TEXT" "J" "ML" p1   0.75  0.00 "GRY/GRN SDY SH")
 (command "LAYER" "S" "CGBCMNT" "")
 (setq p1 (list 256.75 1764.64) p2 (list 0.00 0.00))
 (command "TEXT" "J" "ML" p1   0.75  0.00 "GB")
 (command "LAYER" "S" "CGBMAIN" "")
 (setq p1 (list 214.00 1762.19) p2 (list 220.00 1762.19) p3 (list 220.00 1761.38) p4 (list 214.00 1761.38))
 (command "PLINE" p1 p2 p3 p4 "c")
 (command "HATCH" "ZIGZAG" 4.00 0.00 "L" "")
 (command "COLOR" "BYLAYER")
 (command "LAYER" "S" "CGBLITHCD" "")
 (setq p1 (list 220.00 1761.79) p2 (list 221.35 1761.79))
 (command "LINE" p1 p2 "")
 (setq p1 (list 221.50 1761.41) p2 (list 0.00 0.00))
 (command "TEXT" "J" "ML" p1   0.75  0.00 "474")
 (command "LAYER" "S" "CGBTHK" "")
 (setq p1 (list 226.00 1761.41) p2 (list 0.00 0.00))
 (command "TEXT" "J" "ML" p1   0.75  0.00 "0.81")
 (command "LAYER" "S" "CGBHZID" "")
 (setq p1 (list 230.50 1761.41) p2 (list 0.00 0.00))
 (command "TEXT" "J" "ML" p1   0.75  0.00 "")
 (setq p1 (list 232.75 1761.41) p2 (list 0.00 0.00))
 (command "TEXT" "J" "ML" p1   0.75  0.00 "8451")
 (command "LAYER" "S" "CGBLITHTXT" "")
 (setq p1 (list 236.50 1761.41) p2 (list 0.00 0.00))
 (command "TEXT" "J" "ML" p1   0.75  0.00 "GRY/GRN SDY SH W/LS NODS")
 (command "LAYER" "S" "CGBCMNT" "")
 (setq p1 (list 256.75 1761.41) p2 (list 0.00 0.00))
 (command "TEXT" "J" "ML" p1   0.75  0.00 "")
 (command "LAYER" "S" "CGBMAIN" "")
 (setq p1 (list 214.00 1761.38) p2 (list 220.00 1761.38) p3 (list 220.00 1760.08) p4 (list 214.00 1760.08))
 (command "PLINE" p1 p2 p3 p4 "c")
 (command "HATCH" "ZIGZAG" 5.00 0.00 "L" "")
 (command "COLOR" "BYLAYER")
 (command "LAYER" "S" "CGBLITHCD" "")
 (setq p1 (list 220.00 1760.73) p2 (list 221.35 1759.48))
 (command "LINE" p1 p2 "")
 (setq p1 (list 221.50 1759.11) p2 (list 0.00 0.00))
 (command "TEXT" "J" "ML" p1   0.75  0.00 "244")
 (command "LAYER" "S" "CGBTHK" "")
 (setq p1 (list 226.00 1759.11) p2 (list 0.00 0.00))
 (command "TEXT" "J" "ML" p1   0.75  0.00 "1.30")
 (command "LAYER" "S" "CGBHZID" "")
 (setq p1 (list 230.50 1759.11) p2 (list 0.00 0.00))
 (command "TEXT" "J" "ML" p1   0.75  0.00 "")
 (setq p1 (list 232.75 1759.11) p2 (list 0.00 0.00))
 (command "TEXT" "J" "ML" p1   0.75  0.00 "8451")
 (command "LAYER" "S" "CGBLITHTXT" "")
 (setq p1 (list 236.50 1759.11) p2 (list 0.00 0.00))
 (command "TEXT" "J" "ML" p1   0.75  0.00 "GRN SH W/LS NODS")
 (command "LAYER" "S" "CGBCMNT" "")
 (setq p1 (list 256.75 1759.11) p2 (list 0.00 0.00))
 (command "TEXT" "J" "ML" p1   0.75  0.00 "FNS UP")
 (command "LAYER" "S" "CGBMAIN" "")
 (setq p1 (list 214.00 1760.08) p2 (list 220.00 1760.08) p3 (list 220.00 1757.28) p4 (list 214.00 1757.28))
 (command "PLINE" p1 p2 p3 p4 "c")
 (command "HATCH" "ZIGZAG" 4.00 0.00 "L" "")
 (command "COLOR" "BYLAYER")
 (command "LAYER" "S" "CGBLITHCD" "")
 (setq p1 (list 220.00 1758.68) p2 (list 221.35 1758.23))
 (command "LINE" p1 p2 "")
 (setq p1 (list 221.50 1757.86) p2 (list 0.00 0.00))
 (command "TEXT" "J" "ML" p1   0.75  0.00 "374")
 (command "LAYER" "S" "CGBTHK" "")
 (setq p1 (list 226.00 1757.86) p2 (list 0.00 0.00))
 (command "TEXT" "J" "ML" p1   0.75  0.00 "2.80")
 (command "LAYER" "S" "CGBHZID" "")
 (setq p1 (list 230.50 1757.86) p2 (list 0.00 0.00))
 (command "TEXT" "J" "ML" p1   0.75  0.00 "")
 (setq p1 (list 232.75 1757.86) p2 (list 0.00 0.00))
 (command "TEXT" "J" "ML" p1   0.75  0.00 "8451")
 (command "LAYER" "S" "CGBLITHTXT" "")
 (setq p1 (list 236.50 1757.86) p2 (list 0.00 0.00))
 (command "TEXT" "J" "ML" p1   0.75  0.00 "GRY/GRN SDY SH")
 (command "LAYER" "S" "CGBCMNT" "")
 (setq p1 (list 256.75 1757.86) p2 (list 0.00 0.00))
 (command "TEXT" "J" "ML" p1   0.75  0.00 "SLC")
 (command "LAYER" "S" "CGBMAIN" "")
 (setq p1 (list 214.00 1757.28) p2 (list 220.00 1757.28) p3 (list 220.00 1757.01) p4 (list 214.00 1757.01))
 (command "PLINE" p1 p2 p3 p4 "c")
 (command "HATCH" "ZIGZAG" 5.00 0.00 "L" "")
 (command "COLOR" "BYLAYER")
 (command "LAYER" "S" "CGBLITHCD" "")
 (setq p1 (list 220.00 1757.15) p2 (list 221.35 1756.98))
 (command "LINE" p1 p2 "")
 (setq p1 (list 221.50 1756.61) p2 (list 0.00 0.00))
 (command "TEXT" "J" "ML" p1   0.75  0.00 "074")
 (command "LAYER" "S" "CGBTHK" "")
 (setq p1 (list 226.00 1756.61) p2 (list 0.00 0.00))
 (command "TEXT" "J" "ML" p1   0.75  0.00 "0.27")
 (command "LAYER" "S" "CGBHZID" "")
 (setq p1 (list 230.50 1756.61) p2 (list 0.00 0.00))
 (command "TEXT" "J" "ML" p1   0.75  0.00 "")
 (setq p1 (list 232.75 1756.61) p2 (list 0.00 0.00))
 (command "TEXT" "J" "ML" p1   0.75  0.00 "8451")
 (command "LAYER" "S" "CGBLITHTXT" "")
 (setq p1 (list 236.50 1756.61) p2 (list 0.00 0.00))
 (command "TEXT" "J" "ML" p1   0.75  0.00 "MASS IRNSTN")
 (command "LAYER" "S" "CGBCMNT" "")
 (setq p1 (list 256.75 1756.61) p2 (list 0.00 0.00))
 (command "TEXT" "J" "ML" p1   0.75  0.00 "")
 (command "LAYER" "S" "CGBMAIN" "")
 (setq p1 (list 214.00 1757.01) p2 (list 220.00 1757.01) p3 (list 220.00 1756.01) p4 (list 214.00 1756.01))
 (command "PLINE" p1 p2 p3 p4 "c")
 (command "HATCH" "ZIGZAG" 0.50 0.00 "L" "")
 (command "COLOR" "BYLAYER")
 (command "LAYER" "S" "CGBLITHCD" "")
 (setq p1 (list 220.00 1756.51) p2 (list 221.35 1755.73))
 (command "LINE" p1 p2 "")
 (setq p1 (list 221.50 1755.36) p2 (list 0.00 0.00))
 (command "TEXT" "J" "ML" p1   0.75  0.00 "323")
 (command "LAYER" "S" "CGBTHK" "")
 (setq p1 (list 226.00 1755.36) p2 (list 0.00 0.00))
 (command "TEXT" "J" "ML" p1   0.75  0.00 "1.00")
 (command "LAYER" "S" "CGBHZID" "")
 (setq p1 (list 230.50 1755.36) p2 (list 0.00 0.00))
 (command "TEXT" "J" "ML" p1   0.75  0.00 "")
 (setq p1 (list 232.75 1755.36) p2 (list 0.00 0.00))
 (command "TEXT" "J" "ML" p1   0.75  0.00 "8451")
 (command "LAYER" "S" "CGBLITHTXT" "")
 (setq p1 (list 236.50 1755.36) p2 (list 0.00 0.00))
 (command "TEXT" "J" "ML" p1   0.75  0.00 "DRK GRY SH W/SS STKS")
 (command "LAYER" "S" "CGBCMNT" "")
 (setq p1 (list 256.75 1755.36) p2 (list 0.00 0.00))
 (command "TEXT" "J" "ML" p1   0.75  0.00 "")
 (command "LAYER" "S" "CGBMAIN" "")
 (setq p1 (list 214.00 1756.01) p2 (list 220.00 1756.01) p3 (list 220.00 1755.22) p4 (list 214.00 1755.22))
 (command "PLINE" p1 p2 p3 p4 "c")
 (command "HATCH" "ZIGZAG" 4.00 0.00 "L" "")
 (command "COLOR" "BYLAYER")
 (command "LAYER" "S" "CGBLITHCD" "")
 (setq p1 (list 220.00 1755.62) p2 (list 221.35 1754.48))
 (command "LINE" p1 p2 "")
 (setq p1 (list 221.50 1754.11) p2 (list 0.00 0.00))
 (command "TEXT" "J" "ML" p1   0.75  0.00 "544")
 (command "LAYER" "S" "CGBTHK" "")
 (setq p1 (list 226.00 1754.11) p2 (list 0.00 0.00))
 (command "TEXT" "J" "ML" p1   0.75  0.00 "0.79")
 (command "LAYER" "S" "CGBHZID" "")
 (setq p1 (list 230.50 1754.11) p2 (list 0.00 0.00))
 (command "TEXT" "J" "ML" p1   0.75  0.00 "")
 (setq p1 (list 232.75 1754.11) p2 (list 0.00 0.00))
 (command "TEXT" "J" "ML" p1   0.75  0.00 "8451")
 (command "LAYER" "S" "CGBLITHTXT" "")
 (setq p1 (list 236.50 1754.11) p2 (list 0.00 0.00))
 (command "TEXT" "J" "ML" p1   0.75  0.00 "GRY MASS SS")
 (command "LAYER" "S" "CGBCMNT" "")
 (setq p1 (list 256.75 1754.11) p2 (list 0.00 0.00))
 (command "TEXT" "J" "ML" p1   0.75  0.00 "GB")
 (command "LAYER" "S" "CGBMAIN" "")
 (setq p1 (list 214.00 1755.22) p2 (list 220.00 1755.22) p3 (list 220.00 1754.24) p4 (list 214.00 1754.24))
 (command "PLINE" p1 p2 p3 p4 "c")
 (command "HATCH" "ZIGZAG" 5.00 0.00 "L" "")
 (command "COLOR" "BYLAYER")
 (command "LAYER" "S" "CGBLITHCD" "")
 (setq p1 (list 220.00 1754.73) p2 (list 221.35 1753.23))
 (command "LINE" p1 p2 "")
 (setq p1 (list 221.50 1752.86) p2 (list 0.00 0.00))
 (command "TEXT" "J" "ML" p1   0.75  0.00 "322")
 (command "LAYER" "S" "CGBTHK" "")
 (setq p1 (list 226.00 1752.86) p2 (list 0.00 0.00))
 (command "TEXT" "J" "ML" p1   0.75  0.00 "0.98")
 (command "LAYER" "S" "CGBHZID" "")
 (setq p1 (list 230.50 1752.86) p2 (list 0.00 0.00))
 (command "TEXT" "J" "ML" p1   0.75  0.00 "")
 (setq p1 (list 232.75 1752.86) p2 (list 0.00 0.00))
 (command "TEXT" "J" "ML" p1   0.75  0.00 "8451")
 (command "LAYER" "S" "CGBLITHTXT" "")
 (setq p1 (list 236.50 1752.86) p2 (list 0.00 0.00))
 (command "TEXT" "J" "ML" p1   0.75  0.00 "DRK GRY SH+INTERBED SS")
 (command "LAYER" "S" "CGBCMNT" "")
 (setq p1 (list 256.75 1752.86) p2 (list 0.00 0.00))
 (command "TEXT" "J" "ML" p1   0.75  0.00 "")
 (command "LAYER" "S" "CGBMAIN" "")
 (setq p1 (list 214.00 1754.24) p2 (list 220.00 1754.24) p3 (list 220.00 1750.79) p4 (list 214.00 1750.79))
 (command "PLINE" p1 p2 p3 p4 "c")
 (command "HATCH" "ZIGZAG" 4.00 0.00 "L" "")
 (command "COLOR" "BYLAYER")
 (command "LAYER" "S" "CGBLITHCD" "")
 (setq p1 (list 220.00 1752.52) p2 (list 221.35 1751.98))
 (command "LINE" p1 p2 "")
 (setq p1 (list 221.50 1751.61) p2 (list 0.00 0.00))
 (command "TEXT" "J" "ML" p1   0.75  0.00 "543")
 (command "LAYER" "S" "CGBTHK" "")
 (setq p1 (list 226.00 1751.61) p2 (list 0.00 0.00))
 (command "TEXT" "J" "ML" p1   0.75  0.00 "3.45")
 (command "LAYER" "S" "CGBHZID" "")
 (setq p1 (list 230.50 1751.61) p2 (list 0.00 0.00))
 (command "TEXT" "J" "ML" p1   0.75  0.00 "")
 (setq p1 (list 232.75 1751.61) p2 (list 0.00 0.00))
 (command "TEXT" "J" "ML" p1   0.75  0.00 "8451")
 (command "LAYER" "S" "CGBLITHTXT" "")
 (setq p1 (list 236.50 1751.61) p2 (list 0.00 0.00))
 (command "TEXT" "J" "ML" p1   0.75  0.00 "GRY SS W/SH STKS")
 (command "LAYER" "S" "CGBCMNT" "")
 (setq p1 (list 256.75 1751.61) p2 (list 0.00 0.00))
 (command "TEXT" "J" "ML" p1   0.75  0.00 "CRSN UP")
 (command "LAYER" "S" "CGBMAIN" "")
 (setq p1 (list 214.00 1750.79) p2 (list 220.00 1750.79) p3 (list 220.00 1749.59) p4 (list 214.00 1749.59))
 (command "PLINE" p1 p2 p3 p4 "c")
 (command "HATCH" "ZIGZAG" 0.50 0.00 "L" "")
 (command "COLOR" "BYLAYER")
 (command "LAYER" "S" "CGBLITHCD" "")
 (setq p1 (list 220.00 1750.19) p2 (list 221.35 1750.19))
 (command "LINE" p1 p2 "")
 (setq p1 (list 221.50 1749.82) p2 (list 0.00 0.00))
 (command "TEXT" "J" "ML" p1   0.75  0.00 "323")
 (command "LAYER" "S" "CGBTHK" "")
 (setq p1 (list 226.00 1749.82) p2 (list 0.00 0.00))
 (command "TEXT" "J" "ML" p1   0.75  0.00 "1.20")
 (command "LAYER" "S" "CGBHZID" "")
 (setq p1 (list 230.50 1749.82) p2 (list 0.00 0.00))
 (command "TEXT" "J" "ML" p1   0.75  0.00 "")
 (setq p1 (list 232.75 1749.82) p2 (list 0.00 0.00))
 (command "TEXT" "J" "ML" p1   0.75  0.00 "8451")
 (command "LAYER" "S" "CGBLITHTXT" "")
 (setq p1 (list 236.50 1749.82) p2 (list 0.00 0.00))
 (command "TEXT" "J" "ML" p1   0.75  0.00 "DRK GRY SH W/SS STKS")
 (command "LAYER" "S" "CGBCMNT" "")
 (setq p1 (list 256.75 1749.82) p2 (list 0.00 0.00))
 (command "TEXT" "J" "ML" p1   0.75  0.00 "")
 (command "LAYER" "S" "CGBMAIN" "")
 (setq p1 (list 214.00 1749.59) p2 (list 220.00 1749.59) p3 (list 220.00 1746.94) p4 (list 214.00 1746.94))
 (command "PLINE" p1 p2 p3 p4 "c")
 (command "HATCH" "ZIGZAG" 5.00 0.00 "L" "")
 (command "COLOR" "BYLAYER")
 (command "LAYER" "S" "CGBLITHCD" "")
 (setq p1 (list 220.00 1748.27) p2 (list 221.35 1748.27))
 (command "LINE" p1 p2 "")
 (setq p1 (list 221.50 1747.89) p2 (list 0.00 0.00))
 (command "TEXT" "J" "ML" p1   0.75  0.00 "144")
 (command "LAYER" "S" "CGBTHK" "")
 (setq p1 (list 226.00 1747.89) p2 (list 0.00 0.00))
 (command "TEXT" "J" "ML" p1   0.75  0.00 "2.65")
 (command "LAYER" "S" "CGBHZID" "")
 (setq p1 (list 230.50 1747.89) p2 (list 0.00 0.00))
 (command "TEXT" "J" "ML" p1   0.75  0.00 "")
 (setq p1 (list 232.75 1747.89) p2 (list 0.00 0.00))
 (command "TEXT" "J" "ML" p1   0.75  0.00 "8451")
 (command "LAYER" "S" "CGBLITHTXT" "")
 (setq p1 (list 236.50 1747.89) p2 (list 0.00 0.00))
 (command "TEXT" "J" "ML" p1   0.75  0.00 "GRN SH")
 (command "LAYER" "S" "CGBCMNT" "")
 (setq p1 (list 256.75 1747.89) p2 (list 0.00 0.00))
 (command "TEXT" "J" "ML" p1   0.75  0.00 "BRKN,FRACS")
 (command "LAYER" "S" "CGBMAIN" "")
 (setq p1 (list 214.00 1746.94) p2 (list 220.00 1746.94) p3 (list 220.00 1744.76) p4 (list 214.00 1744.76))
 (command "PLINE" p1 p2 p3 p4 "c")
 (command "HATCH" "ZIGZAG" 0.25 0.00 "L" "")
 (command "COLOR" "BYLAYER")
 (command "LAYER" "S" "CGBLITHCD" "")
 (setq p1 (list 220.00 1745.85) p2 (list 221.35 1745.85))
 (command "LINE" p1 p2 "")
 (setq p1 (list 221.50 1745.48) p2 (list 0.00 0.00))
 (command "TEXT" "J" "ML" p1   0.75  0.00 "177")
 (command "LAYER" "S" "CGBTHK" "")
 (setq p1 (list 226.00 1745.48) p2 (list 0.00 0.00))
 (command "TEXT" "J" "ML" p1   0.75  0.00 "2.18")
 (command "LAYER" "S" "CGBHZID" "")
 (setq p1 (list 230.50 1745.48) p2 (list 0.00 0.00))
 (command "TEXT" "J" "ML" p1   0.75  0.00 "")
 (setq p1 (list 232.75 1745.48) p2 (list 0.00 0.00))
 (command "TEXT" "J" "ML" p1   0.75  0.00 "8451")
 (command "LAYER" "S" "CGBLITHTXT" "")
 (setq p1 (list 236.50 1745.48) p2 (list 0.00 0.00))
 (command "TEXT" "J" "ML" p1   0.75  0.00 "GRY/GRN FIRECLAY")
 (command "LAYER" "S" "CGBCMNT" "")
 (setq p1 (list 256.75 1745.48) p2 (list 0.00 0.00))
 (command "TEXT" "J" "ML" p1   0.75  0.00 "BRKN")
 (command "LAYER" "S" "CGBMAIN" "")
 (setq p1 (list 214.00 1744.76) p2 (list 220.00 1744.76) p3 (list 220.00 1743.04) p4 (list 214.00 1743.04))
 (command "PLINE" p1 p2 p3 p4 "c")
 (command "HATCH" "ZIGZAG" 5.00 0.00 "L" "")
 (command "COLOR" "BYLAYER")
 (command "LAYER" "S" "CGBLITHCD" "")
 (setq p1 (list 220.00 1743.90) p2 (list 221.35 1743.90))
 (command "LINE" p1 p2 "")
 (setq p1 (list 221.50 1743.53) p2 (list 0.00 0.00))
 (command "TEXT" "J" "ML" p1   0.75  0.00 "274")
 (command "LAYER" "S" "CGBTHK" "")
 (setq p1 (list 226.00 1743.53) p2 (list 0.00 0.00))
 (command "TEXT" "J" "ML" p1   0.75  0.00 "1.72")
 (command "LAYER" "S" "CGBHZID" "")
 (setq p1 (list 230.50 1743.53) p2 (list 0.00 0.00))
 (command "TEXT" "J" "ML" p1   0.75  0.00 "")
 (setq p1 (list 232.75 1743.53) p2 (list 0.00 0.00))
 (command "TEXT" "J" "ML" p1   0.75  0.00 "8451")
 (command "LAYER" "S" "CGBLITHTXT" "")
 (setq p1 (list 236.50 1743.53) p2 (list 0.00 0.00))
 (command "TEXT" "J" "ML" p1   0.75  0.00 "GRY/GRN SH W/LS NODS")
 (command "LAYER" "S" "CGBCMNT" "")
 (setq p1 (list 256.75 1743.53) p2 (list 0.00 0.00))
 (command "TEXT" "J" "ML" p1   0.75  0.00 "SLX")
 (command "LAYER" "S" "CGBMAIN" "")
 (setq p1 (list 214.00 1743.04) p2 (list 220.00 1743.04) p3 (list 220.00 1740.04) p4 (list 214.00 1740.04))
 (command "PLINE" p1 p2 p3 p4 "c")
 (command "HATCH" "ZIGZAG" 3.00 0.00 "L" "")
 (command "COLOR" "BYLAYER")
 (command "LAYER" "S" "CGBLITHCD" "")
 (setq p1 (list 220.00 1741.54) p2 (list 221.35 1741.54))
 (command "LINE" p1 p2 "")
 (setq p1 (list 221.50 1741.17) p2 (list 0.00 0.00))
 (command "TEXT" "J" "ML" p1   0.75  0.00 "157")
 (command "LAYER" "S" "CGBTHK" "")
 (setq p1 (list 226.00 1741.17) p2 (list 0.00 0.00))
 (command "TEXT" "J" "ML" p1   0.75  0.00 "3.00")
 (command "LAYER" "S" "CGBHZID" "")
 (setq p1 (list 230.50 1741.17) p2 (list 0.00 0.00))
 (command "TEXT" "J" "ML" p1   0.75  0.00 "")
 (setq p1 (list 232.75 1741.17) p2 (list 0.00 0.00))
 (command "TEXT" "J" "ML" p1   0.75  0.00 "8451")
 (command "LAYER" "S" "CGBLITHTXT" "")
 (setq p1 (list 236.50 1741.17) p2 (list 0.00 0.00))
 (command "TEXT" "J" "ML" p1   0.75  0.00 "RED+GRN CLYSTN")
 (command "LAYER" "S" "CGBCMNT" "")
 (setq p1 (list 256.75 1741.17) p2 (list 0.00 0.00))
 (command "TEXT" "J" "ML" p1   0.75  0.00 "SLX")
 (command "LAYER" "S" "CGBMAIN" "")
 (setq p1 (list 214.00 1740.04) p2 (list 220.00 1740.04) p3 (list 220.00 1732.32) p4 (list 214.00 1732.32))
 (command "PLINE" p1 p2 p3 p4 "c")
 (command "HATCH" "ZIGZAG" 5.00 0.00 "L" "")
 (command "COLOR" "BYLAYER")
 (command "LAYER" "S" "CGBLITHCD" "")
 (setq p1 (list 220.00 1736.18) p2 (list 221.35 1736.18))
 (command "LINE" p1 p2 "")
 (setq p1 (list 221.50 1735.81) p2 (list 0.00 0.00))
 (command "TEXT" "J" "ML" p1   0.75  0.00 "343")
 (command "LAYER" "S" "CGBTHK" "")
 (setq p1 (list 226.00 1735.81) p2 (list 0.00 0.00))
 (command "TEXT" "J" "ML" p1   0.75  0.00 "7.72")
 (command "LAYER" "S" "CGBHZID" "")
 (setq p1 (list 230.50 1735.81) p2 (list 0.00 0.00))
 (command "TEXT" "J" "ML" p1   0.75  0.00 "")
 (setq p1 (list 232.75 1735.81) p2 (list 0.00 0.00))
 (command "TEXT" "J" "ML" p1   0.75  0.00 "8451")
 (command "LAYER" "S" "CGBLITHTXT" "")
 (setq p1 (list 236.50 1735.81) p2 (list 0.00 0.00))
 (command "TEXT" "J" "ML" p1   0.75  0.00 "GRN SH W/SS STKS")
 (command "LAYER" "S" "CGBCMNT" "")
 (setq p1 (list 256.75 1735.81) p2 (list 0.00 0.00))
 (command "TEXT" "J" "ML" p1   0.75  0.00 "")
 (command "LAYER" "S" "CGBMAIN" "")
 (setq p1 (list 214.00 1732.32) p2 (list 220.00 1732.32) p3 (list 220.00 1731.94) p4 (list 214.00 1731.94))
 (command "PLINE" p1 p2 p3 p4 "c")
 (command "HATCH" "ZIGZAG" 5.00 0.00 "L" "")
 (command "COLOR" "BYLAYER")
 (command "LAYER" "S" "CGBLITHCD" "")
 (setq p1 (list 220.00 1732.13) p2 (list 221.35 1732.13))
 (command "LINE" p1 p2 "")
 (setq p1 (list 221.50 1731.76) p2 (list 0.00 0.00))
 (command "TEXT" "J" "ML" p1   0.75  0.00 "144")
 (command "LAYER" "S" "CGBTHK" "")
 (setq p1 (list 226.00 1731.76) p2 (list 0.00 0.00))
 (command "TEXT" "J" "ML" p1   0.75  0.00 "0.38")
 (command "LAYER" "S" "CGBHZID" "")
 (setq p1 (list 230.50 1731.76) p2 (list 0.00 0.00))
 (command "TEXT" "J" "ML" p1   0.75  0.00 "")
 (setq p1 (list 232.75 1731.76) p2 (list 0.00 0.00))
 (command "TEXT" "J" "ML" p1   0.75  0.00 "8451")
 (command "LAYER" "S" "CGBLITHTXT" "")
 (setq p1 (list 236.50 1731.76) p2 (list 0.00 0.00))
 (command "TEXT" "J" "ML" p1   0.75  0.00 "GRN SH")
 (command "LAYER" "S" "CGBCMNT" "")
 (setq p1 (list 256.75 1731.76) p2 (list 0.00 0.00))
 (command "TEXT" "J" "ML" p1   0.75  0.00 "")
 (command "LAYER" "S" "CGBMAIN" "")
 (setq p1 (list 214.00 1731.94) p2 (list 220.00 1731.94) p3 (list 220.00 1731.04) p4 (list 214.00 1731.04))
 (command "PLINE" p1 p2 p3 p4 "c")
 (command "HATCH" "ZIGZAG" 5.00 0.00 "L" "")
 (command "COLOR" "BYLAYER")
 (command "LAYER" "S" "CGBLITHCD" "")
 (setq p1 (list 220.00 1731.49) p2 (list 221.35 1730.24))
 (command "LINE" p1 p2 "")
 (setq p1 (list 221.50 1729.87) p2 (list 0.00 0.00))
 (command "TEXT" "J" "ML" p1   0.75  0.00 "144")
 (command "LAYER" "S" "CGBTHK" "")
 (setq p1 (list 226.00 1729.87) p2 (list 0.00 0.00))
 (command "TEXT" "J" "ML" p1   0.75  0.00 "0.90")
 (command "LAYER" "S" "CGBHZID" "")
 (setq p1 (list 230.50 1729.87) p2 (list 0.00 0.00))
 (command "TEXT" "J" "ML" p1   0.75  0.00 "")
 (setq p1 (list 232.75 1729.87) p2 (list 0.00 0.00))
 (command "TEXT" "J" "ML" p1   0.75  0.00 "8451")
 (command "LAYER" "S" "CGBLITHTXT" "")
 (setq p1 (list 236.50 1729.87) p2 (list 0.00 0.00))
 (command "TEXT" "J" "ML" p1   0.75  0.00 "GRN SH")
 (command "LAYER" "S" "CGBCMNT" "")
 (setq p1 (list 256.75 1729.87) p2 (list 0.00 0.00))
 (command "TEXT" "J" "ML" p1   0.75  0.00 "")
 (command "LAYER" "S" "CGBMAIN" "")
 (setq p1 (list 214.00 1731.04) p2 (list 220.00 1731.04) p3 (list 220.00 1729.72) p4 (list 214.00 1729.72))
 (command "PLINE" p1 p2 p3 p4 "c")
 (command "HATCH" "ZIGZAG" 4.00 22.50 "L" "")
 (command "COLOR" "BYLAYER")
 (command "LAYER" "S" "CGBLITHCD" "")
 (setq p1 (list 220.00 1730.38) p2 (list 221.35 1728.99))
 (command "LINE" p1 p2 "")
 (setq p1 (list 221.50 1728.62) p2 (list 0.00 0.00))
 (command "TEXT" "J" "ML" p1   0.75  0.00 "114")
 (command "LAYER" "S" "CGBTHK" "")
 (setq p1 (list 226.00 1728.62) p2 (list 0.00 0.00))
 (command "TEXT" "J" "ML" p1   0.75  0.00 "1.32")
 (command "LAYER" "S" "CGBHZID" "")
 (setq p1 (list 230.50 1728.62) p2 (list 0.00 0.00))
 (command "TEXT" "J" "ML" p1   0.75  0.00 "")
 (setq p1 (list 232.75 1728.62) p2 (list 0.00 0.00))
 (command "TEXT" "J" "ML" p1   0.75  0.00 "8451")
 (command "LAYER" "S" "CGBLITHTXT" "")
 (setq p1 (list 236.50 1728.62) p2 (list 0.00 0.00))
 (command "TEXT" "J" "ML" p1   0.75  0.00 "BLK SH")
 (command "LAYER" "S" "CGBCMNT" "")
 (setq p1 (list 256.75 1728.62) p2 (list 0.00 0.00))
 (command "TEXT" "J" "ML" p1   0.75  0.00 "SLX,BRKN")
 (command "LAYER" "S" "CGBMAIN" "")
 (command "LAYER" "S" "CGBLITHCD" "")
 (setq p1 (list 220.00 1729.72) p2 (list 221.35 1727.74))
 (command "LINE" p1 p2 "")
 (setq p1 (list 221.50 1727.37) p2 (list 0.00 0.00))
 (command "TEXT" "J" "ML" p1   0.75  0.00 "020")
 (command "LAYER" "S" "CGBTHK" "")
 (setq p1 (list 226.00 1727.37) p2 (list 0.00 0.00))
 (command "TEXT" "J" "ML" p1   0.75  0.00 "0.00")
 (command "LAYER" "S" "CGBHZID" "")
 (setq p1 (list 230.50 1727.37) p2 (list 0.00 0.00))
 (command "TEXT" "J" "ML" p1   0.75  0.00 "")
 (setq p1 (list 232.75 1727.37) p2 (list 0.00 0.00))
 (command "TEXT" "J" "ML" p1   0.75  0.00 "8000")
 (command "LAYER" "S" "CGBLITHTXT" "")
 (setq p1 (list 236.50 1727.37) p2 (list 0.00 0.00))
 (command "TEXT" "J" "ML" p1   0.75  0.00 "COAL")
 (command "LAYER" "S" "CGBCMNT" "")
 (setq p1 (list 256.75 1727.37) p2 (list 0.00 0.00))
 (command "TEXT" "J" "ML" p1   0.75  0.00 "BAK HRZN")
 (command "LAYER" "S" "CGBMAIN" "")
 (setq p1 (list 214.00 1729.72) p2 (list 220.00 1729.72) p3 (list 220.00 1728.84) p4 (list 214.00 1728.84))
 (command "PLINE" p1 p2 p3 p4 "c")
 (command "HATCH" "ZIGZAG" 4.00 0.00 "L" "")
 (command "COLOR" "BYLAYER")
 (command "LAYER" "S" "CGBLITHCD" "")
 (setq p1 (list 220.00 1729.28) p2 (list 221.35 1726.49))
 (command "LINE" p1 p2 "")
 (setq p1 (list 221.50 1726.12) p2 (list 0.00 0.00))
 (command "TEXT" "J" "ML" p1   0.75  0.00 "124")
 (command "LAYER" "S" "CGBTHK" "")
 (setq p1 (list 226.00 1726.12) p2 (list 0.00 0.00))
 (command "TEXT" "J" "ML" p1   0.75  0.00 "0.88")
 (command "LAYER" "S" "CGBHZID" "")
 (setq p1 (list 230.50 1726.12) p2 (list 0.00 0.00))
 (command "TEXT" "J" "ML" p1   0.75  0.00 "")
 (setq p1 (list 232.75 1726.12) p2 (list 0.00 0.00))
 (command "TEXT" "J" "ML" p1   0.75  0.00 "7951")
 (command "LAYER" "S" "CGBLITHTXT" "")
 (setq p1 (list 236.50 1726.12) p2 (list 0.00 0.00))
 (command "TEXT" "J" "ML" p1   0.75  0.00 "DRK GRY SH")
 (command "LAYER" "S" "CGBCMNT" "")
 (setq p1 (list 256.75 1726.12) p2 (list 0.00 0.00))
 (command "TEXT" "J" "ML" p1   0.75  0.00 "SLX")
 (command "LAYER" "S" "CGBMAIN" "")
 (setq p1 (list 214.00 1728.84) p2 (list 220.00 1728.84) p3 (list 220.00 1727.70) p4 (list 214.00 1727.70))
 (command "PLINE" p1 p2 p3 p4 "c")
 (command "HATCH" "ZIGZAG" 3.00 0.00 "L" "")
 (command "COLOR" "BYLAYER")
 (command "LAYER" "S" "CGBLITHCD" "")
 (setq p1 (list 220.00 1728.27) p2 (list 221.35 1725.24))
 (command "LINE" p1 p2 "")
 (setq p1 (list 221.50 1724.87) p2 (list 0.00 0.00))
 (command "TEXT" "J" "ML" p1   0.75  0.00 "154")
 (command "LAYER" "S" "CGBTHK" "")
 (setq p1 (list 226.00 1724.87) p2 (list 0.00 0.00))
 (command "TEXT" "J" "ML" p1   0.75  0.00 "1.14")
 (command "LAYER" "S" "CGBHZID" "")
 (setq p1 (list 230.50 1724.87) p2 (list 0.00 0.00))
 (command "TEXT" "J" "ML" p1   0.75  0.00 "")
 (setq p1 (list 232.75 1724.87) p2 (list 0.00 0.00))
 (command "TEXT" "J" "ML" p1   0.75  0.00 "7951")
 (command "LAYER" "S" "CGBLITHTXT" "")
 (setq p1 (list 236.50 1724.87) p2 (list 0.00 0.00))
 (command "TEXT" "J" "ML" p1   0.75  0.00 "RED+GRN SH")
 (command "LAYER" "S" "CGBCMNT" "")
 (setq p1 (list 256.75 1724.87) p2 (list 0.00 0.00))
 (command "TEXT" "J" "ML" p1   0.75  0.00 "SLX")
 (command "LAYER" "S" "CGBMAIN" "")
 (setq p1 (list 214.00 1727.70) p2 (list 220.00 1727.70) p3 (list 220.00 1726.34) p4 (list 214.00 1726.34))
 (command "PLINE" p1 p2 p3 p4 "c")
 (command "HATCH" "ZIGZAG" 4.00 0.00 "L" "")
 (command "COLOR" "BYLAYER")
 (command "LAYER" "S" "CGBLITHCD" "")
 (setq p1 (list 220.00 1727.02) p2 (list 221.35 1723.99))
 (command "LINE" p1 p2 "")
 (setq p1 (list 221.50 1723.62) p2 (list 0.00 0.00))
 (command "TEXT" "J" "ML" p1   0.75  0.00 "124")
 (command "LAYER" "S" "CGBTHK" "")
 (setq p1 (list 226.00 1723.62) p2 (list 0.00 0.00))
 (command "TEXT" "J" "ML" p1   0.75  0.00 "1.36")
 (command "LAYER" "S" "CGBHZID" "")
 (setq p1 (list 230.50 1723.62) p2 (list 0.00 0.00))
 (command "TEXT" "J" "ML" p1   0.75  0.00 "")
 (setq p1 (list 232.75 1723.62) p2 (list 0.00 0.00))
 (command "TEXT" "J" "ML" p1   0.75  0.00 "7951")
 (command "LAYER" "S" "CGBLITHTXT" "")
 (setq p1 (list 236.50 1723.62) p2 (list 0.00 0.00))
 (command "TEXT" "J" "ML" p1   0.75  0.00 "DRK GRY SH")
 (command "LAYER" "S" "CGBCMNT" "")
 (setq p1 (list 256.75 1723.62) p2 (list 0.00 0.00))
 (command "TEXT" "J" "ML" p1   0.75  0.00 "")
 (command "LAYER" "S" "CGBMAIN" "")
 (setq p1 (list 214.00 1726.34) p2 (list 220.00 1726.34) p3 (list 220.00 1723.42) p4 (list 214.00 1723.42))
 (command "PLINE" p1 p2 p3 p4 "c")
 (command "HATCH" "ZIGZAG" 5.00 0.00 "L" "")
 (command "COLOR" "BYLAYER")
 (command "LAYER" "S" "CGBLITHCD" "")
 (setq p1 (list 220.00 1724.88) p2 (list 221.35 1722.74))
 (command "LINE" p1 p2 "")
 (setq p1 (list 221.50 1722.37) p2 (list 0.00 0.00))
 (command "TEXT" "J" "ML" p1   0.75  0.00 "174")
 (command "LAYER" "S" "CGBTHK" "")
 (setq p1 (list 226.00 1722.37) p2 (list 0.00 0.00))
 (command "TEXT" "J" "ML" p1   0.75  0.00 "2.92")
 (command "LAYER" "S" "CGBHZID" "")
 (setq p1 (list 230.50 1722.37) p2 (list 0.00 0.00))
 (command "TEXT" "J" "ML" p1   0.75  0.00 "")
 (setq p1 (list 232.75 1722.37) p2 (list 0.00 0.00))
 (command "TEXT" "J" "ML" p1   0.75  0.00 "7951")
 (command "LAYER" "S" "CGBLITHTXT" "")
 (setq p1 (list 236.50 1722.37) p2 (list 0.00 0.00))
 (command "TEXT" "J" "ML" p1   0.75  0.00 "GRY/GRN SH")
 (command "LAYER" "S" "CGBCMNT" "")
 (setq p1 (list 256.75 1722.37) p2 (list 0.00 0.00))
 (command "TEXT" "J" "ML" p1   0.75  0.00 "SLX")
 (command "LAYER" "S" "CGBMAIN" "")
 (setq p1 (list 214.00 1723.42) p2 (list 220.00 1723.42) p3 (list 220.00 1721.94) p4 (list 214.00 1721.94))
 (command "PLINE" p1 p2 p3 p4 "c")
 (command "HATCH" "ZIGZAG" 5.00 0.00 "L" "")
 (command "COLOR" "BYLAYER")
 (command "LAYER" "S" "CGBLITHCD" "")
 (setq p1 (list 220.00 1722.68) p2 (list 221.35 1721.49))
 (command "LINE" p1 p2 "")
 (setq p1 (list 221.50 1721.12) p2 (list 0.00 0.00))
 (command "TEXT" "J" "ML" p1   0.75  0.00 "174")
 (command "LAYER" "S" "CGBTHK" "")
 (setq p1 (list 226.00 1721.12) p2 (list 0.00 0.00))
 (command "TEXT" "J" "ML" p1   0.75  0.00 "1.48")
 (command "LAYER" "S" "CGBHZID" "")
 (setq p1 (list 230.50 1721.12) p2 (list 0.00 0.00))
 (command "TEXT" "J" "ML" p1   0.75  0.00 "")
 (setq p1 (list 232.75 1721.12) p2 (list 0.00 0.00))
 (command "TEXT" "J" "ML" p1   0.75  0.00 "7951")
 (command "LAYER" "S" "CGBLITHTXT" "")
 (setq p1 (list 236.50 1721.12) p2 (list 0.00 0.00))
 (command "TEXT" "J" "ML" p1   0.75  0.00 "GRY/GRN SH")
 (command "LAYER" "S" "CGBCMNT" "")
 (setq p1 (list 256.75 1721.12) p2 (list 0.00 0.00))
 (command "TEXT" "J" "ML" p1   0.75  0.00 "MTTLD,SLX")
 (command "LAYER" "S" "CGBMAIN" "")
 (setq p1 (list 214.00 1721.94) p2 (list 220.00 1721.94) p3 (list 220.00 1720.22) p4 (list 214.00 1720.22))
 (command "PLINE" p1 p2 p3 p4 "c")
 (command "HATCH" "ZIGZAG" 10.00 45.00 "L" "")
 (command "COLOR" "BYLAYER")
 (command "LAYER" "S" "CGBLITHCD" "")
 (setq p1 (list 220.00 1721.08) p2 (list 221.35 1720.24))
 (command "LINE" p1 p2 "")
 (setq p1 (list 221.50 1719.87) p2 (list 0.00 0.00))
 (command "TEXT" "J" "ML" p1   0.75  0.00 "094")
 (command "LAYER" "S" "CGBTHK" "")
 (setq p1 (list 226.00 1719.87) p2 (list 0.00 0.00))
 (command "TEXT" "J" "ML" p1   0.75  0.00 "1.72")
 (command "LAYER" "S" "CGBHZID" "")
 (setq p1 (list 230.50 1719.87) p2 (list 0.00 0.00))
 (command "TEXT" "J" "ML" p1   0.75  0.00 "")
 (setq p1 (list 232.75 1719.87) p2 (list 0.00 0.00))
 (command "TEXT" "J" "ML" p1   0.75  0.00 "7951")
 (command "LAYER" "S" "CGBLITHTXT" "")
 (setq p1 (list 236.50 1719.87) p2 (list 0.00 0.00))
 (command "TEXT" "J" "ML" p1   0.75  0.00 "MASS FLINT CLAY")
 (command "LAYER" "S" "CGBCMNT" "")
 (setq p1 (list 256.75 1719.87) p2 (list 0.00 0.00))
 (command "TEXT" "J" "ML" p1   0.75  0.00 "SLX")
 (command "LAYER" "S" "CGBMAIN" "")
 (setq p1 (list 214.00 1720.22) p2 (list 220.00 1720.22) p3 (list 220.00 1718.70) p4 (list 214.00 1718.70))
 (command "PLINE" p1 p2 p3 p4 "c")
 (command "HATCH" "ZIGZAG" 5.00 0.00 "L" "")
 (command "COLOR" "BYLAYER")
 (command "LAYER" "S" "CGBLITHCD" "")
 (setq p1 (list 220.00 1719.46) p2 (list 221.35 1718.99))
 (command "LINE" p1 p2 "")
 (setq p1 (list 221.50 1718.62) p2 (list 0.00 0.00))
 (command "TEXT" "J" "ML" p1   0.75  0.00 "144")
 (command "LAYER" "S" "CGBTHK" "")
 (setq p1 (list 226.00 1718.62) p2 (list 0.00 0.00))
 (command "TEXT" "J" "ML" p1   0.75  0.00 "1.52")
 (command "LAYER" "S" "CGBHZID" "")
 (setq p1 (list 230.50 1718.62) p2 (list 0.00 0.00))
 (command "TEXT" "J" "ML" p1   0.75  0.00 "")
 (setq p1 (list 232.75 1718.62) p2 (list 0.00 0.00))
 (command "TEXT" "J" "ML" p1   0.75  0.00 "7951")
 (command "LAYER" "S" "CGBLITHTXT" "")
 (setq p1 (list 236.50 1718.62) p2 (list 0.00 0.00))
 (command "TEXT" "J" "ML" p1   0.75  0.00 "GRN SH")
 (command "LAYER" "S" "CGBCMNT" "")
 (setq p1 (list 256.75 1718.62) p2 (list 0.00 0.00))
 (command "TEXT" "J" "ML" p1   0.75  0.00 "")
 (command "LAYER" "S" "CGBMAIN" "")
 (setq p1 (list 214.00 1718.70) p2 (list 220.00 1718.70) p3 (list 220.00 1709.15) p4 (list 214.00 1709.15))
 (command "PLINE" p1 p2 p3 p4 "c")
 (command "HATCH" "ZIGZAG" 4.00 0.00 "L" "")
 (command "COLOR" "BYLAYER")
 (command "LAYER" "S" "CGBLITHCD" "")
 (setq p1 (list 220.00 1713.93) p2 (list 221.35 1713.93))
 (command "LINE" p1 p2 "")
 (setq p1 (list 221.50 1713.55) p2 (list 0.00 0.00))
 (command "TEXT" "J" "ML" p1   0.75  0.00 "444")
 (command "LAYER" "S" "CGBTHK" "")
 (setq p1 (list 226.00 1713.55) p2 (list 0.00 0.00))
 (command "TEXT" "J" "ML" p1   0.75  0.00 "9.55")
 (command "LAYER" "S" "CGBHZID" "")
 (setq p1 (list 230.50 1713.55) p2 (list 0.00 0.00))
 (command "TEXT" "J" "ML" p1   0.75  0.00 "")
 (setq p1 (list 232.75 1713.55) p2 (list 0.00 0.00))
 (command "TEXT" "J" "ML" p1   0.75  0.00 "7951")
 (command "LAYER" "S" "CGBLITHTXT" "")
 (setq p1 (list 236.50 1713.55) p2 (list 0.00 0.00))
 (command "TEXT" "J" "ML" p1   0.75  0.00 "GRN SDY SH W/LS NODS")
 (command "LAYER" "S" "CGBCMNT" "")
 (setq p1 (list 256.75 1713.55) p2 (list 0.00 0.00))
 (command "TEXT" "J" "ML" p1   0.75  0.00 "GB,CALC")
 (command "LAYER" "S" "CGBMAIN" "")
 (setq p1 (list 214.00 1709.15) p2 (list 220.00 1709.15) p3 (list 220.00 1706.94) p4 (list 214.00 1706.94))
 (command "PLINE" p1 p2 p3 p4 "c")
 (command "HATCH" "ZIGZAG" 5.00 0.00 "L" "")
 (command "COLOR" "BYLAYER")
 (command "LAYER" "S" "CGBLITHCD" "")
 (setq p1 (list 220.00 1708.05) p2 (list 221.35 1708.05))
 (command "LINE" p1 p2 "")
 (setq p1 (list 221.50 1707.67) p2 (list 0.00 0.00))
 (command "TEXT" "J" "ML" p1   0.75  0.00 "144")
 (command "LAYER" "S" "CGBTHK" "")
 (setq p1 (list 226.00 1707.67) p2 (list 0.00 0.00))
 (command "TEXT" "J" "ML" p1   0.75  0.00 "2.21")
 (command "LAYER" "S" "CGBHZID" "")
 (setq p1 (list 230.50 1707.67) p2 (list 0.00 0.00))
 (command "TEXT" "J" "ML" p1   0.75  0.00 "")
 (setq p1 (list 232.75 1707.67) p2 (list 0.00 0.00))
 (command "TEXT" "J" "ML" p1   0.75  0.00 "7951")
 (command "LAYER" "S" "CGBLITHTXT" "")
 (setq p1 (list 236.50 1707.67) p2 (list 0.00 0.00))
 (command "TEXT" "J" "ML" p1   0.75  0.00 "GRN SH")
 (command "LAYER" "S" "CGBCMNT" "")
 (setq p1 (list 256.75 1707.67) p2 (list 0.00 0.00))
 (command "TEXT" "J" "ML" p1   0.75  0.00 "")
 (command "LAYER" "S" "CGBMAIN" "")
 (setq p1 (list 214.00 1706.94) p2 (list 220.00 1706.94) p3 (list 220.00 1705.14) p4 (list 214.00 1705.14))
 (command "PLINE" p1 p2 p3 p4 "c")
 (command "HATCH" "ZIGZAG" 5.00 0.00 "L" "")
 (command "COLOR" "BYLAYER")
 (command "LAYER" "S" "CGBLITHCD" "")
 (setq p1 (list 220.00 1706.04) p2 (list 221.35 1706.04))
 (command "LINE" p1 p2 "")
 (setq p1 (list 221.50 1705.67) p2 (list 0.00 0.00))
 (command "TEXT" "J" "ML" p1   0.75  0.00 "144")
 (command "LAYER" "S" "CGBTHK" "")
 (setq p1 (list 226.00 1705.67) p2 (list 0.00 0.00))
 (command "TEXT" "J" "ML" p1   0.75  0.00 "1.80")
 (command "LAYER" "S" "CGBHZID" "")
 (setq p1 (list 230.50 1705.67) p2 (list 0.00 0.00))
 (command "TEXT" "J" "ML" p1   0.75  0.00 "")
 (setq p1 (list 232.75 1705.67) p2 (list 0.00 0.00))
 (command "TEXT" "J" "ML" p1   0.75  0.00 "7951")
 (command "LAYER" "S" "CGBLITHTXT" "")
 (setq p1 (list 236.50 1705.67) p2 (list 0.00 0.00))
 (command "TEXT" "J" "ML" p1   0.75  0.00 "GRN SH")
 (command "LAYER" "S" "CGBCMNT" "")
 (setq p1 (list 256.75 1705.67) p2 (list 0.00 0.00))
 (command "TEXT" "J" "ML" p1   0.75  0.00 "")
 (command "LAYER" "S" "CGBMAIN" "")
 (setq p1 (list 214.00 1705.14) p2 (list 220.00 1705.14) p3 (list 220.00 1704.87) p4 (list 214.00 1704.87))
 (command "PLINE" p1 p2 p3 p4 "c")
 (command "HATCH" "ZIGZAG" 5.00 0.00 "L" "")
 (command "COLOR" "BYLAYER")
 (command "LAYER" "S" "CGBLITHCD" "")
 (setq p1 (list 220.00 1705.01) p2 (list 221.35 1703.76))
 (command "LINE" p1 p2 "")
 (setq p1 (list 221.50 1703.38) p2 (list 0.00 0.00))
 (command "TEXT" "J" "ML" p1   0.75  0.00 "144")
 (command "LAYER" "S" "CGBTHK" "")
 (setq p1 (list 226.00 1703.38) p2 (list 0.00 0.00))
 (command "TEXT" "J" "ML" p1   0.75  0.00 "0.27")
 (command "LAYER" "S" "CGBHZID" "")
 (setq p1 (list 230.50 1703.38) p2 (list 0.00 0.00))
 (command "TEXT" "J" "ML" p1   0.75  0.00 "")
 (setq p1 (list 232.75 1703.38) p2 (list 0.00 0.00))
 (command "TEXT" "J" "ML" p1   0.75  0.00 "7951")
 (command "LAYER" "S" "CGBLITHTXT" "")
 (setq p1 (list 236.50 1703.38) p2 (list 0.00 0.00))
 (command "TEXT" "J" "ML" p1   0.75  0.00 "GRN SH")
 (command "LAYER" "S" "CGBCMNT" "")
 (setq p1 (list 256.75 1703.38) p2 (list 0.00 0.00))
 (command "TEXT" "J" "ML" p1   0.75  0.00 "SS FILL BURS")
 (command "LAYER" "S" "CGBMAIN" "")
 (setq p1 (list 214.00 1704.87) p2 (list 220.00 1704.87) p3 (list 220.00 1704.38) p4 (list 214.00 1704.38))
 (command "PLINE" p1 p2 p3 p4 "c")
 (command "HATCH" "ZIGZAG" 4.00 0.00 "L" "")
 (command "COLOR" "BYLAYER")
 (command "LAYER" "S" "CGBLITHCD" "")
 (setq p1 (list 220.00 1704.63) p2 (list 221.35 1702.51))
 (command "LINE" p1 p2 "")
 (setq p1 (list 221.50 1702.13) p2 (list 0.00 0.00))
 (command "TEXT" "J" "ML" p1   0.75  0.00 "544")
 (command "LAYER" "S" "CGBTHK" "")
 (setq p1 (list 226.00 1702.13) p2 (list 0.00 0.00))
 (command "TEXT" "J" "ML" p1   0.75  0.00 "0.49")
 (command "LAYER" "S" "CGBHZID" "")
 (setq p1 (list 230.50 1702.13) p2 (list 0.00 0.00))
 (command "TEXT" "J" "ML" p1   0.75  0.00 "")
 (setq p1 (list 232.75 1702.13) p2 (list 0.00 0.00))
 (command "TEXT" "J" "ML" p1   0.75  0.00 "7951")
 (command "LAYER" "S" "CGBLITHTXT" "")
 (setq p1 (list 236.50 1702.13) p2 (list 0.00 0.00))
 (command "TEXT" "J" "ML" p1   0.75  0.00 "GRY MASS SS")
 (command "LAYER" "S" "CGBCMNT" "")
 (setq p1 (list 256.75 1702.13) p2 (list 0.00 0.00))
 (command "TEXT" "J" "ML" p1   0.75  0.00 "SLC")
 (command "LAYER" "S" "CGBMAIN" "")
 (setq p1 (list 214.00 1704.38) p2 (list 220.00 1704.38) p3 (list 220.00 1703.68) p4 (list 214.00 1703.68))
 (command "PLINE" p1 p2 p3 p4 "c")
 (command "HATCH" "ZIGZAG" 4.00 0.00 "L" "")
 (command "COLOR" "BYLAYER")
 (command "LAYER" "S" "CGBLITHCD" "")
 (setq p1 (list 220.00 1704.03) p2 (list 221.35 1701.26))
 (command "LINE" p1 p2 "")
 (setq p1 (list 221.50 1700.88) p2 (list 0.00 0.00))
 (command "TEXT" "J" "ML" p1   0.75  0.00 "344")
 (command "LAYER" "S" "CGBTHK" "")
 (setq p1 (list 226.00 1700.88) p2 (list 0.00 0.00))
 (command "TEXT" "J" "ML" p1   0.75  0.00 "0.70")
 (command "LAYER" "S" "CGBHZID" "")
 (setq p1 (list 230.50 1700.88) p2 (list 0.00 0.00))
 (command "TEXT" "J" "ML" p1   0.75  0.00 "")
 (setq p1 (list 232.75 1700.88) p2 (list 0.00 0.00))
 (command "TEXT" "J" "ML" p1   0.75  0.00 "7951")
 (command "LAYER" "S" "CGBLITHTXT" "")
 (setq p1 (list 236.50 1700.88) p2 (list 0.00 0.00))
 (command "TEXT" "J" "ML" p1   0.75  0.00 "GRN MASS SDY SH")
 (command "LAYER" "S" "CGBCMNT" "")
 (setq p1 (list 256.75 1700.88) p2 (list 0.00 0.00))
 (command "TEXT" "J" "ML" p1   0.75  0.00 "SLC")
 (command "LAYER" "S" "CGBMAIN" "")
 (setq p1 (list 214.00 1703.68) p2 (list 220.00 1703.68) p3 (list 220.00 1702.66) p4 (list 214.00 1702.66))
 (command "PLINE" p1 p2 p3 p4 "c")
 (command "HATCH" "ZIGZAG" 4.00 0.00 "L" "")
 (command "COLOR" "BYLAYER")
 (command "LAYER" "S" "CGBLITHCD" "")
 (setq p1 (list 220.00 1703.17) p2 (list 221.35 1700.01))
 (command "LINE" p1 p2 "")
 (setq p1 (list 221.50 1699.63) p2 (list 0.00 0.00))
 (command "TEXT" "J" "ML" p1   0.75  0.00 "544")
 (command "LAYER" "S" "CGBTHK" "")
 (setq p1 (list 226.00 1699.63) p2 (list 0.00 0.00))
 (command "TEXT" "J" "ML" p1   0.75  0.00 "1.02")
 (command "LAYER" "S" "CGBHZID" "")
 (setq p1 (list 230.50 1699.63) p2 (list 0.00 0.00))
 (command "TEXT" "J" "ML" p1   0.75  0.00 "")
 (setq p1 (list 232.75 1699.63) p2 (list 0.00 0.00))
 (command "TEXT" "J" "ML" p1   0.75  0.00 "7951")
 (command "LAYER" "S" "CGBLITHTXT" "")
 (setq p1 (list 236.50 1699.63) p2 (list 0.00 0.00))
 (command "TEXT" "J" "ML" p1   0.75  0.00 "GRY MASS SS")
 (command "LAYER" "S" "CGBCMNT" "")
 (setq p1 (list 256.75 1699.63) p2 (list 0.00 0.00))
 (command "TEXT" "J" "ML" p1   0.75  0.00 "SLC")
 (command "LAYER" "S" "CGBMAIN" "")
 (setq p1 (list 214.00 1702.66) p2 (list 220.00 1702.66) p3 (list 220.00 1701.73) p4 (list 214.00 1701.73))
 (command "PLINE" p1 p2 p3 p4 "c")
 (command "HATCH" "ZIGZAG" 5.00 0.00 "L" "")
 (command "COLOR" "BYLAYER")
 (command "LAYER" "S" "CGBLITHCD" "")
 (setq p1 (list 220.00 1702.20) p2 (list 221.35 1698.76))
 (command "LINE" p1 p2 "")
 (setq p1 (list 221.50 1698.38) p2 (list 0.00 0.00))
 (command "TEXT" "J" "ML" p1   0.75  0.00 "342")
 (command "LAYER" "S" "CGBTHK" "")
 (setq p1 (list 226.00 1698.38) p2 (list 0.00 0.00))
 (command "TEXT" "J" "ML" p1   0.75  0.00 "0.93")
 (command "LAYER" "S" "CGBHZID" "")
 (setq p1 (list 230.50 1698.38) p2 (list 0.00 0.00))
 (command "TEXT" "J" "ML" p1   0.75  0.00 "")
 (setq p1 (list 232.75 1698.38) p2 (list 0.00 0.00))
 (command "TEXT" "J" "ML" p1   0.75  0.00 "7951")
 (command "LAYER" "S" "CGBLITHTXT" "")
 (setq p1 (list 236.50 1698.38) p2 (list 0.00 0.00))
 (command "TEXT" "J" "ML" p1   0.75  0.00 "GRN SH+INTERBED SS")
 (command "LAYER" "S" "CGBCMNT" "")
 (setq p1 (list 256.75 1698.38) p2 (list 0.00 0.00))
 (command "TEXT" "J" "ML" p1   0.75  0.00 "SLC")
 (command "LAYER" "S" "CGBMAIN" "")
 (setq p1 (list 214.00 1701.73) p2 (list 220.00 1701.73) p3 (list 220.00 1695.06) p4 (list 214.00 1695.06))
 (command "PLINE" p1 p2 p3 p4 "c")
 (command "HATCH" "ZIGZAG" 4.00 0.00 "L" "")
 (command "COLOR" "BYLAYER")
 (command "LAYER" "S" "CGBLITHCD" "")
 (setq p1 (list 220.00 1698.40) p2 (list 221.35 1697.51))
 (command "LINE" p1 p2 "")
 (setq p1 (list 221.50 1697.13) p2 (list 0.00 0.00))
 (command "TEXT" "J" "ML" p1   0.75  0.00 "541")
 (command "LAYER" "S" "CGBTHK" "")
 (setq p1 (list 226.00 1697.13) p2 (list 0.00 0.00))
 (command "TEXT" "J" "ML" p1   0.75  0.00 "6.67")
 (command "LAYER" "S" "CGBHZID" "")
 (setq p1 (list 230.50 1697.13) p2 (list 0.00 0.00))
 (command "TEXT" "J" "ML" p1   0.75  0.00 "")
 (setq p1 (list 232.75 1697.13) p2 (list 0.00 0.00))
 (command "TEXT" "J" "ML" p1   0.75  0.00 "7951")
 (command "LAYER" "S" "CGBLITHTXT" "")
 (setq p1 (list 236.50 1697.13) p2 (list 0.00 0.00))
 (command "TEXT" "J" "ML" p1   0.75  0.00 "GRY CROSSBED SS")
 (command "LAYER" "S" "CGBCMNT" "")
 (setq p1 (list 256.75 1697.13) p2 (list 0.00 0.00))
 (command "TEXT" "J" "ML" p1   0.75  0.00 "SLC")
 (command "LAYER" "S" "CGBMAIN" "")
 (setq p1 (list 214.00 1695.06) p2 (list 220.00 1695.06) p3 (list 220.00 1693.54) p4 (list 214.00 1693.54))
 (command "PLINE" p1 p2 p3 p4 "c")
 (command "HATCH" "ZIGZAG" 4.00 0.00 "L" "")
 (command "COLOR" "BYLAYER")
 (command "LAYER" "S" "CGBLITHCD" "")
 (setq p1 (list 220.00 1694.30) p2 (list 221.35 1694.30))
 (command "LINE" p1 p2 "")
 (setq p1 (list 221.50 1693.93) p2 (list 0.00 0.00))
 (command "TEXT" "J" "ML" p1   0.75  0.00 "344")
 (command "LAYER" "S" "CGBTHK" "")
 (setq p1 (list 226.00 1693.93) p2 (list 0.00 0.00))
 (command "TEXT" "J" "ML" p1   0.75  0.00 "1.52")
 (command "LAYER" "S" "CGBHZID" "")
 (setq p1 (list 230.50 1693.93) p2 (list 0.00 0.00))
 (command "TEXT" "J" "ML" p1   0.75  0.00 "")
 (setq p1 (list 232.75 1693.93) p2 (list 0.00 0.00))
 (command "TEXT" "J" "ML" p1   0.75  0.00 "7951")
 (command "LAYER" "S" "CGBLITHTXT" "")
 (setq p1 (list 236.50 1693.93) p2 (list 0.00 0.00))
 (command "TEXT" "J" "ML" p1   0.75  0.00 "GRN MASS SDY SH")
 (command "LAYER" "S" "CGBCMNT" "")
 (setq p1 (list 256.75 1693.93) p2 (list 0.00 0.00))
 (command "TEXT" "J" "ML" p1   0.75  0.00 "GB")
 (command "LAYER" "S" "CGBMAIN" "")
 (setq p1 (list 214.00 1693.54) p2 (list 220.00 1693.54) p3 (list 220.00 1691.79) p4 (list 214.00 1691.79))
 (command "PLINE" p1 p2 p3 p4 "c")
 (command "HATCH" "ZIGZAG" 4.00 0.00 "L" "")
 (command "COLOR" "BYLAYER")
 (command "LAYER" "S" "CGBLITHCD" "")
 (setq p1 (list 220.00 1692.67) p2 (list 221.35 1692.67))
 (command "LINE" p1 p2 "")
 (setq p1 (list 221.50 1692.29) p2 (list 0.00 0.00))
 (command "TEXT" "J" "ML" p1   0.75  0.00 "541")
 (command "LAYER" "S" "CGBTHK" "")
 (setq p1 (list 226.00 1692.29) p2 (list 0.00 0.00))
 (command "TEXT" "J" "ML" p1   0.75  0.00 "1.75")
 (command "LAYER" "S" "CGBHZID" "")
 (setq p1 (list 230.50 1692.29) p2 (list 0.00 0.00))
 (command "TEXT" "J" "ML" p1   0.75  0.00 "")
 (setq p1 (list 232.75 1692.29) p2 (list 0.00 0.00))
 (command "TEXT" "J" "ML" p1   0.75  0.00 "7951")
 (command "LAYER" "S" "CGBLITHTXT" "")
 (setq p1 (list 236.50 1692.29) p2 (list 0.00 0.00))
 (command "TEXT" "J" "ML" p1   0.75  0.00 "GRY CROSSBED SS")
 (command "LAYER" "S" "CGBCMNT" "")
 (setq p1 (list 256.75 1692.29) p2 (list 0.00 0.00))
 (command "TEXT" "J" "ML" p1   0.75  0.00 "")
 (command "LAYER" "S" "CGBMAIN" "")
 (setq p1 (list 214.00 1691.79) p2 (list 220.00 1691.79) p3 (list 220.00 1687.43) p4 (list 214.00 1687.43))
 (command "PLINE" p1 p2 p3 p4 "c")
 (command "HATCH" "ZIGZAG" 4.00 0.00 "L" "")
 (command "COLOR" "BYLAYER")
 (command "LAYER" "S" "CGBLITHCD" "")
 (setq p1 (list 220.00 1689.61) p2 (list 221.35 1689.61))
 (command "LINE" p1 p2 "")
 (setq p1 (list 221.50 1689.24) p2 (list 0.00 0.00))
 (command "TEXT" "J" "ML" p1   0.75  0.00 "541")
 (command "LAYER" "S" "CGBTHK" "")
 (setq p1 (list 226.00 1689.24) p2 (list 0.00 0.00))
 (command "TEXT" "J" "ML" p1   0.75  0.00 "4.36")
 (command "LAYER" "S" "CGBHZID" "")
 (setq p1 (list 230.50 1689.24) p2 (list 0.00 0.00))
 (command "TEXT" "J" "ML" p1   0.75  0.00 "")
 (setq p1 (list 232.75 1689.24) p2 (list 0.00 0.00))
 (command "TEXT" "J" "ML" p1   0.75  0.00 "7951")
 (command "LAYER" "S" "CGBLITHTXT" "")
 (setq p1 (list 236.50 1689.24) p2 (list 0.00 0.00))
 (command "TEXT" "J" "ML" p1   0.75  0.00 "GRY CROSSBED SS")
 (command "LAYER" "S" "CGBCMNT" "")
 (setq p1 (list 256.75 1689.24) p2 (list 0.00 0.00))
 (command "TEXT" "J" "ML" p1   0.75  0.00 "")
 (command "LAYER" "S" "CGBMAIN" "")
 (setq p1 (list 214.00 1687.43) p2 (list 220.00 1687.43) p3 (list 220.00 1685.92) p4 (list 214.00 1685.92))
 (command "PLINE" p1 p2 p3 p4 "c")
 (command "HATCH" "ZIGZAG" 0.25 0.00 "L" "")
 (command "COLOR" "BYLAYER")
 (command "LAYER" "S" "CGBLITHCD" "")
 (setq p1 (list 220.00 1686.68) p2 (list 221.35 1686.68))
 (command "LINE" p1 p2 "")
 (setq p1 (list 221.50 1686.30) p2 (list 0.00 0.00))
 (command "TEXT" "J" "ML" p1   0.75  0.00 "742")
 (command "LAYER" "S" "CGBTHK" "")
 (setq p1 (list 226.00 1686.30) p2 (list 0.00 0.00))
 (command "TEXT" "J" "ML" p1   0.75  0.00 "1.51")
 (command "LAYER" "S" "CGBHZID" "")
 (setq p1 (list 230.50 1686.30) p2 (list 0.00 0.00))
 (command "TEXT" "J" "ML" p1   0.75  0.00 "")
 (setq p1 (list 232.75 1686.30) p2 (list 0.00 0.00))
 (command "TEXT" "J" "ML" p1   0.75  0.00 "7951")
 (command "LAYER" "S" "CGBLITHTXT" "")
 (setq p1 (list 236.50 1686.30) p2 (list 0.00 0.00))
 (command "TEXT" "J" "ML" p1   0.75  0.00 "GRY SH PEB CGL")
 (command "LAYER" "S" "CGBCMNT" "")
 (setq p1 (list 256.75 1686.30) p2 (list 0.00 0.00))
 (command "TEXT" "J" "ML" p1   0.75  0.00 "SH SPARS")
 (command "LAYER" "S" "CGBMAIN" "")
 (setq p1 (list 214.00 1685.92) p2 (list 220.00 1685.92) p3 (list 220.00 1682.55) p4 (list 214.00 1682.55))
 (command "PLINE" p1 p2 p3 p4 "c")
 (command "HATCH" "ZIGZAG" 4.00 0.00 "L" "")
 (command "COLOR" "BYLAYER")
 (command "LAYER" "S" "CGBLITHCD" "")
 (setq p1 (list 220.00 1684.24) p2 (list 221.35 1684.24))
 (command "LINE" p1 p2 "")
 (setq p1 (list 221.50 1683.86) p2 (list 0.00 0.00))
 (command "TEXT" "J" "ML" p1   0.75  0.00 "541")
 (command "LAYER" "S" "CGBTHK" "")
 (setq p1 (list 226.00 1683.86) p2 (list 0.00 0.00))
 (command "TEXT" "J" "ML" p1   0.75  0.00 "3.37")
 (command "LAYER" "S" "CGBHZID" "")
 (setq p1 (list 230.50 1683.86) p2 (list 0.00 0.00))
 (command "TEXT" "J" "ML" p1   0.75  0.00 "")
 (setq p1 (list 232.75 1683.86) p2 (list 0.00 0.00))
 (command "TEXT" "J" "ML" p1   0.75  0.00 "7951")
 (command "LAYER" "S" "CGBLITHTXT" "")
 (setq p1 (list 236.50 1683.86) p2 (list 0.00 0.00))
 (command "TEXT" "J" "ML" p1   0.75  0.00 "GRY CROSSBED SS")
 (command "LAYER" "S" "CGBCMNT" "")
 (setq p1 (list 256.75 1683.86) p2 (list 0.00 0.00))
 (command "TEXT" "J" "ML" p1   0.75  0.00 "")
 (command "LAYER" "S" "CGBMAIN" "")
 (setq p1 (list 214.00 1682.55) p2 (list 220.00 1682.55) p3 (list 220.00 1681.91) p4 (list 214.00 1681.91))
 (command "PLINE" p1 p2 p3 p4 "c")
 (command "HATCH" "ZIGZAG" 0.25 0.00 "L" "")
 (command "COLOR" "BYLAYER")
 (command "LAYER" "S" "CGBLITHCD" "")
 (setq p1 (list 220.00 1682.23) p2 (list 221.35 1682.23))
 (command "LINE" p1 p2 "")
 (setq p1 (list 221.50 1681.86) p2 (list 0.00 0.00))
 (command "TEXT" "J" "ML" p1   0.75  0.00 "742")
 (command "LAYER" "S" "CGBTHK" "")
 (setq p1 (list 226.00 1681.86) p2 (list 0.00 0.00))
 (command "TEXT" "J" "ML" p1   0.75  0.00 "0.64")
 (command "LAYER" "S" "CGBHZID" "")
 (setq p1 (list 230.50 1681.86) p2 (list 0.00 0.00))
 (command "TEXT" "J" "ML" p1   0.75  0.00 "")
 (setq p1 (list 232.75 1681.86) p2 (list 0.00 0.00))
 (command "TEXT" "J" "ML" p1   0.75  0.00 "7951")
 (command "LAYER" "S" "CGBLITHTXT" "")
 (setq p1 (list 236.50 1681.86) p2 (list 0.00 0.00))
 (command "TEXT" "J" "ML" p1   0.75  0.00 "GRY SH PEB CGL")
 (command "LAYER" "S" "CGBCMNT" "")
 (setq p1 (list 256.75 1681.86) p2 (list 0.00 0.00))
 (command "TEXT" "J" "ML" p1   0.75  0.00 "")
 (command "LAYER" "S" "CGBMAIN" "")
 (setq p1 (list 214.00 1681.91) p2 (list 220.00 1681.91) p3 (list 220.00 1678.63) p4 (list 214.00 1678.63))
 (command "PLINE" p1 p2 p3 p4 "c")
 (command "HATCH" "ZIGZAG" 4.00 0.00 "L" "")
 (command "COLOR" "BYLAYER")
 (command "LAYER" "S" "CGBLITHCD" "")
 (setq p1 (list 220.00 1680.27) p2 (list 221.35 1680.27))
 (command "LINE" p1 p2 "")
 (setq p1 (list 221.50 1679.90) p2 (list 0.00 0.00))
 (command "TEXT" "J" "ML" p1   0.75  0.00 "543")
 (command "LAYER" "S" "CGBTHK" "")
 (setq p1 (list 226.00 1679.90) p2 (list 0.00 0.00))
 (command "TEXT" "J" "ML" p1   0.75  0.00 "3.28")
 (command "LAYER" "S" "CGBHZID" "")
 (setq p1 (list 230.50 1679.90) p2 (list 0.00 0.00))
 (command "TEXT" "J" "ML" p1   0.75  0.00 "")
 (setq p1 (list 232.75 1679.90) p2 (list 0.00 0.00))
 (command "TEXT" "J" "ML" p1   0.75  0.00 "7951")
 (command "LAYER" "S" "CGBLITHTXT" "")
 (setq p1 (list 236.50 1679.90) p2 (list 0.00 0.00))
 (command "TEXT" "J" "ML" p1   0.75  0.00 "GRY SS W/SH STKS")
 (command "LAYER" "S" "CGBCMNT" "")
 (setq p1 (list 256.75 1679.90) p2 (list 0.00 0.00))
 (command "TEXT" "J" "ML" p1   0.75  0.00 "")
 (command "LAYER" "S" "CGBMAIN" "")
 (setq p1 (list 214.00 1678.63) p2 (list 220.00 1678.63) p3 (list 220.00 1676.84) p4 (list 214.00 1676.84))
 (command "PLINE" p1 p2 p3 p4 "c")
 (command "HATCH" "ZIGZAG" 4.00 0.00 "L" "")
 (command "COLOR" "BYLAYER")
 (command "LAYER" "S" "CGBLITHCD" "")
 (setq p1 (list 220.00 1677.74) p2 (list 221.35 1677.74))
 (command "LINE" p1 p2 "")
 (setq p1 (list 221.50 1677.36) p2 (list 0.00 0.00))
 (command "TEXT" "J" "ML" p1   0.75  0.00 "541")
 (command "LAYER" "S" "CGBTHK" "")
 (setq p1 (list 226.00 1677.36) p2 (list 0.00 0.00))
 (command "TEXT" "J" "ML" p1   0.75  0.00 "1.79")
 (command "LAYER" "S" "CGBHZID" "")
 (setq p1 (list 230.50 1677.36) p2 (list 0.00 0.00))
 (command "TEXT" "J" "ML" p1   0.75  0.00 "")
 (setq p1 (list 232.75 1677.36) p2 (list 0.00 0.00))
 (command "TEXT" "J" "ML" p1   0.75  0.00 "7951")
 (command "LAYER" "S" "CGBLITHTXT" "")
 (setq p1 (list 236.50 1677.36) p2 (list 0.00 0.00))
 (command "TEXT" "J" "ML" p1   0.75  0.00 "GRY CROSSBED SS")
 (command "LAYER" "S" "CGBCMNT" "")
 (setq p1 (list 256.75 1677.36) p2 (list 0.00 0.00))
 (command "TEXT" "J" "ML" p1   0.75  0.00 "")
 (command "LAYER" "S" "CGBMAIN" "")
 (setq p1 (list 214.00 1676.84) p2 (list 220.00 1676.84) p3 (list 220.00 1667.27) p4 (list 214.00 1667.27))
 (command "PLINE" p1 p2 p3 p4 "c")
 (command "HATCH" "ZIGZAG" 4.00 0.00 "L" "")
 (command "COLOR" "BYLAYER")
 (command "LAYER" "S" "CGBLITHCD" "")
 (setq p1 (list 220.00 1672.06) p2 (list 221.35 1672.06))
 (command "LINE" p1 p2 "")
 (setq p1 (list 221.50 1671.68) p2 (list 0.00 0.00))
 (command "TEXT" "J" "ML" p1   0.75  0.00 "541")
 (command "LAYER" "S" "CGBTHK" "")
 (setq p1 (list 226.00 1671.68) p2 (list 0.00 0.00))
 (command "TEXT" "J" "ML" p1   0.75  0.00 "9.57")
 (command "LAYER" "S" "CGBHZID" "")
 (setq p1 (list 230.50 1671.68) p2 (list 0.00 0.00))
 (command "TEXT" "J" "ML" p1   0.75  0.00 "")
 (setq p1 (list 232.75 1671.68) p2 (list 0.00 0.00))
 (command "TEXT" "J" "ML" p1   0.75  0.00 "7951")
 (command "LAYER" "S" "CGBLITHTXT" "")
 (setq p1 (list 236.50 1671.68) p2 (list 0.00 0.00))
 (command "TEXT" "J" "ML" p1   0.75  0.00 "GRY CROSSBED SS")
 (command "LAYER" "S" "CGBCMNT" "")
 (setq p1 (list 256.75 1671.68) p2 (list 0.00 0.00))
 (command "TEXT" "J" "ML" p1   0.75  0.00 "")
 (command "LAYER" "S" "CGBMAIN" "")
 (setq p1 (list 214.00 1667.27) p2 (list 220.00 1667.27) p3 (list 220.00 1667.00) p4 (list 214.00 1667.00))
 (command "PLINE" p1 p2 p3 p4 "c")
 (command "HATCH" "ZIGZAG" 5.00 0.00 "L" "")
 (command "COLOR" "BYLAYER")
 (command "LAYER" "S" "CGBLITHCD" "")
 (setq p1 (list 220.00 1667.14) p2 (list 221.35 1667.14))
 (command "LINE" p1 p2 "")
 (setq p1 (list 221.50 1666.76) p2 (list 0.00 0.00))
 (command "TEXT" "J" "ML" p1   0.75  0.00 "144")
 (command "LAYER" "S" "CGBTHK" "")
 (setq p1 (list 226.00 1666.76) p2 (list 0.00 0.00))
 (command "TEXT" "J" "ML" p1   0.75  0.00 "0.27")
 (command "LAYER" "S" "CGBHZID" "")
 (setq p1 (list 230.50 1666.76) p2 (list 0.00 0.00))
 (command "TEXT" "J" "ML" p1   0.75  0.00 "")
 (setq p1 (list 232.75 1666.76) p2 (list 0.00 0.00))
 (command "TEXT" "J" "ML" p1   0.75  0.00 "7951")
 (command "LAYER" "S" "CGBLITHTXT" "")
 (setq p1 (list 236.50 1666.76) p2 (list 0.00 0.00))
 (command "TEXT" "J" "ML" p1   0.75  0.00 "GRN SH")
 (command "LAYER" "S" "CGBCMNT" "")
 (setq p1 (list 256.75 1666.76) p2 (list 0.00 0.00))
 (command "TEXT" "J" "ML" p1   0.75  0.00 "")
 (command "LAYER" "S" "CGBMAIN" "")
 (setq p1 (list 214.00 1667.00) p2 (list 220.00 1667.00) p3 (list 220.00 1662.80) p4 (list 214.00 1662.80))
 (command "PLINE" p1 p2 p3 p4 "c")
 (command "HATCH" "ZIGZAG" 4.00 0.00 "L" "")
 (command "COLOR" "BYLAYER")
 (command "LAYER" "S" "CGBLITHCD" "")
 (setq p1 (list 220.00 1664.90) p2 (list 221.35 1664.90))
 (command "LINE" p1 p2 "")
 (setq p1 (list 221.50 1664.53) p2 (list 0.00 0.00))
 (command "TEXT" "J" "ML" p1   0.75  0.00 "564")
 (command "LAYER" "S" "CGBTHK" "")
 (setq p1 (list 226.00 1664.53) p2 (list 0.00 0.00))
 (command "TEXT" "J" "ML" p1   0.75  0.00 "4.20")
 (command "LAYER" "S" "CGBHZID" "")
 (setq p1 (list 230.50 1664.53) p2 (list 0.00 0.00))
 (command "TEXT" "J" "ML" p1   0.75  0.00 "")
 (setq p1 (list 232.75 1664.53) p2 (list 0.00 0.00))
 (command "TEXT" "J" "ML" p1   0.75  0.00 "7951")
 (command "LAYER" "S" "CGBLITHTXT" "")
 (setq p1 (list 236.50 1664.53) p2 (list 0.00 0.00))
 (command "TEXT" "J" "ML" p1   0.75  0.00 "HARD MASS SS")
 (command "LAYER" "S" "CGBCMNT" "")
 (setq p1 (list 256.75 1664.53) p2 (list 0.00 0.00))
 (command "TEXT" "J" "ML" p1   0.75  0.00 "")
 (command "LAYER" "S" "CGBMAIN" "")
 (setq p1 (list 214.00 1662.80) p2 (list 220.00 1662.80) p3 (list 220.00 1661.94) p4 (list 214.00 1661.94))
 (command "PLINE" p1 p2 p3 p4 "c")
 (command "HATCH" "ZIGZAG" 0.25 0.00 "L" "")
 (command "COLOR" "BYLAYER")
 (command "LAYER" "S" "CGBLITHCD" "")
 (setq p1 (list 220.00 1662.37) p2 (list 221.35 1662.37))
 (command "LINE" p1 p2 "")
 (setq p1 (list 221.50 1662.00) p2 (list 0.00 0.00))
 (command "TEXT" "J" "ML" p1   0.75  0.00 "742")
 (command "LAYER" "S" "CGBTHK" "")
 (setq p1 (list 226.00 1662.00) p2 (list 0.00 0.00))
 (command "TEXT" "J" "ML" p1   0.75  0.00 "0.86")
 (command "LAYER" "S" "CGBHZID" "")
 (setq p1 (list 230.50 1662.00) p2 (list 0.00 0.00))
 (command "TEXT" "J" "ML" p1   0.75  0.00 "")
 (setq p1 (list 232.75 1662.00) p2 (list 0.00 0.00))
 (command "TEXT" "J" "ML" p1   0.75  0.00 "7951")
 (command "LAYER" "S" "CGBLITHTXT" "")
 (setq p1 (list 236.50 1662.00) p2 (list 0.00 0.00))
 (command "TEXT" "J" "ML" p1   0.75  0.00 "GRY SH PEB CGL")
 (command "LAYER" "S" "CGBCMNT" "")
 (setq p1 (list 256.75 1662.00) p2 (list 0.00 0.00))
 (command "TEXT" "J" "ML" p1   0.75  0.00 "COALY SH W/PE")
 (command "LAYER" "S" "CGBMAIN" "")
 (setq p1 (list 214.00 1661.94) p2 (list 220.00 1661.94) p3 (list 220.00 1661.54) p4 (list 214.00 1661.54))
 (command "PLINE" p1 p2 p3 p4 "c")
 (command "HATCH" "ZIGZAG" 0.25 0.00 "L" "")
 (command "COLOR" "BYLAYER")
 (command "LAYER" "S" "CGBLITHCD" "")
 (setq p1 (list 220.00 1661.74) p2 (list 221.35 1660.49))
 (command "LINE" p1 p2 "")
 (setq p1 (list 221.50 1660.12) p2 (list 0.00 0.00))
 (command "TEXT" "J" "ML" p1   0.75  0.00 "742")
 (command "LAYER" "S" "CGBTHK" "")
 (setq p1 (list 226.00 1660.12) p2 (list 0.00 0.00))
 (command "TEXT" "J" "ML" p1   0.75  0.00 "0.40")
 (command "LAYER" "S" "CGBHZID" "")
 (setq p1 (list 230.50 1660.12) p2 (list 0.00 0.00))
 (command "TEXT" "J" "ML" p1   0.75  0.00 "")
 (setq p1 (list 232.75 1660.12) p2 (list 0.00 0.00))
 (command "TEXT" "J" "ML" p1   0.75  0.00 "7951")
 (command "LAYER" "S" "CGBLITHTXT" "")
 (setq p1 (list 236.50 1660.12) p2 (list 0.00 0.00))
 (command "TEXT" "J" "ML" p1   0.75  0.00 "GRY SH PEB CGL")
 (command "LAYER" "S" "CGBCMNT" "")
 (setq p1 (list 256.75 1660.12) p2 (list 0.00 0.00))
 (command "TEXT" "J" "ML" p1   0.75  0.00 "")
 (command "LAYER" "S" "CGBMAIN" "")
 (setq p1 (list 214.00 1661.54) p2 (list 220.00 1661.54) p3 (list 220.00 1659.14) p4 (list 214.00 1659.14))
 (command "PLINE" p1 p2 p3 p4 "c")
 (command "HATCH" "ZIGZAG" 0.25 0.00 "L" "")
 (command "COLOR" "BYLAYER")
 (command "LAYER" "S" "CGBLITHCD" "")
 (setq p1 (list 220.00 1660.34) p2 (list 221.35 1659.24))
 (command "LINE" p1 p2 "")
 (setq p1 (list 221.50 1658.87) p2 (list 0.00 0.00))
 (command "TEXT" "J" "ML" p1   0.75  0.00 "754")
 (command "LAYER" "S" "CGBTHK" "")
 (setq p1 (list 226.00 1658.87) p2 (list 0.00 0.00))
 (command "TEXT" "J" "ML" p1   0.75  0.00 "2.40")
 (command "LAYER" "S" "CGBHZID" "")
 (setq p1 (list 230.50 1658.87) p2 (list 0.00 0.00))
 (command "TEXT" "J" "ML" p1   0.75  0.00 "")
 (setq p1 (list 232.75 1658.87) p2 (list 0.00 0.00))
 (command "TEXT" "J" "ML" p1   0.75  0.00 "7951")
 (command "LAYER" "S" "CGBLITHTXT" "")
 (setq p1 (list 236.50 1658.87) p2 (list 0.00 0.00))
 (command "TEXT" "J" "ML" p1   0.75  0.00 "XTLIZED QTZ PEB CGL")
 (command "LAYER" "S" "CGBCMNT" "")
 (setq p1 (list 256.75 1658.87) p2 (list 0.00 0.00))
 (command "TEXT" "J" "ML" p1   0.75  0.00 "")
 (command "LAYER" "S" "CGBMAIN" "")
 (setq p1 (list 214.00 1659.14) p2 (list 220.00 1659.14) p3 (list 220.00 1658.97) p4 (list 214.00 1658.97))
 (command "PLINE" p1 p2 p3 p4 "c")
 (command "HATCH" "ZIGZAG" 0.25 0.00 "L" "")
 (command "COLOR" "BYLAYER")
 (command "LAYER" "S" "CGBLITHCD" "")
 (setq p1 (list 220.00 1659.06) p2 (list 221.35 1657.99))
 (command "LINE" p1 p2 "")
 (setq p1 (list 221.50 1657.62) p2 (list 0.00 0.00))
 (command "TEXT" "J" "ML" p1   0.75  0.00 "742")
 (command "LAYER" "S" "CGBTHK" "")
 (setq p1 (list 226.00 1657.62) p2 (list 0.00 0.00))
 (command "TEXT" "J" "ML" p1   0.75  0.00 "0.17")
 (command "LAYER" "S" "CGBHZID" "")
 (setq p1 (list 230.50 1657.62) p2 (list 0.00 0.00))
 (command "TEXT" "J" "ML" p1   0.75  0.00 "")
 (setq p1 (list 232.75 1657.62) p2 (list 0.00 0.00))
 (command "TEXT" "J" "ML" p1   0.75  0.00 "7951")
 (command "LAYER" "S" "CGBLITHTXT" "")
 (setq p1 (list 236.50 1657.62) p2 (list 0.00 0.00))
 (command "TEXT" "J" "ML" p1   0.75  0.00 "GRY SH PEB CGL")
 (command "LAYER" "S" "CGBCMNT" "")
 (setq p1 (list 256.75 1657.62) p2 (list 0.00 0.00))
 (command "TEXT" "J" "ML" p1   0.75  0.00 "")
 (command "LAYER" "S" "CGBMAIN" "")
 (setq p1 (list 214.00 1658.97) p2 (list 220.00 1658.97) p3 (list 220.00 1658.16) p4 (list 214.00 1658.16))
 (command "PLINE" p1 p2 p3 p4 "c")
 (command "HATCH" "ZIGZAG" 4.00 0.00 "L" "")
 (command "COLOR" "BYLAYER")
 (command "LAYER" "S" "CGBLITHCD" "")
 (setq p1 (list 220.00 1658.57) p2 (list 221.35 1656.74))
 (command "LINE" p1 p2 "")
 (setq p1 (list 221.50 1656.37) p2 (list 0.00 0.00))
 (command "TEXT" "J" "ML" p1   0.75  0.00 "124")
 (command "LAYER" "S" "CGBTHK" "")
 (setq p1 (list 226.00 1656.37) p2 (list 0.00 0.00))
 (command "TEXT" "J" "ML" p1   0.75  0.00 "0.81")
 (command "LAYER" "S" "CGBHZID" "")
 (setq p1 (list 230.50 1656.37) p2 (list 0.00 0.00))
 (command "TEXT" "J" "ML" p1   0.75  0.00 "")
 (setq p1 (list 232.75 1656.37) p2 (list 0.00 0.00))
 (command "TEXT" "J" "ML" p1   0.75  0.00 "7951")
 (command "LAYER" "S" "CGBLITHTXT" "")
 (setq p1 (list 236.50 1656.37) p2 (list 0.00 0.00))
 (command "TEXT" "J" "ML" p1   0.75  0.00 "DRK GRY SH")
 (command "LAYER" "S" "CGBCMNT" "")
 (setq p1 (list 256.75 1656.37) p2 (list 0.00 0.00))
 (command "TEXT" "J" "ML" p1   0.75  0.00 "SLX,BRKN")
 (command "LAYER" "S" "CGBMAIN" "")
 (setq p1 (list 214.00 1658.16) p2 (list 220.00 1658.16) p3 (list 220.00 1655.84) p4 (list 214.00 1655.84))
 (command "PLINE" p1 p2 p3 p4 "c")
 (command "HATCH" "ZIGZAG" 4.00 0.00 "L" "")
 (command "COLOR" "BYLAYER")
 (command "LAYER" "S" "CGBLITHCD" "")
 (setq p1 (list 220.00 1657.00) p2 (list 221.35 1655.49))
 (command "LINE" p1 p2 "")
 (setq p1 (list 221.50 1655.12) p2 (list 0.00 0.00))
 (command "TEXT" "J" "ML" p1   0.75  0.00 "373")
 (command "LAYER" "S" "CGBTHK" "")
 (setq p1 (list 226.00 1655.12) p2 (list 0.00 0.00))
 (command "TEXT" "J" "ML" p1   0.75  0.00 "2.32")
 (command "LAYER" "S" "CGBHZID" "")
 (setq p1 (list 230.50 1655.12) p2 (list 0.00 0.00))
 (command "TEXT" "J" "ML" p1   0.75  0.00 "")
 (setq p1 (list 232.75 1655.12) p2 (list 0.00 0.00))
 (command "TEXT" "J" "ML" p1   0.75  0.00 "7951")
 (command "LAYER" "S" "CGBLITHTXT" "")
 (setq p1 (list 236.50 1655.12) p2 (list 0.00 0.00))
 (command "TEXT" "J" "ML" p1   0.75  0.00 "GRY/GRN SH W/SS STKS")
 (command "LAYER" "S" "CGBCMNT" "")
 (setq p1 (list 256.75 1655.12) p2 (list 0.00 0.00))
 (command "TEXT" "J" "ML" p1   0.75  0.00 "")
 (command "LAYER" "S" "CGBMAIN" "")
 (setq p1 (list 214.00 1655.84) p2 (list 220.00 1655.84) p3 (list 220.00 1651.97) p4 (list 214.00 1651.97))
 (command "PLINE" p1 p2 p3 p4 "c")
 (command "HATCH" "ZIGZAG" 5.00 0.00 "L" "")
 (command "COLOR" "BYLAYER")
 (command "LAYER" "S" "CGBLITHCD" "")
 (setq p1 (list 220.00 1653.91) p2 (list 221.35 1653.91))
 (command "LINE" p1 p2 "")
 (setq p1 (list 221.50 1653.53) p2 (list 0.00 0.00))
 (command "TEXT" "J" "ML" p1   0.75  0.00 "274")
 (command "LAYER" "S" "CGBTHK" "")
 (setq p1 (list 226.00 1653.53) p2 (list 0.00 0.00))
 (command "TEXT" "J" "ML" p1   0.75  0.00 "3.87")
 (command "LAYER" "S" "CGBHZID" "")
 (setq p1 (list 230.50 1653.53) p2 (list 0.00 0.00))
 (command "TEXT" "J" "ML" p1   0.75  0.00 "")
 (setq p1 (list 232.75 1653.53) p2 (list 0.00 0.00))
 (command "TEXT" "J" "ML" p1   0.75  0.00 "7951")
 (command "LAYER" "S" "CGBLITHTXT" "")
 (setq p1 (list 236.50 1653.53) p2 (list 0.00 0.00))
 (command "TEXT" "J" "ML" p1   0.75  0.00 "GRY/GRN SH W/LS NODS")
 (command "LAYER" "S" "CGBCMNT" "")
 (setq p1 (list 256.75 1653.53) p2 (list 0.00 0.00))
 (command "TEXT" "J" "ML" p1   0.75  0.00 "CALC VEINS")
 (command "LAYER" "S" "CGBMAIN" "")
 (setq p1 (list 214.00 1651.97) p2 (list 220.00 1651.97) p3 (list 220.00 1649.92) p4 (list 214.00 1649.92))
 (command "PLINE" p1 p2 p3 p4 "c")
 (command "HATCH" "ZIGZAG" 5.00 0.00 "L" "")
 (command "COLOR" "BYLAYER")
 (command "LAYER" "S" "CGBLITHCD" "")
 (setq p1 (list 220.00 1650.95) p2 (list 221.35 1650.95))
 (command "LINE" p1 p2 "")
 (setq p1 (list 221.50 1650.57) p2 (list 0.00 0.00))
 (command "TEXT" "J" "ML" p1   0.75  0.00 "174")
 (command "LAYER" "S" "CGBTHK" "")
 (setq p1 (list 226.00 1650.57) p2 (list 0.00 0.00))
 (command "TEXT" "J" "ML" p1   0.75  0.00 "2.05")
 (command "LAYER" "S" "CGBHZID" "")
 (setq p1 (list 230.50 1650.57) p2 (list 0.00 0.00))
 (command "TEXT" "J" "ML" p1   0.75  0.00 "")
 (setq p1 (list 232.75 1650.57) p2 (list 0.00 0.00))
 (command "TEXT" "J" "ML" p1   0.75  0.00 "7951")
 (command "LAYER" "S" "CGBLITHTXT" "")
 (setq p1 (list 236.50 1650.57) p2 (list 0.00 0.00))
 (command "TEXT" "J" "ML" p1   0.75  0.00 "GRY/GRN SH")
 (command "LAYER" "S" "CGBCMNT" "")
 (setq p1 (list 256.75 1650.57) p2 (list 0.00 0.00))
 (command "TEXT" "J" "ML" p1   0.75  0.00 "")
 (command "LAYER" "S" "CGBMAIN" "")
 (setq p1 (list 214.00 1649.92) p2 (list 220.00 1649.92) p3 (list 220.00 1648.99) p4 (list 214.00 1648.99))
 (command "PLINE" p1 p2 p3 p4 "c")
 (command "HATCH" "ZIGZAG" 4.00 0.00 "L" "")
 (command "COLOR" "BYLAYER")
 (command "LAYER" "S" "CGBLITHCD" "")
 (setq p1 (list 220.00 1649.46) p2 (list 221.35 1649.46))
 (command "LINE" p1 p2 "")
 (setq p1 (list 221.50 1649.08) p2 (list 0.00 0.00))
 (command "TEXT" "J" "ML" p1   0.75  0.00 "374")
 (command "LAYER" "S" "CGBTHK" "")
 (setq p1 (list 226.00 1649.08) p2 (list 0.00 0.00))
 (command "TEXT" "J" "ML" p1   0.75  0.00 "0.93")
 (command "LAYER" "S" "CGBHZID" "")
 (setq p1 (list 230.50 1649.08) p2 (list 0.00 0.00))
 (command "TEXT" "J" "ML" p1   0.75  0.00 "")
 (setq p1 (list 232.75 1649.08) p2 (list 0.00 0.00))
 (command "TEXT" "J" "ML" p1   0.75  0.00 "7951")
 (command "LAYER" "S" "CGBLITHTXT" "")
 (setq p1 (list 236.50 1649.08) p2 (list 0.00 0.00))
 (command "TEXT" "J" "ML" p1   0.75  0.00 "GRY/GRN SDY SH")
 (command "LAYER" "S" "CGBCMNT" "")
 (setq p1 (list 256.75 1649.08) p2 (list 0.00 0.00))
 (command "TEXT" "J" "ML" p1   0.75  0.00 "")
 (command "LAYER" "S" "CGBMAIN" "")
 (setq p1 (list 214.00 1648.99) p2 (list 220.00 1648.99) p3 (list 220.00 1648.52) p4 (list 214.00 1648.52))
 (command "PLINE" p1 p2 p3 p4 "c")
 (command "HATCH" "ZIGZAG" 5.00 0.00 "L" "")
 (command "COLOR" "BYLAYER")
 (command "LAYER" "S" "CGBLITHCD" "")
 (setq p1 (list 220.00 1648.76) p2 (list 221.35 1647.51))
 (command "LINE" p1 p2 "")
 (setq p1 (list 221.50 1647.13) p2 (list 0.00 0.00))
 (command "TEXT" "J" "ML" p1   0.75  0.00 "904")
 (command "LAYER" "S" "CGBTHK" "")
 (setq p1 (list 226.00 1647.13) p2 (list 0.00 0.00))
 (command "TEXT" "J" "ML" p1   0.75  0.00 "0.47")
 (command "LAYER" "S" "CGBHZID" "")
 (setq p1 (list 230.50 1647.13) p2 (list 0.00 0.00))
 (command "TEXT" "J" "ML" p1   0.75  0.00 "")
 (setq p1 (list 232.75 1647.13) p2 (list 0.00 0.00))
 (command "TEXT" "J" "ML" p1   0.75  0.00 "7951")
 (command "LAYER" "S" "CGBLITHTXT" "")
 (setq p1 (list 236.50 1647.13) p2 (list 0.00 0.00))
 (command "TEXT" "J" "ML" p1   0.75  0.00 "MASS FN GRND LS")
 (command "LAYER" "S" "CGBCMNT" "")
 (setq p1 (list 256.75 1647.13) p2 (list 0.00 0.00))
 (command "TEXT" "J" "ML" p1   0.75  0.00 "")
 (command "LAYER" "S" "CGBMAIN" "")
 (setq p1 (list 214.00 1648.52) p2 (list 220.00 1648.52) p3 (list 220.00 1646.94) p4 (list 214.00 1646.94))
 (command "PLINE" p1 p2 p3 p4 "c")
 (command "HATCH" "ZIGZAG" 4.00 0.00 "L" "")
 (command "COLOR" "BYLAYER")
 (command "LAYER" "S" "CGBLITHCD" "")
 (setq p1 (list 220.00 1647.73) p2 (list 221.35 1646.26))
 (command "LINE" p1 p2 "")
 (setq p1 (list 221.50 1645.88) p2 (list 0.00 0.00))
 (command "TEXT" "J" "ML" p1   0.75  0.00 "344")
 (command "LAYER" "S" "CGBTHK" "")
 (setq p1 (list 226.00 1645.88) p2 (list 0.00 0.00))
 (command "TEXT" "J" "ML" p1   0.75  0.00 "1.58")
 (command "LAYER" "S" "CGBHZID" "")
 (setq p1 (list 230.50 1645.88) p2 (list 0.00 0.00))
 (command "TEXT" "J" "ML" p1   0.75  0.00 "")
 (setq p1 (list 232.75 1645.88) p2 (list 0.00 0.00))
 (command "TEXT" "J" "ML" p1   0.75  0.00 "7951")
 (command "LAYER" "S" "CGBLITHTXT" "")
 (setq p1 (list 236.50 1645.88) p2 (list 0.00 0.00))
 (command "TEXT" "J" "ML" p1   0.75  0.00 "GRN MASS SDY SH")
 (command "LAYER" "S" "CGBCMNT" "")
 (setq p1 (list 256.75 1645.88) p2 (list 0.00 0.00))
 (command "TEXT" "J" "ML" p1   0.75  0.00 "")
 (command "LAYER" "S" "CGBMAIN" "")
 (setq p1 (list 214.00 1646.94) p2 (list 220.00 1646.94) p3 (list 220.00 1642.94) p4 (list 214.00 1642.94))
 (command "PLINE" p1 p2 p3 p4 "c")
 (command "HATCH" "ZIGZAG" 4.00 0.00 "L" "")
 (command "COLOR" "BYLAYER")
 (command "LAYER" "S" "CGBLITHCD" "")
 (setq p1 (list 220.00 1644.94) p2 (list 221.35 1644.94))
 (command "LINE" p1 p2 "")
 (setq p1 (list 221.50 1644.57) p2 (list 0.00 0.00))
 (command "TEXT" "J" "ML" p1   0.75  0.00 "344")
 (command "LAYER" "S" "CGBTHK" "")
 (setq p1 (list 226.00 1644.57) p2 (list 0.00 0.00))
 (command "TEXT" "J" "ML" p1   0.75  0.00 "4.00")
 (command "LAYER" "S" "CGBHZID" "")
 (setq p1 (list 230.50 1644.57) p2 (list 0.00 0.00))
 (command "TEXT" "J" "ML" p1   0.75  0.00 "")
 (setq p1 (list 232.75 1644.57) p2 (list 0.00 0.00))
 (command "TEXT" "J" "ML" p1   0.75  0.00 "7951")
 (command "LAYER" "S" "CGBLITHTXT" "")
 (setq p1 (list 236.50 1644.57) p2 (list 0.00 0.00))
 (command "TEXT" "J" "ML" p1   0.75  0.00 "GRN MASS SDY SH")
 (command "LAYER" "S" "CGBCMNT" "")
 (setq p1 (list 256.75 1644.57) p2 (list 0.00 0.00))
 (command "TEXT" "J" "ML" p1   0.75  0.00 "GB")
 (command "LAYER" "S" "CGBMAIN" "")
 (setq p1 (list 214.00 1642.94) p2 (list 220.00 1642.94) p3 (list 220.00 1639.17) p4 (list 214.00 1639.17))
 (command "PLINE" p1 p2 p3 p4 "c")
 (command "HATCH" "ZIGZAG" 4.00 0.00 "L" "")
 (command "COLOR" "BYLAYER")
 (command "LAYER" "S" "CGBLITHCD" "")
 (setq p1 (list 220.00 1641.06) p2 (list 221.35 1641.06))
 (command "LINE" p1 p2 "")
 (setq p1 (list 221.50 1640.68) p2 (list 0.00 0.00))
 (command "TEXT" "J" "ML" p1   0.75  0.00 "373")
 (command "LAYER" "S" "CGBTHK" "")
 (setq p1 (list 226.00 1640.68) p2 (list 0.00 0.00))
 (command "TEXT" "J" "ML" p1   0.75  0.00 "3.77")
 (command "LAYER" "S" "CGBHZID" "")
 (setq p1 (list 230.50 1640.68) p2 (list 0.00 0.00))
 (command "TEXT" "J" "ML" p1   0.75  0.00 "")
 (setq p1 (list 232.75 1640.68) p2 (list 0.00 0.00))
 (command "TEXT" "J" "ML" p1   0.75  0.00 "7951")
 (command "LAYER" "S" "CGBLITHTXT" "")
 (setq p1 (list 236.50 1640.68) p2 (list 0.00 0.00))
 (command "TEXT" "J" "ML" p1   0.75  0.00 "GRY/GRN SH W/SS STKS")
 (command "LAYER" "S" "CGBCMNT" "")
 (setq p1 (list 256.75 1640.68) p2 (list 0.00 0.00))
 (command "TEXT" "J" "ML" p1   0.75  0.00 "GB")
 (command "LAYER" "S" "CGBMAIN" "")
 (setq p1 (list 214.00 1639.17) p2 (list 220.00 1639.17) p3 (list 220.00 1634.22) p4 (list 214.00 1634.22))
 (command "PLINE" p1 p2 p3 p4 "c")
 (command "HATCH" "ZIGZAG" 4.00 0.00 "L" "")
 (command "COLOR" "BYLAYER")
 (command "LAYER" "S" "CGBLITHCD" "")
 (setq p1 (list 220.00 1636.70) p2 (list 221.35 1636.70))
 (command "LINE" p1 p2 "")
 (setq p1 (list 221.50 1636.32) p2 (list 0.00 0.00))
 (command "TEXT" "J" "ML" p1   0.75  0.00 "124")
 (command "LAYER" "S" "CGBTHK" "")
 (setq p1 (list 226.00 1636.32) p2 (list 0.00 0.00))
 (command "TEXT" "J" "ML" p1   0.75  0.00 "4.95")
 (command "LAYER" "S" "CGBHZID" "")
 (setq p1 (list 230.50 1636.32) p2 (list 0.00 0.00))
 (command "TEXT" "J" "ML" p1   0.75  0.00 "")
 (setq p1 (list 232.75 1636.32) p2 (list 0.00 0.00))
 (command "TEXT" "J" "ML" p1   0.75  0.00 "7951")
 (command "LAYER" "S" "CGBLITHTXT" "")
 (setq p1 (list 236.50 1636.32) p2 (list 0.00 0.00))
 (command "TEXT" "J" "ML" p1   0.75  0.00 "DRK GRY SH")
 (command "LAYER" "S" "CGBCMNT" "")
 (setq p1 (list 256.75 1636.32) p2 (list 0.00 0.00))
 (command "TEXT" "J" "ML" p1   0.75  0.00 "GB")
 (command "LAYER" "S" "CGBMAIN" "")
 (setq p1 (list 214.00 1634.22) p2 (list 220.00 1634.22) p3 (list 220.00 1631.94) p4 (list 214.00 1631.94))
 (command "PLINE" p1 p2 p3 p4 "c")
 (command "HATCH" "ZIGZAG" 4.00 22.50 "L" "")
 (command "COLOR" "BYLAYER")
 (command "LAYER" "S" "CGBLITHCD" "")
 (setq p1 (list 220.00 1633.08) p2 (list 221.35 1633.08))
 (command "LINE" p1 p2 "")
 (setq p1 (list 221.50 1632.71) p2 (list 0.00 0.00))
 (command "TEXT" "J" "ML" p1   0.75  0.00 "114")
 (command "LAYER" "S" "CGBTHK" "")
 (setq p1 (list 226.00 1632.71) p2 (list 0.00 0.00))
 (command "TEXT" "J" "ML" p1   0.75  0.00 "2.28")
 (command "LAYER" "S" "CGBHZID" "")
 (setq p1 (list 230.50 1632.71) p2 (list 0.00 0.00))
 (command "TEXT" "J" "ML" p1   0.75  0.00 "")
 (setq p1 (list 232.75 1632.71) p2 (list 0.00 0.00))
 (command "TEXT" "J" "ML" p1   0.75  0.00 "7951")
 (command "LAYER" "S" "CGBLITHTXT" "")
 (setq p1 (list 236.50 1632.71) p2 (list 0.00 0.00))
 (command "TEXT" "J" "ML" p1   0.75  0.00 "BLK SH")
 (command "LAYER" "S" "CGBCMNT" "")
 (setq p1 (list 256.75 1632.71) p2 (list 0.00 0.00))
 (command "TEXT" "J" "ML" p1   0.75  0.00 "")
 (command "LAYER" "S" "CGBMAIN" "")
 (setq p1 (list 214.00 1631.94) p2 (list 220.00 1631.94) p3 (list 220.00 1630.68) p4 (list 214.00 1630.68))
 (command "PLINE" p1 p2 p3 p4 "c")
 (command "HATCH" "ZIGZAG" 4.00 22.50 "L" "")
 (command "COLOR" "BYLAYER")
 (command "LAYER" "S" "CGBLITHCD" "")
 (setq p1 (list 220.00 1631.31) p2 (list 221.35 1631.31))
 (command "LINE" p1 p2 "")
 (setq p1 (list 221.50 1630.94) p2 (list 0.00 0.00))
 (command "TEXT" "J" "ML" p1   0.75  0.00 "114")
 (command "LAYER" "S" "CGBTHK" "")
 (setq p1 (list 226.00 1630.94) p2 (list 0.00 0.00))
 (command "TEXT" "J" "ML" p1   0.75  0.00 "1.26")
 (command "LAYER" "S" "CGBHZID" "")
 (setq p1 (list 230.50 1630.94) p2 (list 0.00 0.00))
 (command "TEXT" "J" "ML" p1   0.75  0.00 "")
 (setq p1 (list 232.75 1630.94) p2 (list 0.00 0.00))
 (command "TEXT" "J" "ML" p1   0.75  0.00 "7951")
 (command "LAYER" "S" "CGBLITHTXT" "")
 (setq p1 (list 236.50 1630.94) p2 (list 0.00 0.00))
 (command "TEXT" "J" "ML" p1   0.75  0.00 "BLK SH")
 (command "LAYER" "S" "CGBCMNT" "")
 (setq p1 (list 256.75 1630.94) p2 (list 0.00 0.00))
 (command "TEXT" "J" "ML" p1   0.75  0.00 "PYRT/CALC VEI")
 (command "LAYER" "S" "CGBMAIN" "")
 (setq p1 (list 214.00 1630.68) p2 (list 220.00 1630.68) p3 (list 220.00 1630.20) p4 (list 214.00 1630.20))
 (command "PLINE" p1 p2 p3 p4 "c")
 (command "HATCH" "ZIGZAG" 0.40 45.00 "L" "")
 (command "COLOR" "BYLAYER")
 (command "LAYER" "S" "CGBLITHCD" "")
 (setq p1 (list 220.00 1630.44) p2 (list 221.35 1629.19))
 (command "LINE" p1 p2 "")
 (setq p1 (list 221.50 1628.82) p2 (list 0.00 0.00))
 (command "TEXT" "J" "ML" p1   0.75  0.00 "023")
 (command "LAYER" "S" "CGBTHK" "")
 (setq p1 (list 226.00 1628.82) p2 (list 0.00 0.00))
 (command "TEXT" "J" "ML" p1   0.75  0.00 "0.48")
 (command "LAYER" "S" "CGBHZID" "")
 (setq p1 (list 230.50 1628.82) p2 (list 0.00 0.00))
 (command "TEXT" "J" "ML" p1   0.75  0.00 "")
 (setq p1 (list 232.75 1628.82) p2 (list 0.00 0.00))
 (command "TEXT" "J" "ML" p1   0.75  0.00 "7500")
 (command "LAYER" "S" "CGBLITHTXT" "")
 (setq p1 (list 236.50 1628.82) p2 (list 0.00 0.00))
 (command "TEXT" "J" "ML" p1   0.75  0.00 "COAL W/BONE STKS")
 (command "LAYER" "S" "CGBCMNT" "")
 (setq p1 (list 256.75 1628.82) p2 (list 0.00 0.00))
 (command "TEXT" "J" "ML" p1   0.75  0.00 "BONEY @ TOP")
 (command "LAYER" "S" "CGBMAIN" "")
 (setq p1 (list 214.00 1630.20) p2 (list 220.00 1630.20) p3 (list 220.00 1629.98) p4 (list 214.00 1629.98))
 (command "PLINE" p1 p2 p3 p4 "c")
 (command "HATCH" "ZIGZAG" 4.00 22.50 "L" "")
 (command "COLOR" "BYLAYER")
 (command "LAYER" "S" "CGBLITHCD" "")
 (setq p1 (list 220.00 1630.09) p2 (list 221.35 1627.94))
 (command "LINE" p1 p2 "")
 (setq p1 (list 221.50 1627.57) p2 (list 0.00 0.00))
 (command "TEXT" "J" "ML" p1   0.75  0.00 "114")
 (command "LAYER" "S" "CGBTHK" "")
 (setq p1 (list 226.00 1627.57) p2 (list 0.00 0.00))
 (command "TEXT" "J" "ML" p1   0.75  0.00 "0.22")
 (command "LAYER" "S" "CGBHZID" "")
 (setq p1 (list 230.50 1627.57) p2 (list 0.00 0.00))
 (command "TEXT" "J" "ML" p1   0.75  0.00 "")
 (setq p1 (list 232.75 1627.57) p2 (list 0.00 0.00))
 (command "TEXT" "J" "ML" p1   0.75  0.00 "7500")
 (command "LAYER" "S" "CGBLITHTXT" "")
 (setq p1 (list 236.50 1627.57) p2 (list 0.00 0.00))
 (command "TEXT" "J" "ML" p1   0.75  0.00 "BLK SH")
 (command "LAYER" "S" "CGBCMNT" "")
 (setq p1 (list 256.75 1627.57) p2 (list 0.00 0.00))
 (command "TEXT" "J" "ML" p1   0.75  0.00 "mmmmmmmmmmmmmmmmmmmmmmmmmmmmmmmmmmmmmmmmmmmmmmmmmmmmmmmmmmmm")
 (command "LAYER" "S" "CGBMAIN" "")
 (setq p1 (list 214.00 1629.98) p2 (list 220.00 1629.98) p3 (list 220.00 1629.61) p4 (list 214.00 1629.61))
 (command "PLINE" p1 p2 p3 p4 "c")
 (command "HATCH" "ZIGZAG" 1.00 45.00 "L" "")
 (command "COLOR" "BYLAYER")
 (command "LAYER" "S" "CGBLITHCD" "")
 (setq p1 (list 220.00 1629.80) p2 (list 221.35 1626.69))
 (command "LINE" p1 p2 "")
 (setq p1 (list 221.50 1626.32) p2 (list 0.00 0.00))
 (command "TEXT" "J" "ML" p1   0.75  0.00 "028")
 (command "LAYER" "S" "CGBTHK" "")
 (setq p1 (list 226.00 1626.32) p2 (list 0.00 0.00))
 (command "TEXT" "J" "ML" p1   0.75  0.00 "0.37")
 (command "LAYER" "S" "CGBHZID" "")
 (setq p1 (list 230.50 1626.32) p2 (list 0.00 0.00))
 (command "TEXT" "J" "ML" p1   0.75  0.00 "")
 (setq p1 (list 232.75 1626.32) p2 (list 0.00 0.00))
 (command "TEXT" "J" "ML" p1   0.75  0.00 "7500")
 (command "LAYER" "S" "CGBLITHTXT" "")
 (setq p1 (list 236.50 1626.32) p2 (list 0.00 0.00))
 (command "TEXT" "J" "ML" p1   0.75  0.00 "COAL W/SH STKS")
 (command "LAYER" "S" "CGBCMNT" "")
 (setq p1 (list 256.75 1626.32) p2 (list 0.00 0.00))
 (command "TEXT" "J" "ML" p1   0.75  0.00 "CALC STKS")
 (command "LAYER" "S" "CGBMAIN" "")
 (setq p1 (list 214.00 1629.61) p2 (list 220.00 1629.61) p3 (list 220.00 1629.50) p4 (list 214.00 1629.50))
 (command "PLINE" p1 p2 p3 p4 "c")
 (command "HATCH" "ZIGZAG" 6.00 0.00 "L" "")
 (command "COLOR" "BYLAYER")
 (command "LAYER" "S" "CGBLITHCD" "")
 (setq p1 (list 220.00 1629.56) p2 (list 221.35 1625.44))
 (command "LINE" p1 p2 "")
 (setq p1 (list 221.50 1625.07) p2 (list 0.00 0.00))
 (command "TEXT" "J" "ML" p1   0.75  0.00 "113")
 (command "LAYER" "S" "CGBTHK" "")
 (setq p1 (list 226.00 1625.07) p2 (list 0.00 0.00))
 (command "TEXT" "J" "ML" p1   0.75  0.00 "0.11")
 (command "LAYER" "S" "CGBHZID" "")
 (setq p1 (list 230.50 1625.07) p2 (list 0.00 0.00))
 (command "TEXT" "J" "ML" p1   0.75  0.00 "")
 (setq p1 (list 232.75 1625.07) p2 (list 0.00 0.00))
 (command "TEXT" "J" "ML" p1   0.75  0.00 "7451")
 (command "LAYER" "S" "CGBLITHTXT" "")
 (setq p1 (list 236.50 1625.07) p2 (list 0.00 0.00))
 (command "TEXT" "J" "ML" p1   0.75  0.00 "BLK SH W/COAL STKS")
 (command "LAYER" "S" "CGBCMNT" "")
 (setq p1 (list 256.75 1625.07) p2 (list 0.00 0.00))
 (command "TEXT" "J" "ML" p1   0.75  0.00 "CALC STKS")
 (command "LAYER" "S" "CGBMAIN" "")
 (setq p1 (list 214.00 1629.50) p2 (list 220.00 1629.50) p3 (list 220.00 1628.61) p4 (list 214.00 1628.61))
 (command "PLINE" p1 p2 p3 p4 "c")
 (command "HATCH" "ZIGZAG" 0.25 0.00 "L" "")
 (command "COLOR" "BYLAYER")
 (command "LAYER" "S" "CGBLITHCD" "")
 (setq p1 (list 220.00 1629.06) p2 (list 221.35 1624.19))
 (command "LINE" p1 p2 "")
 (setq p1 (list 221.50 1623.82) p2 (list 0.00 0.00))
 (command "TEXT" "J" "ML" p1   0.75  0.00 "127")
 (command "LAYER" "S" "CGBTHK" "")
 (setq p1 (list 226.00 1623.82) p2 (list 0.00 0.00))
 (command "TEXT" "J" "ML" p1   0.75  0.00 "0.89")
 (command "LAYER" "S" "CGBHZID" "")
 (setq p1 (list 230.50 1623.82) p2 (list 0.00 0.00))
 (command "TEXT" "J" "ML" p1   0.75  0.00 "")
 (setq p1 (list 232.75 1623.82) p2 (list 0.00 0.00))
 (command "TEXT" "J" "ML" p1   0.75  0.00 "7451")
 (command "LAYER" "S" "CGBLITHTXT" "")
 (setq p1 (list 236.50 1623.82) p2 (list 0.00 0.00))
 (command "TEXT" "J" "ML" p1   0.75  0.00 "DRK GRY FIRECLAY")
 (command "LAYER" "S" "CGBCMNT" "")
 (setq p1 (list 256.75 1623.82) p2 (list 0.00 0.00))
 (command "TEXT" "J" "ML" p1   0.75  0.00 "GB")
 (command "LAYER" "S" "CGBMAIN" "")
 (setq p1 (list 214.00 1628.61) p2 (list 220.00 1628.61) p3 (list 220.00 1623.82) p4 (list 214.00 1623.82))
 (command "PLINE" p1 p2 p3 p4 "c")
 (command "HATCH" "ZIGZAG" 2.50 90.00 "L" "")
 (command "COLOR" "BYLAYER")
 (command "LAYER" "S" "CGBLITHCD" "")
 (setq p1 (list 220.00 1626.22) p2 (list 221.35 1622.94))
 (command "LINE" p1 p2 "")
 (setq p1 (list 221.50 1622.57) p2 (list 0.00 0.00))
 (command "TEXT" "J" "ML" p1   0.75  0.00 "324")
 (command "LAYER" "S" "CGBTHK" "")
 (setq p1 (list 226.00 1622.57) p2 (list 0.00 0.00))
 (command "TEXT" "J" "ML" p1   0.75  0.00 "4.79")
 (command "LAYER" "S" "CGBHZID" "")
 (setq p1 (list 230.50 1622.57) p2 (list 0.00 0.00))
 (command "TEXT" "J" "ML" p1   0.75  0.00 "")
 (setq p1 (list 232.75 1622.57) p2 (list 0.00 0.00))
 (command "TEXT" "J" "ML" p1   0.75  0.00 "7451")
 (command "LAYER" "S" "CGBLITHTXT" "")
 (setq p1 (list 236.50 1622.57) p2 (list 0.00 0.00))
 (command "TEXT" "J" "ML" p1   0.75  0.00 "DRK GRY MASS SDY SH")
 (command "LAYER" "S" "CGBCMNT" "")
 (setq p1 (list 256.75 1622.57) p2 (list 0.00 0.00))
 (command "TEXT" "J" "ML" p1   0.75  0.00 "CALC STKS")
 (command "LAYER" "S" "CGBMAIN" "")
 (setq p1 (list 214.00 1623.82) p2 (list 220.00 1623.82) p3 (list 220.00 1623.16) p4 (list 214.00 1623.16))
 (command "PLINE" p1 p2 p3 p4 "c")
 (command "HATCH" "ZIGZAG" 5.00 0.00 "L" "")
 (command "COLOR" "BYLAYER")
 (command "LAYER" "S" "CGBLITHCD" "")
 (setq p1 (list 220.00 1623.49) p2 (list 221.35 1621.69))
 (command "LINE" p1 p2 "")
 (setq p1 (list 221.50 1621.32) p2 (list 0.00 0.00))
 (command "TEXT" "J" "ML" p1   0.75  0.00 "904")
 (command "LAYER" "S" "CGBTHK" "")
 (setq p1 (list 226.00 1621.32) p2 (list 0.00 0.00))
 (command "TEXT" "J" "ML" p1   0.75  0.00 "0.66")
 (command "LAYER" "S" "CGBHZID" "")
 (setq p1 (list 230.50 1621.32) p2 (list 0.00 0.00))
 (command "TEXT" "J" "ML" p1   0.75  0.00 "")
 (setq p1 (list 232.75 1621.32) p2 (list 0.00 0.00))
 (command "TEXT" "J" "ML" p1   0.75  0.00 "7451")
 (command "LAYER" "S" "CGBLITHTXT" "")
 (setq p1 (list 236.50 1621.32) p2 (list 0.00 0.00))
 (command "TEXT" "J" "ML" p1   0.75  0.00 "MASS FN GRND LS")
 (command "LAYER" "S" "CGBCMNT" "")
 (setq p1 (list 256.75 1621.32) p2 (list 0.00 0.00))
 (command "TEXT" "J" "ML" p1   0.75  0.00 "")
 (command "LAYER" "S" "CGBMAIN" "")
 (setq p1 (list 214.00 1623.16) p2 (list 220.00 1623.16) p3 (list 220.00 1616.94) p4 (list 214.00 1616.94))
 (command "PLINE" p1 p2 p3 p4 "c")
 (command "HATCH" "ZIGZAG" 5.00 0.00 "L" "")
 (command "COLOR" "BYLAYER")
 (command "LAYER" "S" "CGBLITHCD" "")
 (setq p1 (list 220.00 1620.05) p2 (list 221.35 1620.05))
 (command "LINE" p1 p2 "")
 (setq p1 (list 221.50 1619.68) p2 (list 0.00 0.00))
 (command "TEXT" "J" "ML" p1   0.75  0.00 "322")
 (command "LAYER" "S" "CGBTHK" "")
 (setq p1 (list 226.00 1619.68) p2 (list 0.00 0.00))
 (command "TEXT" "J" "ML" p1   0.75  0.00 "6.22")
 (command "LAYER" "S" "CGBHZID" "")
 (setq p1 (list 230.50 1619.68) p2 (list 0.00 0.00))
 (command "TEXT" "J" "ML" p1   0.75  0.00 "")
 (setq p1 (list 232.75 1619.68) p2 (list 0.00 0.00))
 (command "TEXT" "J" "ML" p1   0.75  0.00 "7451")
 (command "LAYER" "S" "CGBLITHTXT" "")
 (setq p1 (list 236.50 1619.68) p2 (list 0.00 0.00))
 (command "TEXT" "J" "ML" p1   0.75  0.00 "DRK GRY SH+INTERBED SS")
 (command "LAYER" "S" "CGBCMNT" "")
 (setq p1 (list 256.75 1619.68) p2 (list 0.00 0.00))
 (command "TEXT" "J" "ML" p1   0.75  0.00 "")
 (command "LAYER" "S" "CGBMAIN" "")
 (setq p1 (list 214.00 1616.94) p2 (list 220.00 1616.94) p3 (list 220.00 1616.66) p4 (list 214.00 1616.66))
 (command "PLINE" p1 p2 p3 p4 "c")
 (command "HATCH" "ZIGZAG" 5.00 0.00 "L" "")
 (command "COLOR" "BYLAYER")
 (command "LAYER" "S" "CGBLITHCD" "")
 (setq p1 (list 220.00 1616.80) p2 (list 221.35 1616.80))
 (command "LINE" p1 p2 "")
 (setq p1 (list 221.50 1616.43) p2 (list 0.00 0.00))
 (command "TEXT" "J" "ML" p1   0.75  0.00 "322")
 (command "LAYER" "S" "CGBTHK" "")
 (setq p1 (list 226.00 1616.43) p2 (list 0.00 0.00))
 (command "TEXT" "J" "ML" p1   0.75  0.00 "0.28")
 (command "LAYER" "S" "CGBHZID" "")
 (setq p1 (list 230.50 1616.43) p2 (list 0.00 0.00))
 (command "TEXT" "J" "ML" p1   0.75  0.00 "")
 (setq p1 (list 232.75 1616.43) p2 (list 0.00 0.00))
 (command "TEXT" "J" "ML" p1   0.75  0.00 "7451")
 (command "LAYER" "S" "CGBLITHTXT" "")
 (setq p1 (list 236.50 1616.43) p2 (list 0.00 0.00))
 (command "TEXT" "J" "ML" p1   0.75  0.00 "DRK GRY SH+INTERBED SS")
 (command "LAYER" "S" "CGBCMNT" "")
 (setq p1 (list 256.75 1616.43) p2 (list 0.00 0.00))
 (command "TEXT" "J" "ML" p1   0.75  0.00 "")
 (command "LAYER" "S" "CGBMAIN" "")
 (setq p1 (list 214.00 1616.66) p2 (list 220.00 1616.66) p3 (list 220.00 1615.04) p4 (list 214.00 1615.04))
 (command "PLINE" p1 p2 p3 p4 "c")
 (command "HATCH" "ZIGZAG" 4.00 0.00 "L" "")
 (command "COLOR" "BYLAYER")
 (command "LAYER" "S" "CGBLITHCD" "")
 (setq p1 (list 220.00 1615.85) p2 (list 221.35 1614.60))
 (command "LINE" p1 p2 "")
 (setq p1 (list 221.50 1614.23) p2 (list 0.00 0.00))
 (command "TEXT" "J" "ML" p1   0.75  0.00 "543")
 (command "LAYER" "S" "CGBTHK" "")
 (setq p1 (list 226.00 1614.23) p2 (list 0.00 0.00))
 (command "TEXT" "J" "ML" p1   0.75  0.00 "1.62")
 (command "LAYER" "S" "CGBHZID" "")
 (setq p1 (list 230.50 1614.23) p2 (list 0.00 0.00))
 (command "TEXT" "J" "ML" p1   0.75  0.00 "")
 (setq p1 (list 232.75 1614.23) p2 (list 0.00 0.00))
 (command "TEXT" "J" "ML" p1   0.75  0.00 "7451")
 (command "LAYER" "S" "CGBLITHTXT" "")
 (setq p1 (list 236.50 1614.23) p2 (list 0.00 0.00))
 (command "TEXT" "J" "ML" p1   0.75  0.00 "GRY SS W/SH STKS")
 (command "LAYER" "S" "CGBCMNT" "")
 (setq p1 (list 256.75 1614.23) p2 (list 0.00 0.00))
 (command "TEXT" "J" "ML" p1   0.75  0.00 "SLC")
 (command "LAYER" "S" "CGBMAIN" "")
 (setq p1 (list 214.00 1615.04) p2 (list 220.00 1615.04) p3 (list 220.00 1614.42) p4 (list 214.00 1614.42))
 (command "PLINE" p1 p2 p3 p4 "c")
 (command "HATCH" "ZIGZAG" 4.00 22.50 "L" "")
 (command "COLOR" "BYLAYER")
 (command "LAYER" "S" "CGBLITHCD" "")
 (setq p1 (list 220.00 1614.73) p2 (list 221.35 1613.35))
 (command "LINE" p1 p2 "")
 (setq p1 (list 221.50 1612.98) p2 (list 0.00 0.00))
 (command "TEXT" "J" "ML" p1   0.75  0.00 "114")
 (command "LAYER" "S" "CGBTHK" "")
 (setq p1 (list 226.00 1612.98) p2 (list 0.00 0.00))
 (command "TEXT" "J" "ML" p1   0.75  0.00 "0.62")
 (command "LAYER" "S" "CGBHZID" "")
 (setq p1 (list 230.50 1612.98) p2 (list 0.00 0.00))
 (command "TEXT" "J" "ML" p1   0.75  0.00 "")
 (setq p1 (list 232.75 1612.98) p2 (list 0.00 0.00))
 (command "TEXT" "J" "ML" p1   0.75  0.00 "7451")
 (command "LAYER" "S" "CGBLITHTXT" "")
 (setq p1 (list 236.50 1612.98) p2 (list 0.00 0.00))
 (command "TEXT" "J" "ML" p1   0.75  0.00 "BLK SH")
 (command "LAYER" "S" "CGBCMNT" "")
 (setq p1 (list 256.75 1612.98) p2 (list 0.00 0.00))
 (command "TEXT" "J" "ML" p1   0.75  0.00 "")
 (command "LAYER" "S" "CGBMAIN" "")
 (setq p1 (list 214.00 1614.42) p2 (list 220.00 1614.42) p3 (list 220.00 1613.64) p4 (list 214.00 1613.64))
 (command "PLINE" p1 p2 p3 p4 "c")
 (command "HATCH" "ZIGZAG" 2.50 90.00 "L" "")
 (command "COLOR" "BYLAYER")
 (command "LAYER" "S" "CGBLITHCD" "")
 (setq p1 (list 220.00 1614.03) p2 (list 221.35 1612.10))
 (command "LINE" p1 p2 "")
 (setq p1 (list 221.50 1611.73) p2 (list 0.00 0.00))
 (command "TEXT" "J" "ML" p1   0.75  0.00 "324")
 (command "LAYER" "S" "CGBTHK" "")
 (setq p1 (list 226.00 1611.73) p2 (list 0.00 0.00))
 (command "TEXT" "J" "ML" p1   0.75  0.00 "0.78")
 (command "LAYER" "S" "CGBHZID" "")
 (setq p1 (list 230.50 1611.73) p2 (list 0.00 0.00))
 (command "TEXT" "J" "ML" p1   0.75  0.00 "")
 (setq p1 (list 232.75 1611.73) p2 (list 0.00 0.00))
 (command "TEXT" "J" "ML" p1   0.75  0.00 "7451")
 (command "LAYER" "S" "CGBLITHTXT" "")
 (setq p1 (list 236.50 1611.73) p2 (list 0.00 0.00))
 (command "TEXT" "J" "ML" p1   0.75  0.00 "DRK GRY MASS SDY SH")
 (command "LAYER" "S" "CGBCMNT" "")
 (setq p1 (list 256.75 1611.73) p2 (list 0.00 0.00))
 (command "TEXT" "J" "ML" p1   0.75  0.00 "")
 (command "LAYER" "S" "CGBMAIN" "")
 (setq p1 (list 214.00 1613.64) p2 (list 220.00 1613.64) p3 (list 220.00 1611.82) p4 (list 214.00 1611.82))
 (command "PLINE" p1 p2 p3 p4 "c")
 (command "HATCH" "ZIGZAG" 4.00 22.50 "L" "")
 (command "COLOR" "BYLAYER")
 (command "LAYER" "S" "CGBLITHCD" "")
 (setq p1 (list 220.00 1612.73) p2 (list 221.35 1610.85))
 (command "LINE" p1 p2 "")
 (setq p1 (list 221.50 1610.48) p2 (list 0.00 0.00))
 (command "TEXT" "J" "ML" p1   0.75  0.00 "114")
 (command "LAYER" "S" "CGBTHK" "")
 (setq p1 (list 226.00 1610.48) p2 (list 0.00 0.00))
 (command "TEXT" "J" "ML" p1   0.75  0.00 "1.82")
 (command "LAYER" "S" "CGBHZID" "")
 (setq p1 (list 230.50 1610.48) p2 (list 0.00 0.00))
 (command "TEXT" "J" "ML" p1   0.75  0.00 "")
 (setq p1 (list 232.75 1610.48) p2 (list 0.00 0.00))
 (command "TEXT" "J" "ML" p1   0.75  0.00 "7451")
 (command "LAYER" "S" "CGBLITHTXT" "")
 (setq p1 (list 236.50 1610.48) p2 (list 0.00 0.00))
 (command "TEXT" "J" "ML" p1   0.75  0.00 "BLK SH")
 (command "LAYER" "S" "CGBCMNT" "")
 (setq p1 (list 256.75 1610.48) p2 (list 0.00 0.00))
 (command "TEXT" "J" "ML" p1   0.75  0.00 "")
 (command "LAYER" "S" "CGBMAIN" "")
 (setq p1 (list 214.00 1611.82) p2 (list 220.00 1611.82) p3 (list 220.00 1607.94) p4 (list 214.00 1607.94))
 (command "PLINE" p1 p2 p3 p4 "c")
 (command "HATCH" "ZIGZAG" 5.00 0.00 "L" "")
 (command "COLOR" "BYLAYER")
 (command "LAYER" "S" "CGBLITHCD" "")
 (setq p1 (list 220.00 1609.88) p2 (list 221.35 1609.60))
 (command "LINE" p1 p2 "")
 (setq p1 (list 221.50 1609.23) p2 (list 0.00 0.00))
 (command "TEXT" "J" "ML" p1   0.75  0.00 "224")
 (command "LAYER" "S" "CGBTHK" "")
 (setq p1 (list 226.00 1609.23) p2 (list 0.00 0.00))
 (command "TEXT" "J" "ML" p1   0.75  0.00 "3.88")
 (command "LAYER" "S" "CGBHZID" "")
 (setq p1 (list 230.50 1609.23) p2 (list 0.00 0.00))
 (command "TEXT" "J" "ML" p1   0.75  0.00 "")
 (setq p1 (list 232.75 1609.23) p2 (list 0.00 0.00))
 (command "TEXT" "J" "ML" p1   0.75  0.00 "7451")
 (command "LAYER" "S" "CGBLITHTXT" "")
 (setq p1 (list 236.50 1609.23) p2 (list 0.00 0.00))
 (command "TEXT" "J" "ML" p1   0.75  0.00 "DRK GRY SH W/LS NODS")
 (command "LAYER" "S" "CGBCMNT" "")
 (setq p1 (list 256.75 1609.23) p2 (list 0.00 0.00))
 (command "TEXT" "J" "ML" p1   0.75  0.00 "DRK")
 (command "LAYER" "S" "CGBMAIN" "")
 (setq p1 (list 214.00 1607.94) p2 (list 220.00 1607.94) p3 (list 220.00 1604.20) p4 (list 214.00 1604.20))
 (command "PLINE" p1 p2 p3 p4 "c")
 (command "HATCH" "ZIGZAG" 5.00 0.00 "L" "")
 (command "COLOR" "BYLAYER")
 (command "LAYER" "S" "CGBLITHCD" "")
 (setq p1 (list 220.00 1606.07) p2 (list 221.35 1606.07))
 (command "LINE" p1 p2 "")
 (setq p1 (list 221.50 1605.70) p2 (list 0.00 0.00))
 (command "TEXT" "J" "ML" p1   0.75  0.00 "274")
 (command "LAYER" "S" "CGBTHK" "")
 (setq p1 (list 226.00 1605.70) p2 (list 0.00 0.00))
 (command "TEXT" "J" "ML" p1   0.75  0.00 "3.74")
 (command "LAYER" "S" "CGBHZID" "")
 (setq p1 (list 230.50 1605.70) p2 (list 0.00 0.00))
 (command "TEXT" "J" "ML" p1   0.75  0.00 "")
 (setq p1 (list 232.75 1605.70) p2 (list 0.00 0.00))
 (command "TEXT" "J" "ML" p1   0.75  0.00 "7451")
 (command "LAYER" "S" "CGBLITHTXT" "")
 (setq p1 (list 236.50 1605.70) p2 (list 0.00 0.00))
 (command "TEXT" "J" "ML" p1   0.75  0.00 "GRY/GRN SH W/LS NODS")
 (command "LAYER" "S" "CGBCMNT" "")
 (setq p1 (list 256.75 1605.70) p2 (list 0.00 0.00))
 (command "TEXT" "J" "ML" p1   0.75  0.00 "")
 (command "LAYER" "S" "CGBMAIN" "")
 (setq p1 (list 214.00 1604.20) p2 (list 220.00 1604.20) p3 (list 220.00 1601.94) p4 (list 214.00 1601.94))
 (command "PLINE" p1 p2 p3 p4 "c")
 (command "HATCH" "ZIGZAG" 5.00 0.00 "L" "")
 (command "COLOR" "BYLAYER")
 (command "LAYER" "S" "CGBLITHCD" "")
 (setq p1 (list 220.00 1603.07) p2 (list 221.35 1603.07))
 (command "LINE" p1 p2 "")
 (setq p1 (list 221.50 1602.70) p2 (list 0.00 0.00))
 (command "TEXT" "J" "ML" p1   0.75  0.00 "224")
 (command "LAYER" "S" "CGBTHK" "")
 (setq p1 (list 226.00 1602.70) p2 (list 0.00 0.00))
 (command "TEXT" "J" "ML" p1   0.75  0.00 "2.26")
 (command "LAYER" "S" "CGBHZID" "")
 (setq p1 (list 230.50 1602.70) p2 (list 0.00 0.00))
 (command "TEXT" "J" "ML" p1   0.75  0.00 "")
 (setq p1 (list 232.75 1602.70) p2 (list 0.00 0.00))
 (command "TEXT" "J" "ML" p1   0.75  0.00 "7451")
 (command "LAYER" "S" "CGBLITHTXT" "")
 (setq p1 (list 236.50 1602.70) p2 (list 0.00 0.00))
 (command "TEXT" "J" "ML" p1   0.75  0.00 "DRK GRY SH W/LS NODS")
 (command "LAYER" "S" "CGBCMNT" "")
 (setq p1 (list 256.75 1602.70) p2 (list 0.00 0.00))
 (command "TEXT" "J" "ML" p1   0.75  0.00 "")
 (command "LAYER" "S" "CGBMAIN" "")
 (setq p1 (list 214.00 1601.94) p2 (list 220.00 1601.94) p3 (list 220.00 1599.99) p4 (list 214.00 1599.99))
 (command "PLINE" p1 p2 p3 p4 "c")
 (command "HATCH" "ZIGZAG" 5.00 0.00 "L" "")
 (command "COLOR" "BYLAYER")
 (command "LAYER" "S" "CGBLITHCD" "")
 (setq p1 (list 220.00 1600.97) p2 (list 221.35 1600.97))
 (command "LINE" p1 p2 "")
 (setq p1 (list 221.50 1600.59) p2 (list 0.00 0.00))
 (command "TEXT" "J" "ML" p1   0.75  0.00 "224")
 (command "LAYER" "S" "CGBTHK" "")
 (setq p1 (list 226.00 1600.59) p2 (list 0.00 0.00))
 (command "TEXT" "J" "ML" p1   0.75  0.00 "1.95")
 (command "LAYER" "S" "CGBHZID" "")
 (setq p1 (list 230.50 1600.59) p2 (list 0.00 0.00))
 (command "TEXT" "J" "ML" p1   0.75  0.00 "")
 (setq p1 (list 232.75 1600.59) p2 (list 0.00 0.00))
 (command "TEXT" "J" "ML" p1   0.75  0.00 "7451")
 (command "LAYER" "S" "CGBLITHTXT" "")
 (setq p1 (list 236.50 1600.59) p2 (list 0.00 0.00))
 (command "TEXT" "J" "ML" p1   0.75  0.00 "DRK GRY SH W/LS NODS")
 (command "LAYER" "S" "CGBCMNT" "")
 (setq p1 (list 256.75 1600.59) p2 (list 0.00 0.00))
 (command "TEXT" "J" "ML" p1   0.75  0.00 "FEW CALC VEIN")
 (command "LAYER" "S" "CGBMAIN" "")
 (setq p1 (list 214.00 1599.99) p2 (list 220.00 1599.99) p3 (list 220.00 1597.04) p4 (list 214.00 1597.04))
 (command "PLINE" p1 p2 p3 p4 "c")
 (command "HATCH" "ZIGZAG" 10.00 45.00 "L" "")
 (command "COLOR" "BYLAYER")
 (command "LAYER" "S" "CGBLITHCD" "")
 (setq p1 (list 220.00 1598.52) p2 (list 221.35 1598.52))
 (command "LINE" p1 p2 "")
 (setq p1 (list 221.50 1598.14) p2 (list 0.00 0.00))
 (command "TEXT" "J" "ML" p1   0.75  0.00 "091")
 (command "LAYER" "S" "CGBTHK" "")
 (setq p1 (list 226.00 1598.14) p2 (list 0.00 0.00))
 (command "TEXT" "J" "ML" p1   0.75  0.00 "2.95")
 (command "LAYER" "S" "CGBHZID" "")
 (setq p1 (list 230.50 1598.14) p2 (list 0.00 0.00))
 (command "TEXT" "J" "ML" p1   0.75  0.00 "")
 (setq p1 (list 232.75 1598.14) p2 (list 0.00 0.00))
 (command "TEXT" "J" "ML" p1   0.75  0.00 "7451")
 (command "LAYER" "S" "CGBLITHTXT" "")
 (setq p1 (list 236.50 1598.14) p2 (list 0.00 0.00))
 (command "TEXT" "J" "ML" p1   0.75  0.00 "BRECCIATED FLINT CLAY")
 (command "LAYER" "S" "CGBCMNT" "")
 (setq p1 (list 256.75 1598.14) p2 (list 0.00 0.00))
 (command "TEXT" "J" "ML" p1   0.75  0.00 "")
 (command "LAYER" "S" "CGBMAIN" "")
 (setq p1 (list 214.00 1597.04) p2 (list 220.00 1597.04) p3 (list 220.00 1595.64) p4 (list 214.00 1595.64))
 (command "PLINE" p1 p2 p3 p4 "c")
 (command "HATCH" "ZIGZAG" 5.00 0.00 "L" "")
 (command "COLOR" "BYLAYER")
 (command "LAYER" "S" "CGBLITHCD" "")
 (setq p1 (list 220.00 1596.34) p2 (list 221.35 1596.34))
 (command "LINE" p1 p2 "")
 (setq p1 (list 221.50 1595.97) p2 (list 0.00 0.00))
 (command "TEXT" "J" "ML" p1   0.75  0.00 "224")
 (command "LAYER" "S" "CGBTHK" "")
 (setq p1 (list 226.00 1595.97) p2 (list 0.00 0.00))
 (command "TEXT" "J" "ML" p1   0.75  0.00 "1.40")
 (command "LAYER" "S" "CGBHZID" "")
 (setq p1 (list 230.50 1595.97) p2 (list 0.00 0.00))
 (command "TEXT" "J" "ML" p1   0.75  0.00 "")
 (setq p1 (list 232.75 1595.97) p2 (list 0.00 0.00))
 (command "TEXT" "J" "ML" p1   0.75  0.00 "7451")
 (command "LAYER" "S" "CGBLITHTXT" "")
 (setq p1 (list 236.50 1595.97) p2 (list 0.00 0.00))
 (command "TEXT" "J" "ML" p1   0.75  0.00 "DRK GRY SH W/LS NODS")
 (command "LAYER" "S" "CGBCMNT" "")
 (setq p1 (list 256.75 1595.97) p2 (list 0.00 0.00))
 (command "TEXT" "J" "ML" p1   0.75  0.00 "CALC VEINS")
 (command "LAYER" "S" "CGBMAIN" "")
 (setq p1 (list 214.00 1595.64) p2 (list 220.00 1595.64) p3 (list 220.00 1591.64) p4 (list 214.00 1591.64))
 (command "PLINE" p1 p2 p3 p4 "c")
 (command "HATCH" "ZIGZAG" 4.00 0.00 "L" "")
 (command "COLOR" "BYLAYER")
 (command "LAYER" "S" "CGBLITHCD" "")
 (setq p1 (list 220.00 1593.64) p2 (list 221.35 1593.64))
 (command "LINE" p1 p2 "")
 (setq p1 (list 221.50 1593.27) p2 (list 0.00 0.00))
 (command "TEXT" "J" "ML" p1   0.75  0.00 "444")
 (command "LAYER" "S" "CGBTHK" "")
 (setq p1 (list 226.00 1593.27) p2 (list 0.00 0.00))
 (command "TEXT" "J" "ML" p1   0.75  0.00 "4.00")
 (command "LAYER" "S" "CGBHZID" "")
 (setq p1 (list 230.50 1593.27) p2 (list 0.00 0.00))
 (command "TEXT" "J" "ML" p1   0.75  0.00 "")
 (setq p1 (list 232.75 1593.27) p2 (list 0.00 0.00))
 (command "TEXT" "J" "ML" p1   0.75  0.00 "7451")
 (command "LAYER" "S" "CGBLITHTXT" "")
 (setq p1 (list 236.50 1593.27) p2 (list 0.00 0.00))
 (command "TEXT" "J" "ML" p1   0.75  0.00 "GRN SDY SH W/LS NODS")
 (command "LAYER" "S" "CGBCMNT" "")
 (setq p1 (list 256.75 1593.27) p2 (list 0.00 0.00))
 (command "TEXT" "J" "ML" p1   0.75  0.00 "")
 (command "LAYER" "S" "CGBMAIN" "")
 (setq p1 (list 214.00 1591.64) p2 (list 220.00 1591.64) p3 (list 220.00 1588.92) p4 (list 214.00 1588.92))
 (command "PLINE" p1 p2 p3 p4 "c")
 (command "HATCH" "ZIGZAG" 0.50 0.00 "L" "")
 (command "COLOR" "BYLAYER")
 (command "LAYER" "S" "CGBLITHCD" "")
 (setq p1 (list 220.00 1590.28) p2 (list 221.35 1590.28))
 (command "LINE" p1 p2 "")
 (setq p1 (list 221.50 1589.91) p2 (list 0.00 0.00))
 (command "TEXT" "J" "ML" p1   0.75  0.00 "804")
 (command "LAYER" "S" "CGBTHK" "")
 (setq p1 (list 226.00 1589.91) p2 (list 0.00 0.00))
 (command "TEXT" "J" "ML" p1   0.75  0.00 "2.72")
 (command "LAYER" "S" "CGBHZID" "")
 (setq p1 (list 230.50 1589.91) p2 (list 0.00 0.00))
 (command "TEXT" "J" "ML" p1   0.75  0.00 "")
 (setq p1 (list 232.75 1589.91) p2 (list 0.00 0.00))
 (command "TEXT" "J" "ML" p1   0.75  0.00 "7451")
 (command "LAYER" "S" "CGBLITHTXT" "")
 (setq p1 (list 236.50 1589.91) p2 (list 0.00 0.00))
 (command "TEXT" "J" "ML" p1   0.75  0.00 "MASS FN GRND SHLY LS")
 (command "LAYER" "S" "CGBCMNT" "")
 (setq p1 (list 256.75 1589.91) p2 (list 0.00 0.00))
 (command "TEXT" "J" "ML" p1   0.75  0.00 "")
 (command "LAYER" "S" "CGBMAIN" "")
 (setq p1 (list 214.00 1588.92) p2 (list 220.00 1588.92) p3 (list 220.00 1586.94) p4 (list 214.00 1586.94))
 (command "PLINE" p1 p2 p3 p4 "c")
 (command "HATCH" "ZIGZAG" 10.00 45.00 "L" "")
 (command "COLOR" "BYLAYER")
 (command "LAYER" "S" "CGBLITHCD" "")
 (setq p1 (list 220.00 1587.93) p2 (list 221.35 1587.93))
 (command "LINE" p1 p2 "")
 (setq p1 (list 221.50 1587.56) p2 (list 0.00 0.00))
 (command "TEXT" "J" "ML" p1   0.75  0.00 "091")
 (command "LAYER" "S" "CGBTHK" "")
 (setq p1 (list 226.00 1587.56) p2 (list 0.00 0.00))
 (command "TEXT" "J" "ML" p1   0.75  0.00 "1.98")
 (command "LAYER" "S" "CGBHZID" "")
 (setq p1 (list 230.50 1587.56) p2 (list 0.00 0.00))
 (command "TEXT" "J" "ML" p1   0.75  0.00 "")
 (setq p1 (list 232.75 1587.56) p2 (list 0.00 0.00))
 (command "TEXT" "J" "ML" p1   0.75  0.00 "7451")
 (command "LAYER" "S" "CGBLITHTXT" "")
 (setq p1 (list 236.50 1587.56) p2 (list 0.00 0.00))
 (command "TEXT" "J" "ML" p1   0.75  0.00 "BRECCIATED FLINT CLAY")
 (command "LAYER" "S" "CGBCMNT" "")
 (setq p1 (list 256.75 1587.56) p2 (list 0.00 0.00))
 (command "TEXT" "J" "ML" p1   0.75  0.00 "")
 (command "LAYER" "S" "CGBMAIN" "")
 (setq p1 (list 214.00 1586.94) p2 (list 220.00 1586.94) p3 (list 220.00 1584.84) p4 (list 214.00 1584.84))
 (command "PLINE" p1 p2 p3 p4 "c")
 (command "HATCH" "ZIGZAG" 10.00 45.00 "L" "")
 (command "COLOR" "BYLAYER")
 (command "LAYER" "S" "CGBLITHCD" "")
 (setq p1 (list 220.00 1585.89) p2 (list 221.35 1585.89))
 (command "LINE" p1 p2 "")
 (setq p1 (list 221.50 1585.52) p2 (list 0.00 0.00))
 (command "TEXT" "J" "ML" p1   0.75  0.00 "091")
 (command "LAYER" "S" "CGBTHK" "")
 (setq p1 (list 226.00 1585.52) p2 (list 0.00 0.00))
 (command "TEXT" "J" "ML" p1   0.75  0.00 "2.10")
 (command "LAYER" "S" "CGBHZID" "")
 (setq p1 (list 230.50 1585.52) p2 (list 0.00 0.00))
 (command "TEXT" "J" "ML" p1   0.75  0.00 "")
 (setq p1 (list 232.75 1585.52) p2 (list 0.00 0.00))
 (command "TEXT" "J" "ML" p1   0.75  0.00 "7451")
 (command "LAYER" "S" "CGBLITHTXT" "")
 (setq p1 (list 236.50 1585.52) p2 (list 0.00 0.00))
 (command "TEXT" "J" "ML" p1   0.75  0.00 "BRECCIATED FLINT CLAY")
 (command "LAYER" "S" "CGBCMNT" "")
 (setq p1 (list 256.75 1585.52) p2 (list 0.00 0.00))
 (command "TEXT" "J" "ML" p1   0.75  0.00 "")
 (command "LAYER" "S" "CGBMAIN" "")
 (setq p1 (list 214.00 1584.84) p2 (list 220.00 1584.84) p3 (list 220.00 1583.44) p4 (list 214.00 1583.44))
 (command "PLINE" p1 p2 p3 p4 "c")
 (command "HATCH" "ZIGZAG" 2.50 90.00 "L" "")
 (command "COLOR" "BYLAYER")
 (command "LAYER" "S" "CGBLITHCD" "")
 (setq p1 (list 220.00 1584.14) p2 (list 221.35 1584.14))
 (command "LINE" p1 p2 "")
 (setq p1 (list 221.50 1583.77) p2 (list 0.00 0.00))
 (command "TEXT" "J" "ML" p1   0.75  0.00 "324")
 (command "LAYER" "S" "CGBTHK" "")
 (setq p1 (list 226.00 1583.77) p2 (list 0.00 0.00))
 (command "TEXT" "J" "ML" p1   0.75  0.00 "1.40")
 (command "LAYER" "S" "CGBHZID" "")
 (setq p1 (list 230.50 1583.77) p2 (list 0.00 0.00))
 (command "TEXT" "J" "ML" p1   0.75  0.00 "")
 (setq p1 (list 232.75 1583.77) p2 (list 0.00 0.00))
 (command "TEXT" "J" "ML" p1   0.75  0.00 "7451")
 (command "LAYER" "S" "CGBLITHTXT" "")
 (setq p1 (list 236.50 1583.77) p2 (list 0.00 0.00))
 (command "TEXT" "J" "ML" p1   0.75  0.00 "DRK GRY MASS SDY SH")
 (command "LAYER" "S" "CGBCMNT" "")
 (setq p1 (list 256.75 1583.77) p2 (list 0.00 0.00))
 (command "TEXT" "J" "ML" p1   0.75  0.00 "SLX")
 (command "LAYER" "S" "CGBMAIN" "")
 (setq p1 (list 214.00 1583.44) p2 (list 220.00 1583.44) p3 (list 220.00 1579.13) p4 (list 214.00 1579.13))
 (command "PLINE" p1 p2 p3 p4 "c")
 (command "HATCH" "ZIGZAG" 4.00 0.00 "L" "")
 (command "COLOR" "BYLAYER")
 (command "LAYER" "S" "CGBLITHCD" "")
 (setq p1 (list 220.00 1581.29) p2 (list 221.35 1581.29))
 (command "LINE" p1 p2 "")
 (setq p1 (list 221.50 1580.91) p2 (list 0.00 0.00))
 (command "TEXT" "J" "ML" p1   0.75  0.00 "457")
 (command "LAYER" "S" "CGBTHK" "")
 (setq p1 (list 226.00 1580.91) p2 (list 0.00 0.00))
 (command "TEXT" "J" "ML" p1   0.75  0.00 "4.31")
 (command "LAYER" "S" "CGBHZID" "")
 (setq p1 (list 230.50 1580.91) p2 (list 0.00 0.00))
 (command "TEXT" "J" "ML" p1   0.75  0.00 "")
 (setq p1 (list 232.75 1580.91) p2 (list 0.00 0.00))
 (command "TEXT" "J" "ML" p1   0.75  0.00 "7451")
 (command "LAYER" "S" "CGBLITHTXT" "")
 (setq p1 (list 236.50 1580.91) p2 (list 0.00 0.00))
 (command "TEXT" "J" "ML" p1   0.75  0.00 "RED+GRN SDY CLYSTN W/LS N")
 (command "LAYER" "S" "CGBCMNT" "")
 (setq p1 (list 256.75 1580.91) p2 (list 0.00 0.00))
 (command "TEXT" "J" "ML" p1   0.75  0.00 "BRKN,SLX")
 (command "LAYER" "S" "CGBMAIN" "")
 (setq p1 (list 214.00 1579.13) p2 (list 220.00 1579.13) p3 (list 220.00 1577.99) p4 (list 214.00 1577.99))
 (command "PLINE" p1 p2 p3 p4 "c")
 (command "HATCH" "ZIGZAG" 0.50 0.00 "L" "")
 (command "COLOR" "BYLAYER")
 (command "LAYER" "S" "CGBLITHCD" "")
 (setq p1 (list 220.00 1578.56) p2 (list 221.35 1578.56))
 (command "LINE" p1 p2 "")
 (setq p1 (list 221.50 1578.19) p2 (list 0.00 0.00))
 (command "TEXT" "J" "ML" p1   0.75  0.00 "804")
 (command "LAYER" "S" "CGBTHK" "")
 (setq p1 (list 226.00 1578.19) p2 (list 0.00 0.00))
 (command "TEXT" "J" "ML" p1   0.75  0.00 "1.14")
 (command "LAYER" "S" "CGBHZID" "")
 (setq p1 (list 230.50 1578.19) p2 (list 0.00 0.00))
 (command "TEXT" "J" "ML" p1   0.75  0.00 "")
 (setq p1 (list 232.75 1578.19) p2 (list 0.00 0.00))
 (command "TEXT" "J" "ML" p1   0.75  0.00 "7451")
 (command "LAYER" "S" "CGBLITHTXT" "")
 (setq p1 (list 236.50 1578.19) p2 (list 0.00 0.00))
 (command "TEXT" "J" "ML" p1   0.75  0.00 "MASS FN GRND SHLY LS")
 (command "LAYER" "S" "CGBCMNT" "")
 (setq p1 (list 256.75 1578.19) p2 (list 0.00 0.00))
 (command "TEXT" "J" "ML" p1   0.75  0.00 "")
 (command "LAYER" "S" "CGBMAIN" "")
 (setq p1 (list 214.00 1577.99) p2 (list 220.00 1577.99) p3 (list 220.00 1574.84) p4 (list 214.00 1574.84))
 (command "PLINE" p1 p2 p3 p4 "c")
 (command "HATCH" "ZIGZAG" 4.00 0.00 "L" "")
 (command "COLOR" "BYLAYER")
 (command "LAYER" "S" "CGBLITHCD" "")
 (setq p1 (list 220.00 1576.42) p2 (list 221.35 1576.42))
 (command "LINE" p1 p2 "")
 (setq p1 (list 221.50 1576.04) p2 (list 0.00 0.00))
 (command "TEXT" "J" "ML" p1   0.75  0.00 "354")
 (command "LAYER" "S" "CGBTHK" "")
 (setq p1 (list 226.00 1576.04) p2 (list 0.00 0.00))
 (command "TEXT" "J" "ML" p1   0.75  0.00 "3.15")
 (command "LAYER" "S" "CGBHZID" "")
 (setq p1 (list 230.50 1576.04) p2 (list 0.00 0.00))
 (command "TEXT" "J" "ML" p1   0.75  0.00 "")
 (setq p1 (list 232.75 1576.04) p2 (list 0.00 0.00))
 (command "TEXT" "J" "ML" p1   0.75  0.00 "7451")
 (command "LAYER" "S" "CGBLITHTXT" "")
 (setq p1 (list 236.50 1576.04) p2 (list 0.00 0.00))
 (command "TEXT" "J" "ML" p1   0.75  0.00 "RED+GRN SDY SH")
 (command "LAYER" "S" "CGBCMNT" "")
 (setq p1 (list 256.75 1576.04) p2 (list 0.00 0.00))
 (command "TEXT" "J" "ML" p1   0.75  0.00 "CALC")
 (command "LAYER" "S" "CGBMAIN" "")
 (setq p1 (list 214.00 1574.84) p2 (list 220.00 1574.84) p3 (list 220.00 1573.49) p4 (list 214.00 1573.49))
 (command "PLINE" p1 p2 p3 p4 "c")
 (command "HATCH" "ZIGZAG" 5.00 0.00 "L" "")
 (command "COLOR" "BYLAYER")
 (command "LAYER" "S" "CGBLITHCD" "")
 (setq p1 (list 220.00 1574.17) p2 (list 221.35 1574.17))
 (command "LINE" p1 p2 "")
 (setq p1 (list 221.50 1573.79) p2 (list 0.00 0.00))
 (command "TEXT" "J" "ML" p1   0.75  0.00 "333")
 (command "LAYER" "S" "CGBTHK" "")
 (setq p1 (list 226.00 1573.79) p2 (list 0.00 0.00))
 (command "TEXT" "J" "ML" p1   0.75  0.00 "1.35")
 (command "LAYER" "S" "CGBHZID" "")
 (setq p1 (list 230.50 1573.79) p2 (list 0.00 0.00))
 (command "TEXT" "J" "ML" p1   0.75  0.00 "")
 (setq p1 (list 232.75 1573.79) p2 (list 0.00 0.00))
 (command "TEXT" "J" "ML" p1   0.75  0.00 "7451")
 (command "LAYER" "S" "CGBLITHTXT" "")
 (setq p1 (list 236.50 1573.79) p2 (list 0.00 0.00))
 (command "TEXT" "J" "ML" p1   0.75  0.00 "LT GRY GRN SH W/SS STKS")
 (command "LAYER" "S" "CGBCMNT" "")
 (setq p1 (list 256.75 1573.79) p2 (list 0.00 0.00))
 (command "TEXT" "J" "ML" p1   0.75  0.00 "")
 (command "LAYER" "S" "CGBMAIN" "")
 (setq p1 (list 214.00 1573.49) p2 (list 220.00 1573.49) p3 (list 220.00 1572.97) p4 (list 214.00 1572.97))
 (command "PLINE" p1 p2 p3 p4 "c")
 (command "HATCH" "ZIGZAG" 4.00 0.00 "L" "")
 (command "COLOR" "BYLAYER")
 (command "LAYER" "S" "CGBLITHCD" "")
 (setq p1 (list 220.00 1573.23) p2 (list 221.35 1571.98))
 (command "LINE" p1 p2 "")
 (setq p1 (list 221.50 1571.61) p2 (list 0.00 0.00))
 (command "TEXT" "J" "ML" p1   0.75  0.00 "124")
 (command "LAYER" "S" "CGBTHK" "")
 (setq p1 (list 226.00 1571.61) p2 (list 0.00 0.00))
 (command "TEXT" "J" "ML" p1   0.75  0.00 "0.52")
 (command "LAYER" "S" "CGBHZID" "")
 (setq p1 (list 230.50 1571.61) p2 (list 0.00 0.00))
 (command "TEXT" "J" "ML" p1   0.75  0.00 "")
 (setq p1 (list 232.75 1571.61) p2 (list 0.00 0.00))
 (command "TEXT" "J" "ML" p1   0.75  0.00 "7451")
 (command "LAYER" "S" "CGBLITHTXT" "")
 (setq p1 (list 236.50 1571.61) p2 (list 0.00 0.00))
 (command "TEXT" "J" "ML" p1   0.75  0.00 "DRK GRY SH")
 (command "LAYER" "S" "CGBCMNT" "")
 (setq p1 (list 256.75 1571.61) p2 (list 0.00 0.00))
 (command "TEXT" "J" "ML" p1   0.75  0.00 "")
 (command "LAYER" "S" "CGBMAIN" "")
 (setq p1 (list 214.00 1572.97) p2 (list 220.00 1572.97) p3 (list 220.00 1571.94) p4 (list 214.00 1571.94))
 (command "PLINE" p1 p2 p3 p4 "c")
 (command "HATCH" "ZIGZAG" 5.00 0.00 "L" "")
 (command "COLOR" "BYLAYER")
 (command "LAYER" "S" "CGBLITHCD" "")
 (setq p1 (list 220.00 1572.46) p2 (list 221.35 1570.73))
 (command "LINE" p1 p2 "")
 (setq p1 (list 221.50 1570.36) p2 (list 0.00 0.00))
 (command "TEXT" "J" "ML" p1   0.75  0.00 "333")
 (command "LAYER" "S" "CGBTHK" "")
 (setq p1 (list 226.00 1570.36) p2 (list 0.00 0.00))
 (command "TEXT" "J" "ML" p1   0.75  0.00 "1.03")
 (command "LAYER" "S" "CGBHZID" "")
 (setq p1 (list 230.50 1570.36) p2 (list 0.00 0.00))
 (command "TEXT" "J" "ML" p1   0.75  0.00 "")
 (setq p1 (list 232.75 1570.36) p2 (list 0.00 0.00))
 (command "TEXT" "J" "ML" p1   0.75  0.00 "7451")
 (command "LAYER" "S" "CGBLITHTXT" "")
 (setq p1 (list 236.50 1570.36) p2 (list 0.00 0.00))
 (command "TEXT" "J" "ML" p1   0.75  0.00 "LT GRY GRN SH W/SS STKS")
 (command "LAYER" "S" "CGBCMNT" "")
 (setq p1 (list 256.75 1570.36) p2 (list 0.00 0.00))
 (command "TEXT" "J" "ML" p1   0.75  0.00 "")
 (command "LAYER" "S" "CGBMAIN" "")
 (setq p1 (list 214.00 1571.94) p2 (list 220.00 1571.94) p3 (list 220.00 1569.12) p4 (list 214.00 1569.12))
 (command "PLINE" p1 p2 p3 p4 "c")
 (command "HATCH" "ZIGZAG" 5.00 0.00 "L" "")
 (command "COLOR" "BYLAYER")
 (command "LAYER" "S" "CGBLITHCD" "")
 (setq p1 (list 220.00 1570.53) p2 (list 221.35 1569.48))
 (command "LINE" p1 p2 "")
 (setq p1 (list 221.50 1569.11) p2 (list 0.00 0.00))
 (command "TEXT" "J" "ML" p1   0.75  0.00 "322")
 (command "LAYER" "S" "CGBTHK" "")
 (setq p1 (list 226.00 1569.11) p2 (list 0.00 0.00))
 (command "TEXT" "J" "ML" p1   0.75  0.00 "2.82")
 (command "LAYER" "S" "CGBHZID" "")
 (setq p1 (list 230.50 1569.11) p2 (list 0.00 0.00))
 (command "TEXT" "J" "ML" p1   0.75  0.00 "")
 (setq p1 (list 232.75 1569.11) p2 (list 0.00 0.00))
 (command "TEXT" "J" "ML" p1   0.75  0.00 "7451")
 (command "LAYER" "S" "CGBLITHTXT" "")
 (setq p1 (list 236.50 1569.11) p2 (list 0.00 0.00))
 (command "TEXT" "J" "ML" p1   0.75  0.00 "DRK GRY SH+INTERBED SS")
 (command "LAYER" "S" "CGBCMNT" "")
 (setq p1 (list 256.75 1569.11) p2 (list 0.00 0.00))
 (command "TEXT" "J" "ML" p1   0.75  0.00 "")
 (command "LAYER" "S" "CGBMAIN" "")
 (setq p1 (list 214.00 1569.12) p2 (list 220.00 1569.12) p3 (list 220.00 1565.18) p4 (list 214.00 1565.18))
 (command "PLINE" p1 p2 p3 p4 "c")
 (command "HATCH" "ZIGZAG" 2.50 90.00 "L" "")
 (command "COLOR" "BYLAYER")
 (command "LAYER" "S" "CGBLITHCD" "")
 (setq p1 (list 220.00 1567.15) p2 (list 221.35 1567.15))
 (command "LINE" p1 p2 "")
 (setq p1 (list 221.50 1566.78) p2 (list 0.00 0.00))
 (command "TEXT" "J" "ML" p1   0.75  0.00 "334")
 (command "LAYER" "S" "CGBTHK" "")
 (setq p1 (list 226.00 1566.78) p2 (list 0.00 0.00))
 (command "TEXT" "J" "ML" p1   0.75  0.00 "3.94")
 (command "LAYER" "S" "CGBHZID" "")
 (setq p1 (list 230.50 1566.78) p2 (list 0.00 0.00))
 (command "TEXT" "J" "ML" p1   0.75  0.00 "")
 (setq p1 (list 232.75 1566.78) p2 (list 0.00 0.00))
 (command "TEXT" "J" "ML" p1   0.75  0.00 "7451")
 (command "LAYER" "S" "CGBLITHTXT" "")
 (setq p1 (list 236.50 1566.78) p2 (list 0.00 0.00))
 (command "TEXT" "J" "ML" p1   0.75  0.00 "LT GRY GRN MASS SDY SH")
 (command "LAYER" "S" "CGBCMNT" "")
 (setq p1 (list 256.75 1566.78) p2 (list 0.00 0.00))
 (command "TEXT" "J" "ML" p1   0.75  0.00 "SLC")
 (command "LAYER" "S" "CGBMAIN" "")
 (setq p1 (list 214.00 1565.18) p2 (list 220.00 1565.18) p3 (list 220.00 1564.86) p4 (list 214.00 1564.86))
 (command "PLINE" p1 p2 p3 p4 "c")
 (command "HATCH" "ZIGZAG" 4.00 0.00 "L" "")
 (command "COLOR" "BYLAYER")
 (command "LAYER" "S" "CGBLITHCD" "")
 (setq p1 (list 220.00 1565.02) p2 (list 221.35 1565.02))
 (command "LINE" p1 p2 "")
 (setq p1 (list 221.50 1564.65) p2 (list 0.00 0.00))
 (command "TEXT" "J" "ML" p1   0.75  0.00 "563")
 (command "LAYER" "S" "CGBTHK" "")
 (setq p1 (list 226.00 1564.65) p2 (list 0.00 0.00))
 (command "TEXT" "J" "ML" p1   0.75  0.00 "0.32")
 (command "LAYER" "S" "CGBHZID" "")
 (setq p1 (list 230.50 1564.65) p2 (list 0.00 0.00))
 (command "TEXT" "J" "ML" p1   0.75  0.00 "")
 (setq p1 (list 232.75 1564.65) p2 (list 0.00 0.00))
 (command "TEXT" "J" "ML" p1   0.75  0.00 "7451")
 (command "LAYER" "S" "CGBLITHTXT" "")
 (setq p1 (list 236.50 1564.65) p2 (list 0.00 0.00))
 (command "TEXT" "J" "ML" p1   0.75  0.00 "HARD SS W/SH STKS")
 (command "LAYER" "S" "CGBCMNT" "")
 (setq p1 (list 256.75 1564.65) p2 (list 0.00 0.00))
 (command "TEXT" "J" "ML" p1   0.75  0.00 "")
 (command "LAYER" "S" "CGBMAIN" "")
 (setq p1 (list 214.00 1564.86) p2 (list 220.00 1564.86) p3 (list 220.00 1562.61) p4 (list 214.00 1562.61))
 (command "PLINE" p1 p2 p3 p4 "c")
 (command "HATCH" "ZIGZAG" 4.00 0.00 "L" "")
 (command "COLOR" "BYLAYER")
 (command "LAYER" "S" "CGBLITHCD" "")
 (setq p1 (list 220.00 1563.74) p2 (list 221.35 1563.74))
 (command "LINE" p1 p2 "")
 (setq p1 (list 221.50 1563.36) p2 (list 0.00 0.00))
 (command "TEXT" "J" "ML" p1   0.75  0.00 "434")
 (command "LAYER" "S" "CGBTHK" "")
 (setq p1 (list 226.00 1563.36) p2 (list 0.00 0.00))
 (command "TEXT" "J" "ML" p1   0.75  0.00 "2.25")
 (command "LAYER" "S" "CGBHZID" "")
 (setq p1 (list 230.50 1563.36) p2 (list 0.00 0.00))
 (command "TEXT" "J" "ML" p1   0.75  0.00 "")
 (setq p1 (list 232.75 1563.36) p2 (list 0.00 0.00))
 (command "TEXT" "J" "ML" p1   0.75  0.00 "7451")
 (command "LAYER" "S" "CGBLITHTXT" "")
 (setq p1 (list 236.50 1563.36) p2 (list 0.00 0.00))
 (command "TEXT" "J" "ML" p1   0.75  0.00 "LT GRY GRN SDY SH W/LS NO")
 (command "LAYER" "S" "CGBCMNT" "")
 (setq p1 (list 256.75 1563.36) p2 (list 0.00 0.00))
 (command "TEXT" "J" "ML" p1   0.75  0.00 "")
 (command "LAYER" "S" "CGBMAIN" "")
 (setq p1 (list 214.00 1562.61) p2 (list 220.00 1562.61) p3 (list 220.00 1561.54) p4 (list 214.00 1561.54))
 (command "PLINE" p1 p2 p3 p4 "c")
 (command "HATCH" "ZIGZAG" 4.00 0.00 "L" "")
 (command "COLOR" "BYLAYER")
 (command "LAYER" "S" "CGBLITHCD" "")
 (setq p1 (list 220.00 1562.08) p2 (list 221.35 1562.08))
 (command "LINE" p1 p2 "")
 (setq p1 (list 221.50 1561.70) p2 (list 0.00 0.00))
 (command "TEXT" "J" "ML" p1   0.75  0.00 "563")
 (command "LAYER" "S" "CGBTHK" "")
 (setq p1 (list 226.00 1561.70) p2 (list 0.00 0.00))
 (command "TEXT" "J" "ML" p1   0.75  0.00 "1.07")
 (command "LAYER" "S" "CGBHZID" "")
 (setq p1 (list 230.50 1561.70) p2 (list 0.00 0.00))
 (command "TEXT" "J" "ML" p1   0.75  0.00 "")
 (setq p1 (list 232.75 1561.70) p2 (list 0.00 0.00))
 (command "TEXT" "J" "ML" p1   0.75  0.00 "7451")
 (command "LAYER" "S" "CGBLITHTXT" "")
 (setq p1 (list 236.50 1561.70) p2 (list 0.00 0.00))
 (command "TEXT" "J" "ML" p1   0.75  0.00 "HARD SS W/SH STKS")
 (command "LAYER" "S" "CGBCMNT" "")
 (setq p1 (list 256.75 1561.70) p2 (list 0.00 0.00))
 (command "TEXT" "J" "ML" p1   0.75  0.00 "")
 (command "LAYER" "S" "CGBMAIN" "")
 (setq p1 (list 214.00 1561.54) p2 (list 220.00 1561.54) p3 (list 220.00 1559.47) p4 (list 214.00 1559.47))
 (command "PLINE" p1 p2 p3 p4 "c")
 (command "HATCH" "ZIGZAG" 4.00 0.00 "L" "")
 (command "COLOR" "BYLAYER")
 (command "LAYER" "S" "CGBLITHCD" "")
 (setq p1 (list 220.00 1560.51) p2 (list 221.35 1560.51))
 (command "LINE" p1 p2 "")
 (setq p1 (list 221.50 1560.13) p2 (list 0.00 0.00))
 (command "TEXT" "J" "ML" p1   0.75  0.00 "124")
 (command "LAYER" "S" "CGBTHK" "")
 (setq p1 (list 226.00 1560.13) p2 (list 0.00 0.00))
 (command "TEXT" "J" "ML" p1   0.75  0.00 "2.07")
 (command "LAYER" "S" "CGBHZID" "")
 (setq p1 (list 230.50 1560.13) p2 (list 0.00 0.00))
 (command "TEXT" "J" "ML" p1   0.75  0.00 "")
 (setq p1 (list 232.75 1560.13) p2 (list 0.00 0.00))
 (command "TEXT" "J" "ML" p1   0.75  0.00 "7451")
 (command "LAYER" "S" "CGBLITHTXT" "")
 (setq p1 (list 236.50 1560.13) p2 (list 0.00 0.00))
 (command "TEXT" "J" "ML" p1   0.75  0.00 "DRK GRY SH")
 (command "LAYER" "S" "CGBCMNT" "")
 (setq p1 (list 256.75 1560.13) p2 (list 0.00 0.00))
 (command "TEXT" "J" "ML" p1   0.75  0.00 "SLX,BRKN")
 (command "LAYER" "S" "CGBMAIN" "")
 (setq p1 (list 214.00 1559.47) p2 (list 220.00 1559.47) p3 (list 220.00 1556.69) p4 (list 214.00 1556.69))
 (command "PLINE" p1 p2 p3 p4 "c")
 (command "HATCH" "ZIGZAG" 2.50 90.00 "L" "")
 (command "COLOR" "BYLAYER")
 (command "LAYER" "S" "CGBLITHCD" "")
 (setq p1 (list 220.00 1558.08) p2 (list 221.35 1558.08))
 (command "LINE" p1 p2 "")
 (setq p1 (list 221.50 1557.71) p2 (list 0.00 0.00))
 (command "TEXT" "J" "ML" p1   0.75  0.00 "334")
 (command "LAYER" "S" "CGBTHK" "")
 (setq p1 (list 226.00 1557.71) p2 (list 0.00 0.00))
 (command "TEXT" "J" "ML" p1   0.75  0.00 "2.78")
 (command "LAYER" "S" "CGBHZID" "")
 (setq p1 (list 230.50 1557.71) p2 (list 0.00 0.00))
 (command "TEXT" "J" "ML" p1   0.75  0.00 "")
 (setq p1 (list 232.75 1557.71) p2 (list 0.00 0.00))
 (command "TEXT" "J" "ML" p1   0.75  0.00 "7451")
 (command "LAYER" "S" "CGBLITHTXT" "")
 (setq p1 (list 236.50 1557.71) p2 (list 0.00 0.00))
 (command "TEXT" "J" "ML" p1   0.75  0.00 "LT GRY GRN MASS SDY SH")
 (command "LAYER" "S" "CGBCMNT" "")
 (setq p1 (list 256.75 1557.71) p2 (list 0.00 0.00))
 (command "TEXT" "J" "ML" p1   0.75  0.00 "GB")
 (command "LAYER" "S" "CGBMAIN" "")
 (setq p1 (list 214.00 1556.69) p2 (list 220.00 1556.69) p3 (list 220.00 1556.62) p4 (list 214.00 1556.62))
 (command "PLINE" p1 p2 p3 p4 "c")
 (command "HATCH" "ZIGZAG" 2.50 90.00 "L" "")
 (command "COLOR" "BYLAYER")
 (command "LAYER" "S" "CGBLITHCD" "")
 (setq p1 (list 220.00 1556.66) p2 (list 221.35 1556.66))
 (command "LINE" p1 p2 "")
 (setq p1 (list 221.50 1556.28) p2 (list 0.00 0.00))
 (command "TEXT" "J" "ML" p1   0.75  0.00 "334")
 (command "LAYER" "S" "CGBTHK" "")
 (setq p1 (list 226.00 1556.28) p2 (list 0.00 0.00))
 (command "TEXT" "J" "ML" p1   0.75  0.00 "0.07")
 (command "LAYER" "S" "CGBHZID" "")
 (setq p1 (list 230.50 1556.28) p2 (list 0.00 0.00))
 (command "TEXT" "J" "ML" p1   0.75  0.00 "")
 (setq p1 (list 232.75 1556.28) p2 (list 0.00 0.00))
 (command "TEXT" "J" "ML" p1   0.75  0.00 "7451")
 (command "LAYER" "S" "CGBLITHTXT" "")
 (setq p1 (list 236.50 1556.28) p2 (list 0.00 0.00))
 (command "TEXT" "J" "ML" p1   0.75  0.00 "LT GRY GRN MASS SDY SH")
 (command "LAYER" "S" "CGBCMNT" "")
 (setq p1 (list 256.75 1556.28) p2 (list 0.00 0.00))
 (command "TEXT" "J" "ML" p1   0.75  0.00 "")
 (command "LAYER" "S" "CGBMAIN" "")
 (command "LAYER" "S" "CGBLITHCD" "")
 (setq p1 (list 220.00 1556.62) p2 (list 221.35 1555.37))
 (command "LINE" p1 p2 "")
 (setq p1 (list 221.50 1555.00) p2 (list 0.00 0.00))
 (command "TEXT" "J" "ML" p1   0.75  0.00 "020")
 (command "LAYER" "S" "CGBTHK" "")
 (setq p1 (list 226.00 1555.00) p2 (list 0.00 0.00))
 (command "TEXT" "J" "ML" p1   0.75  0.00 "0.00")
 (command "LAYER" "S" "CGBHZID" "")
 (setq p1 (list 230.50 1555.00) p2 (list 0.00 0.00))
 (command "TEXT" "J" "ML" p1   0.75  0.00 "")
 (setq p1 (list 232.75 1555.00) p2 (list 0.00 0.00))
 (command "TEXT" "J" "ML" p1   0.75  0.00 "7000")
 (command "LAYER" "S" "CGBLITHTXT" "")
 (setq p1 (list 236.50 1555.00) p2 (list 0.00 0.00))
 (command "TEXT" "J" "ML" p1   0.75  0.00 "COAL")
 (command "LAYER" "S" "CGBCMNT" "")
 (setq p1 (list 256.75 1555.00) p2 (list 0.00 0.00))
 (command "TEXT" "J" "ML" p1   0.75  0.00 "MAH HRZN")
 (command "LAYER" "S" "CGBMAIN" "")
 (setq p1 (list 214.00 1556.62) p2 (list 220.00 1556.62) p3 (list 220.00 1555.39) p4 (list 214.00 1555.39))
 (command "PLINE" p1 p2 p3 p4 "c")
 (command "HATCH" "ZIGZAG" 0.25 0.00 "L" "")
 (command "COLOR" "BYLAYER")
 (command "LAYER" "S" "CGBLITHCD" "")
 (setq p1 (list 220.00 1556.01) p2 (list 221.35 1554.12))
 (command "LINE" p1 p2 "")
 (setq p1 (list 221.50 1553.75) p2 (list 0.00 0.00))
 (command "TEXT" "J" "ML" p1   0.75  0.00 "127")
 (command "LAYER" "S" "CGBTHK" "")
 (setq p1 (list 226.00 1553.75) p2 (list 0.00 0.00))
 (command "TEXT" "J" "ML" p1   0.75  0.00 "1.23")
 (command "LAYER" "S" "CGBHZID" "")
 (setq p1 (list 230.50 1553.75) p2 (list 0.00 0.00))
 (command "TEXT" "J" "ML" p1   0.75  0.00 "")
 (setq p1 (list 232.75 1553.75) p2 (list 0.00 0.00))
 (command "TEXT" "J" "ML" p1   0.75  0.00 "6951")
 (command "LAYER" "S" "CGBLITHTXT" "")
 (setq p1 (list 236.50 1553.75) p2 (list 0.00 0.00))
 (command "TEXT" "J" "ML" p1   0.75  0.00 "DRK GRY FIRECLAY")
 (command "LAYER" "S" "CGBCMNT" "")
 (setq p1 (list 256.75 1553.75) p2 (list 0.00 0.00))
 (command "TEXT" "J" "ML" p1   0.75  0.00 "SLX")
 (command "LAYER" "S" "CGBMAIN" "")
 (setq p1 (list 214.00 1555.39) p2 (list 220.00 1555.39) p3 (list 220.00 1554.45) p4 (list 214.00 1554.45))
 (command "PLINE" p1 p2 p3 p4 "c")
 (command "HATCH" "ZIGZAG" 10.00 45.00 "L" "")
 (command "COLOR" "BYLAYER")
 (command "LAYER" "S" "CGBLITHCD" "")
 (setq p1 (list 220.00 1554.92) p2 (list 221.35 1552.87))
 (command "LINE" p1 p2 "")
 (setq p1 (list 221.50 1552.50) p2 (list 0.00 0.00))
 (command "TEXT" "J" "ML" p1   0.75  0.00 "094")
 (command "LAYER" "S" "CGBTHK" "")
 (setq p1 (list 226.00 1552.50) p2 (list 0.00 0.00))
 (command "TEXT" "J" "ML" p1   0.75  0.00 "0.94")
 (command "LAYER" "S" "CGBHZID" "")
 (setq p1 (list 230.50 1552.50) p2 (list 0.00 0.00))
 (command "TEXT" "J" "ML" p1   0.75  0.00 "")
 (setq p1 (list 232.75 1552.50) p2 (list 0.00 0.00))
 (command "TEXT" "J" "ML" p1   0.75  0.00 "6951")
 (command "LAYER" "S" "CGBLITHTXT" "")
 (setq p1 (list 236.50 1552.50) p2 (list 0.00 0.00))
 (command "TEXT" "J" "ML" p1   0.75  0.00 "MASS FLINT CLAY")
 (command "LAYER" "S" "CGBCMNT" "")
 (setq p1 (list 256.75 1552.50) p2 (list 0.00 0.00))
 (command "TEXT" "J" "ML" p1   0.75  0.00 "")
 (command "LAYER" "S" "CGBMAIN" "")
 (setq p1 (list 214.00 1554.45) p2 (list 220.00 1554.45) p3 (list 220.00 1549.29) p4 (list 214.00 1549.29))
 (command "PLINE" p1 p2 p3 p4 "c")
 (command "HATCH" "ZIGZAG" 4.00 0.00 "L" "")
 (command "COLOR" "BYLAYER")
 (command "LAYER" "S" "CGBLITHCD" "")
 (setq p1 (list 220.00 1551.87) p2 (list 221.35 1551.62))
 (command "LINE" p1 p2 "")
 (setq p1 (list 221.50 1551.25) p2 (list 0.00 0.00))
 (command "TEXT" "J" "ML" p1   0.75  0.00 "434")
 (command "LAYER" "S" "CGBTHK" "")
 (setq p1 (list 226.00 1551.25) p2 (list 0.00 0.00))
 (command "TEXT" "J" "ML" p1   0.75  0.00 "5.16")
 (command "LAYER" "S" "CGBHZID" "")
 (setq p1 (list 230.50 1551.25) p2 (list 0.00 0.00))
 (command "TEXT" "J" "ML" p1   0.75  0.00 "")
 (setq p1 (list 232.75 1551.25) p2 (list 0.00 0.00))
 (command "TEXT" "J" "ML" p1   0.75  0.00 "6951")
 (command "LAYER" "S" "CGBLITHTXT" "")
 (setq p1 (list 236.50 1551.25) p2 (list 0.00 0.00))
 (command "TEXT" "J" "ML" p1   0.75  0.00 "LT GRY GRN SDY SH W/LS NO")
 (command "LAYER" "S" "CGBCMNT" "")
 (setq p1 (list 256.75 1551.25) p2 (list 0.00 0.00))
 (command "TEXT" "J" "ML" p1   0.75  0.00 "SLC")
 (command "LAYER" "S" "CGBMAIN" "")
 (setq p1 (list 214.00 1549.29) p2 (list 220.00 1549.29) p3 (list 220.00 1547.18) p4 (list 214.00 1547.18))
 (command "PLINE" p1 p2 p3 p4 "c")
 (command "HATCH" "ZIGZAG" 4.00 0.00 "L" "")
 (command "COLOR" "BYLAYER")
 (command "LAYER" "S" "CGBLITHCD" "")
 (setq p1 (list 220.00 1548.24) p2 (list 221.35 1548.24))
 (command "LINE" p1 p2 "")
 (setq p1 (list 221.50 1547.86) p2 (list 0.00 0.00))
 (command "TEXT" "J" "ML" p1   0.75  0.00 "544")
 (command "LAYER" "S" "CGBTHK" "")
 (setq p1 (list 226.00 1547.86) p2 (list 0.00 0.00))
 (command "TEXT" "J" "ML" p1   0.75  0.00 "2.11")
 (command "LAYER" "S" "CGBHZID" "")
 (setq p1 (list 230.50 1547.86) p2 (list 0.00 0.00))
 (command "TEXT" "J" "ML" p1   0.75  0.00 "")
 (setq p1 (list 232.75 1547.86) p2 (list 0.00 0.00))
 (command "TEXT" "J" "ML" p1   0.75  0.00 "6700")
 (command "LAYER" "S" "CGBLITHTXT" "")
 (setq p1 (list 236.50 1547.86) p2 (list 0.00 0.00))
 (command "TEXT" "J" "ML" p1   0.75  0.00 "GRY MASS SS")
 (command "LAYER" "S" "CGBCMNT" "")
 (setq p1 (list 256.75 1547.86) p2 (list 0.00 0.00))
 (command "TEXT" "J" "ML" p1   0.75  0.00 "SLC")
 (command "LAYER" "S" "CGBMAIN" "")
 (setq p1 (list 214.00 1547.18) p2 (list 220.00 1547.18) p3 (list 220.00 1547.01) p4 (list 214.00 1547.01))
 (command "PLINE" p1 p2 p3 p4 "c")
 (command "HATCH" "ZIGZAG" 4.00 22.50 "L" "")
 (command "COLOR" "BYLAYER")
 (command "LAYER" "S" "CGBLITHCD" "")
 (setq p1 (list 220.00 1547.10) p2 (list 221.35 1545.85))
 (command "LINE" p1 p2 "")
 (setq p1 (list 221.50 1545.47) p2 (list 0.00 0.00))
 (command "TEXT" "J" "ML" p1   0.75  0.00 "134")
 (command "LAYER" "S" "CGBTHK" "")
 (setq p1 (list 226.00 1545.47) p2 (list 0.00 0.00))
 (command "TEXT" "J" "ML" p1   0.75  0.00 "0.17")
 (command "LAYER" "S" "CGBHZID" "")
 (setq p1 (list 230.50 1545.47) p2 (list 0.00 0.00))
 (command "TEXT" "J" "ML" p1   0.75  0.00 "")
 (setq p1 (list 232.75 1545.47) p2 (list 0.00 0.00))
 (command "TEXT" "J" "ML" p1   0.75  0.00 "6700")
 (command "LAYER" "S" "CGBLITHTXT" "")
 (setq p1 (list 236.50 1545.47) p2 (list 0.00 0.00))
 (command "TEXT" "J" "ML" p1   0.75  0.00 "LT GRY GRN SH")
 (command "LAYER" "S" "CGBCMNT" "")
 (setq p1 (list 256.75 1545.47) p2 (list 0.00 0.00))
 (command "TEXT" "J" "ML" p1   0.75  0.00 "")
 (command "LAYER" "S" "CGBMAIN" "")
 (setq p1 (list 214.00 1547.01) p2 (list 220.00 1547.01) p3 (list 220.00 1541.74) p4 (list 214.00 1541.74))
 (command "PLINE" p1 p2 p3 p4 "c")
 (command "HATCH" "ZIGZAG" 4.00 0.00 "L" "")
 (command "COLOR" "BYLAYER")
 (command "LAYER" "S" "CGBLITHCD" "")
 (setq p1 (list 220.00 1544.38) p2 (list 221.35 1544.38))
 (command "LINE" p1 p2 "")
 (setq p1 (list 221.50 1544.00) p2 (list 0.00 0.00))
 (command "TEXT" "J" "ML" p1   0.75  0.00 "541")
 (command "LAYER" "S" "CGBTHK" "")
 (setq p1 (list 226.00 1544.00) p2 (list 0.00 0.00))
 (command "TEXT" "J" "ML" p1   0.75  0.00 "5.27")
 (command "LAYER" "S" "CGBHZID" "")
 (setq p1 (list 230.50 1544.00) p2 (list 0.00 0.00))
 (command "TEXT" "J" "ML" p1   0.75  0.00 "")
 (setq p1 (list 232.75 1544.00) p2 (list 0.00 0.00))
 (command "TEXT" "J" "ML" p1   0.75  0.00 "6700")
 (command "LAYER" "S" "CGBLITHTXT" "")
 (setq p1 (list 236.50 1544.00) p2 (list 0.00 0.00))
 (command "TEXT" "J" "ML" p1   0.75  0.00 "GRY CROSSBED SS")
 (command "LAYER" "S" "CGBCMNT" "")
 (setq p1 (list 256.75 1544.00) p2 (list 0.00 0.00))
 (command "TEXT" "J" "ML" p1   0.75  0.00 "")
 (command "LAYER" "S" "CGBMAIN" "")
 (setq p1 (list 214.00 1541.74) p2 (list 220.00 1541.74) p3 (list 220.00 1526.94) p4 (list 214.00 1526.94))
 (command "PLINE" p1 p2 p3 p4 "c")
 (command "HATCH" "ZIGZAG" 4.00 0.00 "L" "")
 (command "COLOR" "BYLAYER")
 (command "LAYER" "S" "CGBLITHCD" "")
 (setq p1 (list 220.00 1534.34) p2 (list 221.35 1534.34))
 (command "LINE" p1 p2 "")
 (setq p1 (list 221.50 1533.97) p2 (list 0.00 0.00))
 (command "TEXT" "J" "ML" p1   0.75  0.00 "541")
 (command "LAYER" "S" "CGBTHK" "")
 (setq p1 (list 226.00 1533.97) p2 (list 0.00 0.00))
 (command "TEXT" "J" "ML" p1   0.75  0.00 "14.80")
 (command "LAYER" "S" "CGBHZID" "")
 (setq p1 (list 230.50 1533.97) p2 (list 0.00 0.00))
 (command "TEXT" "J" "ML" p1   0.75  0.00 "")
 (setq p1 (list 232.75 1533.97) p2 (list 0.00 0.00))
 (command "TEXT" "J" "ML" p1   0.75  0.00 "6700")
 (command "LAYER" "S" "CGBLITHTXT" "")
 (setq p1 (list 236.50 1533.97) p2 (list 0.00 0.00))
 (command "TEXT" "J" "ML" p1   0.75  0.00 "GRY CROSSBED SS")
 (command "LAYER" "S" "CGBCMNT" "")
 (setq p1 (list 256.75 1533.97) p2 (list 0.00 0.00))
 (command "TEXT" "J" "ML" p1   0.75  0.00 "")
 (command "LAYER" "S" "CGBMAIN" "")
 (setq p1 (list 214.00 1526.94) p2 (list 220.00 1526.94) p3 (list 220.00 1524.89) p4 (list 214.00 1524.89))
 (command "PLINE" p1 p2 p3 p4 "c")
 (command "HATCH" "ZIGZAG" 4.00 0.00 "L" "")
 (command "COLOR" "BYLAYER")
 (command "LAYER" "S" "CGBLITHCD" "")
 (setq p1 (list 220.00 1525.92) p2 (list 221.35 1525.92))
 (command "LINE" p1 p2 "")
 (setq p1 (list 221.50 1525.54) p2 (list 0.00 0.00))
 (command "TEXT" "J" "ML" p1   0.75  0.00 "541")
 (command "LAYER" "S" "CGBTHK" "")
 (setq p1 (list 226.00 1525.54) p2 (list 0.00 0.00))
 (command "TEXT" "J" "ML" p1   0.75  0.00 "2.05")
 (command "LAYER" "S" "CGBHZID" "")
 (setq p1 (list 230.50 1525.54) p2 (list 0.00 0.00))
 (command "TEXT" "J" "ML" p1   0.75  0.00 "")
 (setq p1 (list 232.75 1525.54) p2 (list 0.00 0.00))
 (command "TEXT" "J" "ML" p1   0.75  0.00 "6700")
 (command "LAYER" "S" "CGBLITHTXT" "")
 (setq p1 (list 236.50 1525.54) p2 (list 0.00 0.00))
 (command "TEXT" "J" "ML" p1   0.75  0.00 "GRY CROSSBED SS")
 (command "LAYER" "S" "CGBCMNT" "")
 (setq p1 (list 256.75 1525.54) p2 (list 0.00 0.00))
 (command "TEXT" "J" "ML" p1   0.75  0.00 "M GR,SLC")
 (command "LAYER" "S" "CGBMAIN" "")
 (setq p1 (list 214.00 1524.89) p2 (list 220.00 1524.89) p3 (list 220.00 1524.57) p4 (list 214.00 1524.57))
 (command "PLINE" p1 p2 p3 p4 "c")
 (command "HATCH" "ZIGZAG" 2.50 90.00 "L" "")
 (command "COLOR" "BYLAYER")
 (command "LAYER" "S" "CGBLITHCD" "")
 (setq p1 (list 220.00 1524.73) p2 (list 221.35 1523.48))
 (command "LINE" p1 p2 "")
 (setq p1 (list 221.50 1523.11) p2 (list 0.00 0.00))
 (command "TEXT" "J" "ML" p1   0.75  0.00 "324")
 (command "LAYER" "S" "CGBTHK" "")
 (setq p1 (list 226.00 1523.11) p2 (list 0.00 0.00))
 (command "TEXT" "J" "ML" p1   0.75  0.00 "0.32")
 (command "LAYER" "S" "CGBHZID" "")
 (setq p1 (list 230.50 1523.11) p2 (list 0.00 0.00))
 (command "TEXT" "J" "ML" p1   0.75  0.00 "")
 (setq p1 (list 232.75 1523.11) p2 (list 0.00 0.00))
 (command "TEXT" "J" "ML" p1   0.75  0.00 "6651")
 (command "LAYER" "S" "CGBLITHTXT" "")
 (setq p1 (list 236.50 1523.11) p2 (list 0.00 0.00))
 (command "TEXT" "J" "ML" p1   0.75  0.00 "DRK GRY MASS SDY SH")
 (command "LAYER" "S" "CGBCMNT" "")
 (setq p1 (list 256.75 1523.11) p2 (list 0.00 0.00))
 (command "TEXT" "J" "ML" p1   0.75  0.00 "SLC")
 (command "LAYER" "S" "CGBMAIN" "")
 (setq p1 (list 214.00 1524.57) p2 (list 220.00 1524.57) p3 (list 220.00 1520.95) p4 (list 214.00 1520.95))
 (command "PLINE" p1 p2 p3 p4 "c")
 (command "HATCH" "ZIGZAG" 4.00 0.00 "L" "")
 (command "COLOR" "BYLAYER")
 (command "LAYER" "S" "CGBLITHCD" "")
 (setq p1 (list 220.00 1522.76) p2 (list 221.35 1522.23))
 (command "LINE" p1 p2 "")
 (setq p1 (list 221.50 1521.86) p2 (list 0.00 0.00))
 (command "TEXT" "J" "ML" p1   0.75  0.00 "564")
 (command "LAYER" "S" "CGBTHK" "")
 (setq p1 (list 226.00 1521.86) p2 (list 0.00 0.00))
 (command "TEXT" "J" "ML" p1   0.75  0.00 "3.62")
 (command "LAYER" "S" "CGBHZID" "")
 (setq p1 (list 230.50 1521.86) p2 (list 0.00 0.00))
 (command "TEXT" "J" "ML" p1   0.75  0.00 "")
 (setq p1 (list 232.75 1521.86) p2 (list 0.00 0.00))
 (command "TEXT" "J" "ML" p1   0.75  0.00 "6400")
 (command "LAYER" "S" "CGBLITHTXT" "")
 (setq p1 (list 236.50 1521.86) p2 (list 0.00 0.00))
 (command "TEXT" "J" "ML" p1   0.75  0.00 "HARD MASS SS")
 (command "LAYER" "S" "CGBCMNT" "")
 (setq p1 (list 256.75 1521.86) p2 (list 0.00 0.00))
 (command "TEXT" "J" "ML" p1   0.75  0.00 "STYLS,SLC,F G")
 (command "LAYER" "S" "CGBMAIN" "")
 (setq p1 (list 214.00 1520.95) p2 (list 220.00 1520.95) p3 (list 220.00 1520.66) p4 (list 214.00 1520.66))
 (command "PLINE" p1 p2 p3 p4 "c")
 (command "HATCH" "ZIGZAG" 4.00 0.00 "L" "")
 (command "COLOR" "BYLAYER")
 (command "LAYER" "S" "CGBLITHCD" "")
 (setq p1 (list 220.00 1520.81) p2 (list 221.35 1520.81))
 (command "LINE" p1 p2 "")
 (setq p1 (list 221.50 1520.43) p2 (list 0.00 0.00))
 (command "TEXT" "J" "ML" p1   0.75  0.00 "124")
 (command "LAYER" "S" "CGBTHK" "")
 (setq p1 (list 226.00 1520.43) p2 (list 0.00 0.00))
 (command "TEXT" "J" "ML" p1   0.75  0.00 "0.29")
 (command "LAYER" "S" "CGBHZID" "")
 (setq p1 (list 230.50 1520.43) p2 (list 0.00 0.00))
 (command "TEXT" "J" "ML" p1   0.75  0.00 "")
 (setq p1 (list 232.75 1520.43) p2 (list 0.00 0.00))
 (command "TEXT" "J" "ML" p1   0.75  0.00 "6400")
 (command "LAYER" "S" "CGBLITHTXT" "")
 (setq p1 (list 236.50 1520.43) p2 (list 0.00 0.00))
 (command "TEXT" "J" "ML" p1   0.75  0.00 "DRK GRY SH")
 (command "LAYER" "S" "CGBCMNT" "")
 (setq p1 (list 256.75 1520.43) p2 (list 0.00 0.00))
 (command "TEXT" "J" "ML" p1   0.75  0.00 "SLC")
 (command "LAYER" "S" "CGBMAIN" "")
 (setq p1 (list 214.00 1520.66) p2 (list 220.00 1520.66) p3 (list 220.00 1515.26) p4 (list 214.00 1515.26))
 (command "PLINE" p1 p2 p3 p4 "c")
 (command "HATCH" "ZIGZAG" 4.00 0.00 "L" "")
 (command "COLOR" "BYLAYER")
 (command "LAYER" "S" "CGBLITHCD" "")
 (setq p1 (list 220.00 1517.96) p2 (list 221.35 1517.96))
 (command "LINE" p1 p2 "")
 (setq p1 (list 221.50 1517.59) p2 (list 0.00 0.00))
 (command "TEXT" "J" "ML" p1   0.75  0.00 "564")
 (command "LAYER" "S" "CGBTHK" "")
 (setq p1 (list 226.00 1517.59) p2 (list 0.00 0.00))
 (command "TEXT" "J" "ML" p1   0.75  0.00 "5.40")
 (command "LAYER" "S" "CGBHZID" "")
 (setq p1 (list 230.50 1517.59) p2 (list 0.00 0.00))
 (command "TEXT" "J" "ML" p1   0.75  0.00 "")
 (setq p1 (list 232.75 1517.59) p2 (list 0.00 0.00))
 (command "TEXT" "J" "ML" p1   0.75  0.00 "6400")
 (command "LAYER" "S" "CGBLITHTXT" "")
 (setq p1 (list 236.50 1517.59) p2 (list 0.00 0.00))
 (command "TEXT" "J" "ML" p1   0.75  0.00 "HARD MASS SS")
 (command "LAYER" "S" "CGBCMNT" "")
 (setq p1 (list 256.75 1517.59) p2 (list 0.00 0.00))
 (command "TEXT" "J" "ML" p1   0.75  0.00 "SLC")
 (command "LAYER" "S" "CGBMAIN" "")
 (setq p1 (list 214.00 1515.26) p2 (list 220.00 1515.26) p3 (list 220.00 1512.77) p4 (list 214.00 1512.77))
 (command "PLINE" p1 p2 p3 p4 "c")
 (command "HATCH" "ZIGZAG" 2.00 45.00 "L" "")
 (command "COLOR" "BYLAYER")
 (command "LAYER" "S" "CGBLITHCD" "")
 (setq p1 (list 220.00 1514.02) p2 (list 221.35 1514.02))
 (command "LINE" p1 p2 "")
 (setq p1 (list 221.50 1513.64) p2 (list 0.00 0.00))
 (command "TEXT" "J" "ML" p1   0.75  0.00 "313")
 (command "LAYER" "S" "CGBTHK" "")
 (setq p1 (list 226.00 1513.64) p2 (list 0.00 0.00))
 (command "TEXT" "J" "ML" p1   0.75  0.00 "2.49")
 (command "LAYER" "S" "CGBHZID" "")
 (setq p1 (list 230.50 1513.64) p2 (list 0.00 0.00))
 (command "TEXT" "J" "ML" p1   0.75  0.00 "")
 (setq p1 (list 232.75 1513.64) p2 (list 0.00 0.00))
 (command "TEXT" "J" "ML" p1   0.75  0.00 "6400")
 (command "LAYER" "S" "CGBLITHTXT" "")
 (setq p1 (list 236.50 1513.64) p2 (list 0.00 0.00))
 (command "TEXT" "J" "ML" p1   0.75  0.00 "BLK SH W/SS STKS")
 (command "LAYER" "S" "CGBCMNT" "")
 (setq p1 (list 256.75 1513.64) p2 (list 0.00 0.00))
 (command "TEXT" "J" "ML" p1   0.75  0.00 "")
 (command "LAYER" "S" "CGBMAIN" "")
 (setq p1 (list 214.00 1512.77) p2 (list 220.00 1512.77) p3 (list 220.00 1510.90) p4 (list 214.00 1510.90))
 (command "PLINE" p1 p2 p3 p4 "c")
 (command "HATCH" "ZIGZAG" 4.00 22.50 "L" "")
 (command "COLOR" "BYLAYER")
 (command "LAYER" "S" "CGBLITHCD" "")
 (setq p1 (list 220.00 1511.84) p2 (list 221.35 1511.84))
 (command "LINE" p1 p2 "")
 (setq p1 (list 221.50 1511.46) p2 (list 0.00 0.00))
 (command "TEXT" "J" "ML" p1   0.75  0.00 "114")
 (command "LAYER" "S" "CGBTHK" "")
 (setq p1 (list 226.00 1511.46) p2 (list 0.00 0.00))
 (command "TEXT" "J" "ML" p1   0.75  0.00 "1.87")
 (command "LAYER" "S" "CGBHZID" "")
 (setq p1 (list 230.50 1511.46) p2 (list 0.00 0.00))
 (command "TEXT" "J" "ML" p1   0.75  0.00 "")
 (setq p1 (list 232.75 1511.46) p2 (list 0.00 0.00))
 (command "TEXT" "J" "ML" p1   0.75  0.00 "6400")
 (command "LAYER" "S" "CGBLITHTXT" "")
 (setq p1 (list 236.50 1511.46) p2 (list 0.00 0.00))
 (command "TEXT" "J" "ML" p1   0.75  0.00 "BLK SH")
 (command "LAYER" "S" "CGBCMNT" "")
 (setq p1 (list 256.75 1511.46) p2 (list 0.00 0.00))
 (command "TEXT" "J" "ML" p1   0.75  0.00 "PYRT @ BASE")
 (command "LAYER" "S" "CGBMAIN" "")
 (setq p1 (list 214.00 1510.90) p2 (list 220.00 1510.90) p3 (list 220.00 1510.68) p4 (list 214.00 1510.68))
 (command "PLINE" p1 p2 p3 p4 "c")
 (command "HATCH" "ZIGZAG" 0.25 0.00 "L" "")
 (command "COLOR" "BYLAYER")
 (command "LAYER" "S" "CGBLITHCD" "")
 (setq p1 (list 220.00 1510.79) p2 (list 221.35 1509.54))
 (command "LINE" p1 p2 "")
 (setq p1 (list 221.50 1509.17) p2 (list 0.00 0.00))
 (command "TEXT" "J" "ML" p1   0.75  0.00 "768")
 (command "LAYER" "S" "CGBTHK" "")
 (setq p1 (list 226.00 1509.17) p2 (list 0.00 0.00))
 (command "TEXT" "J" "ML" p1   0.75  0.00 "0.22")
 (command "LAYER" "S" "CGBHZID" "")
 (setq p1 (list 230.50 1509.17) p2 (list 0.00 0.00))
 (command "TEXT" "J" "ML" p1   0.75  0.00 "")
 (setq p1 (list 232.75 1509.17) p2 (list 0.00 0.00))
 (command "TEXT" "J" "ML" p1   0.75  0.00 "6400")
 (command "LAYER" "S" "CGBLITHTXT" "")
 (setq p1 (list 236.50 1509.17) p2 (list 0.00 0.00))
 (command "TEXT" "J" "ML" p1   0.75  0.00 "HARD SS W/COAL BANDS")
 (command "LAYER" "S" "CGBCMNT" "")
 (setq p1 (list 256.75 1509.17) p2 (list 0.00 0.00))
 (command "TEXT" "J" "ML" p1   0.75  0.00 "ANG SLC")
 (command "LAYER" "S" "CGBMAIN" "")
 (setq p1 (list 214.00 1510.68) p2 (list 220.00 1510.68) p3 (list 220.00 1510.43) p4 (list 214.00 1510.43))
 (command "PLINE" p1 p2 p3 p4 "c")
 (command "HATCH" "ZIGZAG" 2.00 45.00 "L" "")
 (command "COLOR" "BYLAYER")
 (command "LAYER" "S" "CGBLITHCD" "")
 (setq p1 (list 220.00 1510.56) p2 (list 221.35 1508.29))
 (command "LINE" p1 p2 "")
 (setq p1 (list 221.50 1507.92) p2 (list 0.00 0.00))
 (command "TEXT" "J" "ML" p1   0.75  0.00 "312")
 (command "LAYER" "S" "CGBTHK" "")
 (setq p1 (list 226.00 1507.92) p2 (list 0.00 0.00))
 (command "TEXT" "J" "ML" p1   0.75  0.00 "0.25")
 (command "LAYER" "S" "CGBHZID" "")
 (setq p1 (list 230.50 1507.92) p2 (list 0.00 0.00))
 (command "TEXT" "J" "ML" p1   0.75  0.00 "")
 (setq p1 (list 232.75 1507.92) p2 (list 0.00 0.00))
 (command "TEXT" "J" "ML" p1   0.75  0.00 "6400")
 (command "LAYER" "S" "CGBLITHTXT" "")
 (setq p1 (list 236.50 1507.92) p2 (list 0.00 0.00))
 (command "TEXT" "J" "ML" p1   0.75  0.00 "BLK SH+INTERBED SS")
 (command "LAYER" "S" "CGBCMNT" "")
 (setq p1 (list 256.75 1507.92) p2 (list 0.00 0.00))
 (command "TEXT" "J" "ML" p1   0.75  0.00 "SLX @ CNCT")
 (command "LAYER" "S" "CGBMAIN" "")
 (setq p1 (list 214.00 1510.43) p2 (list 220.00 1510.43) p3 (list 220.00 1510.22) p4 (list 214.00 1510.22))
 (command "PLINE" p1 p2 p3 p4 "c")
 (command "HATCH" "ZIGZAG" 4.00 0.00 "L" "")
 (command "COLOR" "BYLAYER")
 (command "LAYER" "S" "CGBLITHCD" "")
 (setq p1 (list 220.00 1510.33) p2 (list 221.35 1507.04))
 (command "LINE" p1 p2 "")
 (setq p1 (list 221.50 1506.67) p2 (list 0.00 0.00))
 (command "TEXT" "J" "ML" p1   0.75  0.00 "563")
 (command "LAYER" "S" "CGBTHK" "")
 (setq p1 (list 226.00 1506.67) p2 (list 0.00 0.00))
 (command "TEXT" "J" "ML" p1   0.75  0.00 "0.21")
 (command "LAYER" "S" "CGBHZID" "")
 (setq p1 (list 230.50 1506.67) p2 (list 0.00 0.00))
 (command "TEXT" "J" "ML" p1   0.75  0.00 "")
 (setq p1 (list 232.75 1506.67) p2 (list 0.00 0.00))
 (command "TEXT" "J" "ML" p1   0.75  0.00 "6400")
 (command "LAYER" "S" "CGBLITHTXT" "")
 (setq p1 (list 236.50 1506.67) p2 (list 0.00 0.00))
 (command "TEXT" "J" "ML" p1   0.75  0.00 "HARD SS W/SH STKS")
 (command "LAYER" "S" "CGBCMNT" "")
 (setq p1 (list 256.75 1506.67) p2 (list 0.00 0.00))
 (command "TEXT" "J" "ML" p1   0.75  0.00 "HRD")
 (command "LAYER" "S" "CGBMAIN" "")
 (setq p1 (list 214.00 1510.22) p2 (list 220.00 1510.22) p3 (list 220.00 1508.26) p4 (list 214.00 1508.26))
 (command "PLINE" p1 p2 p3 p4 "c")
 (command "HATCH" "ZIGZAG" 4.00 22.50 "L" "")
 (command "COLOR" "BYLAYER")
 (command "LAYER" "S" "CGBLITHCD" "")
 (setq p1 (list 220.00 1509.24) p2 (list 221.35 1505.79))
 (command "LINE" p1 p2 "")
 (setq p1 (list 221.50 1505.42) p2 (list 0.00 0.00))
 (command "TEXT" "J" "ML" p1   0.75  0.00 "114")
 (command "LAYER" "S" "CGBTHK" "")
 (setq p1 (list 226.00 1505.42) p2 (list 0.00 0.00))
 (command "TEXT" "J" "ML" p1   0.75  0.00 "1.96")
 (command "LAYER" "S" "CGBHZID" "")
 (setq p1 (list 230.50 1505.42) p2 (list 0.00 0.00))
 (command "TEXT" "J" "ML" p1   0.75  0.00 "")
 (setq p1 (list 232.75 1505.42) p2 (list 0.00 0.00))
 (command "TEXT" "J" "ML" p1   0.75  0.00 "6351")
 (command "LAYER" "S" "CGBLITHTXT" "")
 (setq p1 (list 236.50 1505.42) p2 (list 0.00 0.00))
 (command "TEXT" "J" "ML" p1   0.75  0.00 "BLK SH")
 (command "LAYER" "S" "CGBCMNT" "")
 (setq p1 (list 256.75 1505.42) p2 (list 0.00 0.00))
 (command "TEXT" "J" "ML" p1   0.75  0.00 "BONEY @ BASE")
 (command "LAYER" "S" "CGBMAIN" "")
 (setq p1 (list 214.00 1508.26) p2 (list 220.00 1508.26) p3 (list 220.00 1508.20) p4 (list 214.00 1508.20))
 (command "PLINE" p1 p2 p3 p4 "c")
 (command "HATCH" "ZIGZAG" 4.00 0.00 "L" "")
 (command "COLOR" "BYLAYER")
 (command "LAYER" "S" "CGBLITHCD" "")
 (setq p1 (list 220.00 1508.23) p2 (list 221.35 1504.54))
 (command "LINE" p1 p2 "")
 (setq p1 (list 221.50 1504.17) p2 (list 0.00 0.00))
 (command "TEXT" "J" "ML" p1   0.75  0.00 "124")
 (command "LAYER" "S" "CGBTHK" "")
 (setq p1 (list 226.00 1504.17) p2 (list 0.00 0.00))
 (command "TEXT" "J" "ML" p1   0.75  0.00 "0.06")
 (command "LAYER" "S" "CGBHZID" "")
 (setq p1 (list 230.50 1504.17) p2 (list 0.00 0.00))
 (command "TEXT" "J" "ML" p1   0.75  0.00 "")
 (setq p1 (list 232.75 1504.17) p2 (list 0.00 0.00))
 (command "TEXT" "J" "ML" p1   0.75  0.00 "6351")
 (command "LAYER" "S" "CGBLITHTXT" "")
 (setq p1 (list 236.50 1504.17) p2 (list 0.00 0.00))
 (command "TEXT" "J" "ML" p1   0.75  0.00 "DRK GRY SH")
 (command "LAYER" "S" "CGBCMNT" "")
 (setq p1 (list 256.75 1504.17) p2 (list 0.00 0.00))
 (command "TEXT" "J" "ML" p1   0.75  0.00 "SFT")
 (command "LAYER" "S" "CGBMAIN" "")
 (setq p1 (list 214.00 1508.20) p2 (list 220.00 1508.20) p3 (list 220.00 1508.01) p4 (list 214.00 1508.01))
 (command "PLINE" p1 p2 p3 p4 "c")
 (command "HATCH" "ZIGZAG" 4.00 22.50 "L" "")
 (command "COLOR" "BYLAYER")
 (command "LAYER" "S" "CGBLITHCD" "")
 (setq p1 (list 220.00 1508.11) p2 (list 221.35 1503.29))
 (command "LINE" p1 p2 "")
 (setq p1 (list 221.50 1502.92) p2 (list 0.00 0.00))
 (command "TEXT" "J" "ML" p1   0.75  0.00 "114")
 (command "LAYER" "S" "CGBTHK" "")
 (setq p1 (list 226.00 1502.92) p2 (list 0.00 0.00))
 (command "TEXT" "J" "ML" p1   0.75  0.00 "0.19")
 (command "LAYER" "S" "CGBHZID" "")
 (setq p1 (list 230.50 1502.92) p2 (list 0.00 0.00))
 (command "TEXT" "J" "ML" p1   0.75  0.00 "")
 (setq p1 (list 232.75 1502.92) p2 (list 0.00 0.00))
 (command "TEXT" "J" "ML" p1   0.75  0.00 "6351")
 (command "LAYER" "S" "CGBLITHTXT" "")
 (setq p1 (list 236.50 1502.92) p2 (list 0.00 0.00))
 (command "TEXT" "J" "ML" p1   0.75  0.00 "BLK SH")
 (command "LAYER" "S" "CGBCMNT" "")
 (setq p1 (list 256.75 1502.92) p2 (list 0.00 0.00))
 (command "TEXT" "J" "ML" p1   0.75  0.00 "BONEY")
 (command "LAYER" "S" "CGBMAIN" "")
 (setq p1 (list 214.00 1508.01) p2 (list 220.00 1508.01) p3 (list 220.00 1507.95) p4 (list 214.00 1507.95))
 (command "PLINE" p1 p2 p3 p4 "c")
 (command "HATCH" "ZIGZAG" 0.30 0.00 "L" "")
 (command "COLOR" "BYLAYER")
 (command "LAYER" "S" "CGBLITHCD" "")
 (setq p1 (list 220.00 1507.98) p2 (list 221.35 1502.04))
 (command "LINE" p1 p2 "")
 (setq p1 (list 221.50 1501.67) p2 (list 0.00 0.00))
 (command "TEXT" "J" "ML" p1   0.75  0.00 "034")
 (command "LAYER" "S" "CGBTHK" "")
 (setq p1 (list 226.00 1501.67) p2 (list 0.00 0.00))
 (command "TEXT" "J" "ML" p1   0.75  0.00 "0.06")
 (command "LAYER" "S" "CGBHZID" "")
 (setq p1 (list 230.50 1501.67) p2 (list 0.00 0.00))
 (command "TEXT" "J" "ML" p1   0.75  0.00 "")
 (setq p1 (list 232.75 1501.67) p2 (list 0.00 0.00))
 (command "TEXT" "J" "ML" p1   0.75  0.00 "6351")
 (command "LAYER" "S" "CGBLITHTXT" "")
 (setq p1 (list 236.50 1501.67) p2 (list 0.00 0.00))
 (command "TEXT" "J" "ML" p1   0.75  0.00 "BONE")
 (command "LAYER" "S" "CGBCMNT" "")
 (setq p1 (list 256.75 1501.67) p2 (list 0.00 0.00))
 (command "TEXT" "J" "ML" p1   0.75  0.00 "PYRT @ CNCTS")
 (command "LAYER" "S" "CGBMAIN" "")
 (setq p1 (list 214.00 1507.95) p2 (list 220.00 1507.95) p3 (list 220.00 1507.73) p4 (list 214.00 1507.73))
 (command "PLINE" p1 p2 p3 p4 "c")
 (command "HATCH" "ZIGZAG" 1.00 45.00 "L" "")
 (command "COLOR" "BYLAYER")
 (command "LAYER" "S" "CGBLITHCD" "")
 (setq p1 (list 220.00 1507.84) p2 (list 221.35 1500.79))
 (command "LINE" p1 p2 "")
 (setq p1 (list 221.50 1500.42) p2 (list 0.00 0.00))
 (command "TEXT" "J" "ML" p1   0.75  0.00 "028")
 (command "LAYER" "S" "CGBTHK" "")
 (setq p1 (list 226.00 1500.42) p2 (list 0.00 0.00))
 (command "TEXT" "J" "ML" p1   0.75  0.00 "0.22")
 (command "LAYER" "S" "CGBHZID" "")
 (setq p1 (list 230.50 1500.42) p2 (list 0.00 0.00))
 (command "TEXT" "J" "ML" p1   0.75  0.00 "")
 (setq p1 (list 232.75 1500.42) p2 (list 0.00 0.00))
 (command "TEXT" "J" "ML" p1   0.75  0.00 "6000")
 (command "LAYER" "S" "CGBLITHTXT" "")
 (setq p1 (list 236.50 1500.42) p2 (list 0.00 0.00))
 (command "TEXT" "J" "ML" p1   0.75  0.00 "COAL W/SH STKS")
 (command "LAYER" "S" "CGBCMNT" "")
 (setq p1 (list 256.75 1500.42) p2 (list 0.00 0.00))
 (command "TEXT" "J" "ML" p1   0.75  0.00 "BNDED VIT")
 (command "LAYER" "S" "CGBMAIN" "")
 (setq p1 (list 214.00 1507.73) p2 (list 220.00 1507.73) p3 (list 220.00 1507.57) p4 (list 214.00 1507.57))
 (command "PLINE" p1 p2 p3 p4 "c")
 (command "HATCH" "ZIGZAG" 6.00 0.00 "L" "")
 (command "COLOR" "BYLAYER")
 (command "LAYER" "S" "CGBLITHCD" "")
 (setq p1 (list 220.00 1507.65) p2 (list 221.35 1499.54))
 (command "LINE" p1 p2 "")
 (setq p1 (list 221.50 1499.17) p2 (list 0.00 0.00))
 (command "TEXT" "J" "ML" p1   0.75  0.00 "113")
 (command "LAYER" "S" "CGBTHK" "")
 (setq p1 (list 226.00 1499.17) p2 (list 0.00 0.00))
 (command "TEXT" "J" "ML" p1   0.75  0.00 "0.16")
 (command "LAYER" "S" "CGBHZID" "")
 (setq p1 (list 230.50 1499.17) p2 (list 0.00 0.00))
 (command "TEXT" "J" "ML" p1   0.75  0.00 "")
 (setq p1 (list 232.75 1499.17) p2 (list 0.00 0.00))
 (command "TEXT" "J" "ML" p1   0.75  0.00 "6000")
 (command "LAYER" "S" "CGBLITHTXT" "")
 (setq p1 (list 236.50 1499.17) p2 (list 0.00 0.00))
 (command "TEXT" "J" "ML" p1   0.75  0.00 "BLK SH W/COAL STKS")
 (command "LAYER" "S" "CGBCMNT" "")
 (setq p1 (list 256.75 1499.17) p2 (list 0.00 0.00))
 (command "TEXT" "J" "ML" p1   0.75  0.00 "")
 (command "LAYER" "S" "CGBMAIN" "")
 (setq p1 (list 214.00 1507.57) p2 (list 220.00 1507.57) p3 (list 220.00 1505.13) p4 (list 214.00 1505.13))
 (command "PLINE" p1 p2 p3 p4 "c")
 (command "HATCH" "ZIGZAG" 0.30 22.50 "L" "")
 (command "COLOR" "BYLAYER")
 (command "LAYER" "S" "CGBLITHCD" "")
 (setq p1 (list 220.00 1506.35) p2 (list 221.35 1498.29))
 (command "LINE" p1 p2 "")
 (setq p1 (list 221.50 1497.92) p2 (list 0.00 0.00))
 (command "TEXT" "J" "ML" p1   0.75  0.00 "027")
 (command "LAYER" "S" "CGBTHK" "")
 (setq p1 (list 226.00 1497.92) p2 (list 0.00 0.00))
 (command "TEXT" "J" "ML" p1   0.75  0.00 "2.44")
 (command "LAYER" "S" "CGBHZID" "")
 (setq p1 (list 230.50 1497.92) p2 (list 0.00 0.00))
 (command "TEXT" "J" "ML" p1   0.75  0.00 "")
 (setq p1 (list 232.75 1497.92) p2 (list 0.00 0.00))
 (command "TEXT" "J" "ML" p1   0.75  0.00 "6000")
 (command "LAYER" "S" "CGBLITHTXT" "")
 (setq p1 (list 236.50 1497.92) p2 (list 0.00 0.00))
 (command "TEXT" "J" "ML" p1   0.75  0.00 "COAL W/SH LAYERS")
 (command "LAYER" "S" "CGBCMNT" "")
 (setq p1 (list 256.75 1497.92) p2 (list 0.00 0.00))
 (command "TEXT" "J" "ML" p1   0.75  0.00 "BRGHT W/ DULL")
 (command "LAYER" "S" "CGBMAIN" "")
 (setq p1 (list 214.00 1505.13) p2 (list 220.00 1505.13) p3 (list 220.00 1504.77) p4 (list 214.00 1504.77))
 (command "PLINE" p1 p2 p3 p4 "c")
 (command "HATCH" "ZIGZAG" 4.00 0.00 "L" "")
 (command "COLOR" "BYLAYER")
 (command "LAYER" "S" "CGBLITHCD" "")
 (setq p1 (list 220.00 1504.95) p2 (list 221.35 1497.04))
 (command "LINE" p1 p2 "")
 (setq p1 (list 221.50 1496.67) p2 (list 0.00 0.00))
 (command "TEXT" "J" "ML" p1   0.75  0.00 "123")
 (command "LAYER" "S" "CGBTHK" "")
 (setq p1 (list 226.00 1496.67) p2 (list 0.00 0.00))
 (command "TEXT" "J" "ML" p1   0.75  0.00 "0.36")
 (command "LAYER" "S" "CGBHZID" "")
 (setq p1 (list 230.50 1496.67) p2 (list 0.00 0.00))
 (command "TEXT" "J" "ML" p1   0.75  0.00 "3")
 (setq p1 (list 232.75 1496.67) p2 (list 0.00 0.00))
 (command "TEXT" "J" "ML" p1   0.75  0.00 "5951")
 (command "LAYER" "S" "CGBLITHTXT" "")
 (setq p1 (list 236.50 1496.67) p2 (list 0.00 0.00))
 (command "TEXT" "J" "ML" p1   0.75  0.00 "DRK GRY SH W/COAL STKS")
 (command "LAYER" "S" "CGBCMNT" "")
 (setq p1 (list 256.75 1496.67) p2 (list 0.00 0.00))
 (command "TEXT" "J" "ML" p1   0.75  0.00 "")
 (command "LAYER" "S" "CGBMAIN" "")
 (setq p1 (list 214.00 1504.77) p2 (list 220.00 1504.77) p3 (list 220.00 1504.71) p4 (list 214.00 1504.71))
 (command "PLINE" p1 p2 p3 p4 "c")
 (command "HATCH" "ZIGZAG" 0.40 45.00 "L" "")
 (command "COLOR" "BYLAYER")
 (command "LAYER" "S" "CGBLITHCD" "")
 (setq p1 (list 220.00 1504.74) p2 (list 221.35 1495.79))
 (command "LINE" p1 p2 "")
 (setq p1 (list 221.50 1495.42) p2 (list 0.00 0.00))
 (command "TEXT" "J" "ML" p1   0.75  0.00 "024")
 (command "LAYER" "S" "CGBTHK" "")
 (setq p1 (list 226.00 1495.42) p2 (list 0.00 0.00))
 (command "TEXT" "J" "ML" p1   0.75  0.00 "0.06")
 (command "LAYER" "S" "CGBHZID" "")
 (setq p1 (list 230.50 1495.42) p2 (list 0.00 0.00))
 (command "TEXT" "J" "ML" p1   0.75  0.00 "")
 (setq p1 (list 232.75 1495.42) p2 (list 0.00 0.00))
 (command "TEXT" "J" "ML" p1   0.75  0.00 "5951")
 (command "LAYER" "S" "CGBLITHTXT" "")
 (setq p1 (list 236.50 1495.42) p2 (list 0.00 0.00))
 (command "TEXT" "J" "ML" p1   0.75  0.00 "DULL OR CANNEL COAL")
 (command "LAYER" "S" "CGBCMNT" "")
 (setq p1 (list 256.75 1495.42) p2 (list 0.00 0.00))
 (command "TEXT" "J" "ML" p1   0.75  0.00 "DULL")
 (command "LAYER" "S" "CGBMAIN" "")
 (setq p1 (list 214.00 1504.71) p2 (list 220.00 1504.71) p3 (list 220.00 1503.88) p4 (list 214.00 1503.88))
 (command "PLINE" p1 p2 p3 p4 "c")
 (command "HATCH" "ZIGZAG" 6.00 0.00 "L" "")
 (command "COLOR" "BYLAYER")
 (command "LAYER" "S" "CGBLITHCD" "")
 (setq p1 (list 220.00 1504.30) p2 (list 221.35 1494.54))
 (command "LINE" p1 p2 "")
 (setq p1 (list 221.50 1494.17) p2 (list 0.00 0.00))
 (command "TEXT" "J" "ML" p1   0.75  0.00 "113")
 (command "LAYER" "S" "CGBTHK" "")
 (setq p1 (list 226.00 1494.17) p2 (list 0.00 0.00))
 (command "TEXT" "J" "ML" p1   0.75  0.00 "0.83")
 (command "LAYER" "S" "CGBHZID" "")
 (setq p1 (list 230.50 1494.17) p2 (list 0.00 0.00))
 (command "TEXT" "J" "ML" p1   0.75  0.00 "")
 (setq p1 (list 232.75 1494.17) p2 (list 0.00 0.00))
 (command "TEXT" "J" "ML" p1   0.75  0.00 "5951")
 (command "LAYER" "S" "CGBLITHTXT" "")
 (setq p1 (list 236.50 1494.17) p2 (list 0.00 0.00))
 (command "TEXT" "J" "ML" p1   0.75  0.00 "BLK SH W/COAL STKS")
 (command "LAYER" "S" "CGBCMNT" "")
 (setq p1 (list 256.75 1494.17) p2 (list 0.00 0.00))
 (command "TEXT" "J" "ML" p1   0.75  0.00 "SLX W/VIT BND")
 (command "LAYER" "S" "CGBMAIN" "")
 (setq p1 (list 214.00 1503.88) p2 (list 220.00 1503.88) p3 (list 220.00 1503.83) p4 (list 214.00 1503.83))
 (command "PLINE" p1 p2 p3 p4 "c")
 (command "HATCH" "ZIGZAG" 5.00 0.00 "L" "")
 (command "COLOR" "BYLAYER")
 (command "LAYER" "S" "CGBLITHCD" "")
 (setq p1 (list 220.00 1503.86) p2 (list 221.35 1493.29))
 (command "LINE" p1 p2 "")
 (setq p1 (list 221.50 1492.92) p2 (list 0.00 0.00))
 (command "TEXT" "J" "ML" p1   0.75  0.00 "032")
 (command "LAYER" "S" "CGBTHK" "")
 (setq p1 (list 226.00 1492.92) p2 (list 0.00 0.00))
 (command "TEXT" "J" "ML" p1   0.75  0.00 "0.05")
 (command "LAYER" "S" "CGBHZID" "")
 (setq p1 (list 230.50 1492.92) p2 (list 0.00 0.00))
 (command "TEXT" "J" "ML" p1   0.75  0.00 "")
 (setq p1 (list 232.75 1492.92) p2 (list 0.00 0.00))
 (command "TEXT" "J" "ML" p1   0.75  0.00 "5951")
 (command "LAYER" "S" "CGBLITHTXT" "")
 (setq p1 (list 236.50 1492.92) p2 (list 0.00 0.00))
 (command "TEXT" "J" "ML" p1   0.75  0.00 "BONE W/COAL LAYERS")
 (command "LAYER" "S" "CGBCMNT" "")
 (setq p1 (list 256.75 1492.92) p2 (list 0.00 0.00))
 (command "TEXT" "J" "ML" p1   0.75  0.00 "DULL")
 (command "LAYER" "S" "CGBMAIN" "")
 (setq p1 (list 214.00 1503.83) p2 (list 220.00 1503.83) p3 (list 220.00 1503.22) p4 (list 214.00 1503.22))
 (command "PLINE" p1 p2 p3 p4 "c")
 (command "COLOR" "BLUE")
 (command "SOLID" p1 p2 p4 p3 "")
 (command "COLOR" "BYLAYER")
 (command "LAYER" "S" "CGBLITHCD" "")
 (setq p1 (list 220.00 1503.53) p2 (list 221.35 1492.04))
 (command "LINE" p1 p2 "")
 (setq p1 (list 221.50 1491.67) p2 (list 0.00 0.00))
 (command "TEXT" "J" "ML" p1   0.75  0.00 "021")
 (command "LAYER" "S" "CGBTHK" "")
 (setq p1 (list 226.00 1491.67) p2 (list 0.00 0.00))
 (command "TEXT" "J" "ML" p1   0.75  0.00 "0.61")
 (command "LAYER" "S" "CGBHZID" "")
 (setq p1 (list 230.50 1491.67) p2 (list 0.00 0.00))
 (command "TEXT" "J" "ML" p1   0.75  0.00 "")
 (setq p1 (list 232.75 1491.67) p2 (list 0.00 0.00))
 (command "TEXT" "J" "ML" p1   0.75  0.00 "5500")
 (command "LAYER" "S" "CGBLITHTXT" "")
 (setq p1 (list 236.50 1491.67) p2 (list 0.00 0.00))
 (command "TEXT" "J" "ML" p1   0.75  0.00 "COMMON BANDED COAL")
 (command "LAYER" "S" "CGBCMNT" "")
 (setq p1 (list 256.75 1491.67) p2 (list 0.00 0.00))
 (command "TEXT" "J" "ML" p1   0.75  0.00 "DULL W/VIT BN")
 (command "LAYER" "S" "CGBMAIN" "")
 (setq p1 (list 214.00 1503.22) p2 (list 220.00 1503.22) p3 (list 220.00 1503.07) p4 (list 214.00 1503.07))
 (command "PLINE" p1 p2 p3 p4 "c")
 (command "HATCH" "ZIGZAG" 5.00 0.00 "L" "")
 (command "COLOR" "BYLAYER")
 (command "LAYER" "S" "CGBLITHCD" "")
 (setq p1 (list 220.00 1503.15) p2 (list 221.35 1490.79))
 (command "LINE" p1 p2 "")
 (setq p1 (list 221.50 1490.42) p2 (list 0.00 0.00))
 (command "TEXT" "J" "ML" p1   0.75  0.00 "033")
 (command "LAYER" "S" "CGBTHK" "")
 (setq p1 (list 226.00 1490.42) p2 (list 0.00 0.00))
 (command "TEXT" "J" "ML" p1   0.75  0.00 "0.15")
 (command "LAYER" "S" "CGBHZID" "")
 (setq p1 (list 230.50 1490.42) p2 (list 0.00 0.00))
 (command "TEXT" "J" "ML" p1   0.75  0.00 "")
 (setq p1 (list 232.75 1490.42) p2 (list 0.00 0.00))
 (command "TEXT" "J" "ML" p1   0.75  0.00 "5500")
 (command "LAYER" "S" "CGBLITHTXT" "")
 (setq p1 (list 236.50 1490.42) p2 (list 0.00 0.00))
 (command "TEXT" "J" "ML" p1   0.75  0.00 "BONE W/COAL STKS")
 (command "LAYER" "S" "CGBCMNT" "")
 (setq p1 (list 256.75 1490.42) p2 (list 0.00 0.00))
 (command "TEXT" "J" "ML" p1   0.75  0.00 "DULL")
 (command "LAYER" "S" "CGBMAIN" "")
 (setq p1 (list 214.00 1503.07) p2 (list 220.00 1503.07) p3 (list 220.00 1501.98) p4 (list 214.00 1501.98))
 (command "PLINE" p1 p2 p3 p4 "c")
 (command "COLOR" "BLUE")
 (command "SOLID" p1 p2 p4 p3 "")
 (command "COLOR" "BYLAYER")
 (command "LAYER" "S" "CGBLITHCD" "")
 (setq p1 (list 220.00 1502.53) p2 (list 221.35 1489.54))
 (command "LINE" p1 p2 "")
 (setq p1 (list 221.50 1489.17) p2 (list 0.00 0.00))
 (command "TEXT" "J" "ML" p1   0.75  0.00 "021")
 (command "LAYER" "S" "CGBTHK" "")
 (setq p1 (list 226.00 1489.17) p2 (list 0.00 0.00))
 (command "TEXT" "J" "ML" p1   0.75  0.00 "1.09")
 (command "LAYER" "S" "CGBHZID" "")
 (setq p1 (list 230.50 1489.17) p2 (list 0.00 0.00))
 (command "TEXT" "J" "ML" p1   0.75  0.00 "")
 (setq p1 (list 232.75 1489.17) p2 (list 0.00 0.00))
 (command "TEXT" "J" "ML" p1   0.75  0.00 "5500")
 (command "LAYER" "S" "CGBLITHTXT" "")
 (setq p1 (list 236.50 1489.17) p2 (list 0.00 0.00))
 (command "TEXT" "J" "ML" p1   0.75  0.00 "COMMON BANDED COAL")
 (command "LAYER" "S" "CGBCMNT" "")
 (setq p1 (list 256.75 1489.17) p2 (list 0.00 0.00))
 (command "TEXT" "J" "ML" p1   0.75  0.00 "BRKN VIT")
 (command "LAYER" "S" "CGBMAIN" "")
 (setq p1 (list 214.00 1501.98) p2 (list 220.00 1501.98) p3 (list 220.00 1501.83) p4 (list 214.00 1501.83))
 (command "PLINE" p1 p2 p3 p4 "c")
 (command "HATCH" "ZIGZAG" 0.30 0.00 "L" "")
 (command "COLOR" "BYLAYER")
 (command "LAYER" "S" "CGBLITHCD" "")
 (setq p1 (list 220.00 1501.91) p2 (list 221.35 1488.29))
 (command "LINE" p1 p2 "")
 (setq p1 (list 221.50 1487.92) p2 (list 0.00 0.00))
 (command "TEXT" "J" "ML" p1   0.75  0.00 "034")
 (command "LAYER" "S" "CGBTHK" "")
 (setq p1 (list 226.00 1487.92) p2 (list 0.00 0.00))
 (command "TEXT" "J" "ML" p1   0.75  0.00 "0.15")
 (command "LAYER" "S" "CGBHZID" "")
 (setq p1 (list 230.50 1487.92) p2 (list 0.00 0.00))
 (command "TEXT" "J" "ML" p1   0.75  0.00 "")
 (setq p1 (list 232.75 1487.92) p2 (list 0.00 0.00))
 (command "TEXT" "J" "ML" p1   0.75  0.00 "5500")
 (command "LAYER" "S" "CGBLITHTXT" "")
 (setq p1 (list 236.50 1487.92) p2 (list 0.00 0.00))
 (command "TEXT" "J" "ML" p1   0.75  0.00 "BONE")
 (command "LAYER" "S" "CGBCMNT" "")
 (setq p1 (list 256.75 1487.92) p2 (list 0.00 0.00))
 (command "TEXT" "J" "ML" p1   0.75  0.00 "")
 (command "LAYER" "S" "CGBMAIN" "")
 (setq p1 (list 214.00 1501.83) p2 (list 220.00 1501.83) p3 (list 220.00 1500.62) p4 (list 214.00 1500.62))
 (command "PLINE" p1 p2 p3 p4 "c")
 (command "COLOR" "BLUE")
 (command "SOLID" p1 p2 p4 p3 "")
 (command "COLOR" "BYLAYER")
 (command "LAYER" "S" "CGBLITHCD" "")
 (setq p1 (list 220.00 1501.23) p2 (list 221.35 1487.04))
 (command "LINE" p1 p2 "")
 (setq p1 (list 221.50 1486.67) p2 (list 0.00 0.00))
 (command "TEXT" "J" "ML" p1   0.75  0.00 "021")
 (command "LAYER" "S" "CGBTHK" "")
 (setq p1 (list 226.00 1486.67) p2 (list 0.00 0.00))
 (command "TEXT" "J" "ML" p1   0.75  0.00 "1.21")
 (command "LAYER" "S" "CGBHZID" "")
 (setq p1 (list 230.50 1486.67) p2 (list 0.00 0.00))
 (command "TEXT" "J" "ML" p1   0.75  0.00 "")
 (setq p1 (list 232.75 1486.67) p2 (list 0.00 0.00))
 (command "TEXT" "J" "ML" p1   0.75  0.00 "5500")
 (command "LAYER" "S" "CGBLITHTXT" "")
 (setq p1 (list 236.50 1486.67) p2 (list 0.00 0.00))
 (command "TEXT" "J" "ML" p1   0.75  0.00 "COMMON BANDED COAL")
 (command "LAYER" "S" "CGBCMNT" "")
 (setq p1 (list 256.75 1486.67) p2 (list 0.00 0.00))
 (command "TEXT" "J" "ML" p1   0.75  0.00 "BRKN VIT")
 (command "LAYER" "S" "CGBMAIN" "")
 (setq p1 (list 214.00 1500.62) p2 (list 220.00 1500.62) p3 (list 220.00 1500.39) p4 (list 214.00 1500.39))
 (command "PLINE" p1 p2 p3 p4 "c")
 (command "HATCH" "ZIGZAG" 0.80 0.00 "L" "")
 (command "COLOR" "BYLAYER")
 (command "LAYER" "S" "CGBLITHCD" "")
 (setq p1 (list 220.00 1500.51) p2 (list 221.35 1485.79))
 (command "LINE" p1 p2 "")
 (setq p1 (list 221.50 1485.42) p2 (list 0.00 0.00))
 (command "TEXT" "J" "ML" p1   0.75  0.00 "029")
 (command "LAYER" "S" "CGBTHK" "")
 (setq p1 (list 226.00 1485.42) p2 (list 0.00 0.00))
 (command "TEXT" "J" "ML" p1   0.75  0.00 "0.23")
 (command "LAYER" "S" "CGBHZID" "")
 (setq p1 (list 230.50 1485.42) p2 (list 0.00 0.00))
 (command "TEXT" "J" "ML" p1   0.75  0.00 "")
 (setq p1 (list 232.75 1485.42) p2 (list 0.00 0.00))
 (command "TEXT" "J" "ML" p1   0.75  0.00 "5500")
 (command "LAYER" "S" "CGBLITHTXT" "")
 (setq p1 (list 236.50 1485.42) p2 (list 0.00 0.00))
 (command "TEXT" "J" "ML" p1   0.75  0.00 "COAL W/PYRITE STKS")
 (command "LAYER" "S" "CGBCMNT" "")
 (setq p1 (list 256.75 1485.42) p2 (list 0.00 0.00))
 (command "TEXT" "J" "ML" p1   0.75  0.00 "THK VIT")
 (command "LAYER" "S" "CGBMAIN" "")
 (setq p1 (list 214.00 1500.39) p2 (list 220.00 1500.39) p3 (list 220.00 1500.15) p4 (list 214.00 1500.15))
 (command "PLINE" p1 p2 p3 p4 "c")
 (command "HATCH" "ZIGZAG" 0.30 22.50 "L" "")
 (command "COLOR" "BYLAYER")
 (command "LAYER" "S" "CGBLITHCD" "")
 (setq p1 (list 220.00 1500.27) p2 (list 221.35 1484.54))
 (command "LINE" p1 p2 "")
 (setq p1 (list 221.50 1484.17) p2 (list 0.00 0.00))
 (command "TEXT" "J" "ML" p1   0.75  0.00 "027")
 (command "LAYER" "S" "CGBTHK" "")
 (setq p1 (list 226.00 1484.17) p2 (list 0.00 0.00))
 (command "TEXT" "J" "ML" p1   0.75  0.00 "0.24")
 (command "LAYER" "S" "CGBHZID" "")
 (setq p1 (list 230.50 1484.17) p2 (list 0.00 0.00))
 (command "TEXT" "J" "ML" p1   0.75  0.00 "")
 (setq p1 (list 232.75 1484.17) p2 (list 0.00 0.00))
 (command "TEXT" "J" "ML" p1   0.75  0.00 "5500")
 (command "LAYER" "S" "CGBLITHTXT" "")
 (setq p1 (list 236.50 1484.17) p2 (list 0.00 0.00))
 (command "TEXT" "J" "ML" p1   0.75  0.00 "COAL W/SH LAYERS")
 (command "LAYER" "S" "CGBCMNT" "")
 (setq p1 (list 256.75 1484.17) p2 (list 0.00 0.00))
 (command "TEXT" "J" "ML" p1   0.75  0.00 "")
 (command "LAYER" "S" "CGBMAIN" "")
 (setq p1 (list 214.00 1500.15) p2 (list 220.00 1500.15) p3 (list 220.00 1500.00) p4 (list 214.00 1500.00))
 (command "PLINE" p1 p2 p3 p4 "c")
 (command "COLOR" "BLUE")
 (command "SOLID" p1 p2 p4 p3 "")
 (command "COLOR" "BYLAYER")
 (command "LAYER" "S" "CGBLITHCD" "")
 (setq p1 (list 220.00 1500.08) p2 (list 221.35 1483.29))
 (command "LINE" p1 p2 "")
 (setq p1 (list 221.50 1482.92) p2 (list 0.00 0.00))
 (command "TEXT" "J" "ML" p1   0.75  0.00 "021")
 (command "LAYER" "S" "CGBTHK" "")
 (setq p1 (list 226.00 1482.92) p2 (list 0.00 0.00))
 (command "TEXT" "J" "ML" p1   0.75  0.00 "0.15")
 (command "LAYER" "S" "CGBHZID" "")
 (setq p1 (list 230.50 1482.92) p2 (list 0.00 0.00))
 (command "TEXT" "J" "ML" p1   0.75  0.00 "")
 (setq p1 (list 232.75 1482.92) p2 (list 0.00 0.00))
 (command "TEXT" "J" "ML" p1   0.75  0.00 "5500")
 (command "LAYER" "S" "CGBLITHTXT" "")
 (setq p1 (list 236.50 1482.92) p2 (list 0.00 0.00))
 (command "TEXT" "J" "ML" p1   0.75  0.00 "COMMON BANDED COAL")
 (command "LAYER" "S" "CGBCMNT" "")
 (setq p1 (list 256.75 1482.92) p2 (list 0.00 0.00))
 (command "TEXT" "J" "ML" p1   0.75  0.00 "VIT W/PYRT")
 (command "LAYER" "S" "CGBMAIN" "")
 (setq p1 (list 214.00 1500.00) p2 (list 220.00 1500.00) p3 (list 220.00 1499.62) p4 (list 214.00 1499.62))
 (command "PLINE" p1 p2 p3 p4 "c")
 (command "HATCH" "ZIGZAG" 0.25 0.00 "L" "")
 (command "COLOR" "BYLAYER")
 (command "LAYER" "S" "CGBLITHCD" "")
 (setq p1 (list 220.00 1499.81) p2 (list 221.35 1482.04))
 (command "LINE" p1 p2 "")
 (setq p1 (list 221.50 1481.67) p2 (list 0.00 0.00))
 (command "TEXT" "J" "ML" p1   0.75  0.00 "117")
 (command "LAYER" "S" "CGBTHK" "")
 (setq p1 (list 226.00 1481.67) p2 (list 0.00 0.00))
 (command "TEXT" "J" "ML" p1   0.75  0.00 "0.38")
 (command "LAYER" "S" "CGBHZID" "")
 (setq p1 (list 230.50 1481.67) p2 (list 0.00 0.00))
 (command "TEXT" "J" "ML" p1   0.75  0.00 "")
 (setq p1 (list 232.75 1481.67) p2 (list 0.00 0.00))
 (command "TEXT" "J" "ML" p1   0.75  0.00 "5451")
 (command "LAYER" "S" "CGBLITHTXT" "")
 (setq p1 (list 236.50 1481.67) p2 (list 0.00 0.00))
 (command "TEXT" "J" "ML" p1   0.75  0.00 "BLK FIRECLAY")
 (command "LAYER" "S" "CGBCMNT" "")
 (setq p1 (list 256.75 1481.67) p2 (list 0.00 0.00))
 (command "TEXT" "J" "ML" p1   0.75  0.00 "GB")
 (command "LAYER" "S" "CGBMAIN" "")
 (setq p1 (list 214.00 1499.62) p2 (list 220.00 1499.62) p3 (list 220.00 1498.84) p4 (list 214.00 1498.84))
 (command "PLINE" p1 p2 p3 p4 "c")
 (command "HATCH" "ZIGZAG" 0.25 0.00 "L" "")
 (command "COLOR" "BYLAYER")
 (command "LAYER" "S" "CGBLITHCD" "")
 (setq p1 (list 220.00 1499.23) p2 (list 221.35 1480.79))
 (command "LINE" p1 p2 "")
 (setq p1 (list 221.50 1480.42) p2 (list 0.00 0.00))
 (command "TEXT" "J" "ML" p1   0.75  0.00 "127")
 (command "LAYER" "S" "CGBTHK" "")
 (setq p1 (list 226.00 1480.42) p2 (list 0.00 0.00))
 (command "TEXT" "J" "ML" p1   0.75  0.00 "0.78")
 (command "LAYER" "S" "CGBHZID" "")
 (setq p1 (list 230.50 1480.42) p2 (list 0.00 0.00))
 (command "TEXT" "J" "ML" p1   0.75  0.00 "")
 (setq p1 (list 232.75 1480.42) p2 (list 0.00 0.00))
 (command "TEXT" "J" "ML" p1   0.75  0.00 "5451")
 (command "LAYER" "S" "CGBLITHTXT" "")
 (setq p1 (list 236.50 1480.42) p2 (list 0.00 0.00))
 (command "TEXT" "J" "ML" p1   0.75  0.00 "DRK GRY FIRECLAY")
 (command "LAYER" "S" "CGBCMNT" "")
 (setq p1 (list 256.75 1480.42) p2 (list 0.00 0.00))
 (command "TEXT" "J" "ML" p1   0.75  0.00 "GB")
 (command "LAYER" "S" "CGBMAIN" "")
 (setq p1 (list 214.00 1498.84) p2 (list 220.00 1498.84) p3 (list 220.00 1498.04) p4 (list 214.00 1498.04))
 (command "PLINE" p1 p2 p3 p4 "c")
 (command "HATCH" "ZIGZAG" 0.25 0.00 "L" "")
 (command "COLOR" "BYLAYER")
 (command "LAYER" "S" "CGBLITHCD" "")
 (setq p1 (list 220.00 1498.44) p2 (list 221.35 1479.54))
 (command "LINE" p1 p2 "")
 (setq p1 (list 221.50 1479.17) p2 (list 0.00 0.00))
 (command "TEXT" "J" "ML" p1   0.75  0.00 "127")
 (command "LAYER" "S" "CGBTHK" "")
 (setq p1 (list 226.00 1479.17) p2 (list 0.00 0.00))
 (command "TEXT" "J" "ML" p1   0.75  0.00 "0.80")
 (command "LAYER" "S" "CGBHZID" "")
 (setq p1 (list 230.50 1479.17) p2 (list 0.00 0.00))
 (command "TEXT" "J" "ML" p1   0.75  0.00 "")
 (setq p1 (list 232.75 1479.17) p2 (list 0.00 0.00))
 (command "TEXT" "J" "ML" p1   0.75  0.00 "5451")
 (command "LAYER" "S" "CGBLITHTXT" "")
 (setq p1 (list 236.50 1479.17) p2 (list 0.00 0.00))
 (command "TEXT" "J" "ML" p1   0.75  0.00 "DRK GRY FIRECLAY")
 (command "LAYER" "S" "CGBCMNT" "")
 (setq p1 (list 256.75 1479.17) p2 (list 0.00 0.00))
 (command "TEXT" "J" "ML" p1   0.75  0.00 "V SFT LAYERS")
 (command "LAYER" "S" "CGBMAIN" "")
 (setq p1 (list 214.00 1498.04) p2 (list 220.00 1498.04) p3 (list 220.00 1496.29) p4 (list 214.00 1496.29))
 (command "PLINE" p1 p2 p3 p4 "c")
 (command "HATCH" "ZIGZAG" 0.25 0.00 "L" "")
 (command "COLOR" "BYLAYER")
 (command "LAYER" "S" "CGBLITHCD" "")
 (setq p1 (list 220.00 1497.17) p2 (list 221.35 1478.29))
 (command "LINE" p1 p2 "")
 (setq p1 (list 221.50 1477.92) p2 (list 0.00 0.00))
 (command "TEXT" "J" "ML" p1   0.75  0.00 "127")
 (command "LAYER" "S" "CGBTHK" "")
 (setq p1 (list 226.00 1477.92) p2 (list 0.00 0.00))
 (command "TEXT" "J" "ML" p1   0.75  0.00 "1.75")
 (command "LAYER" "S" "CGBHZID" "")
 (setq p1 (list 230.50 1477.92) p2 (list 0.00 0.00))
 (command "TEXT" "J" "ML" p1   0.75  0.00 "")
 (setq p1 (list 232.75 1477.92) p2 (list 0.00 0.00))
 (command "TEXT" "J" "ML" p1   0.75  0.00 "5451")
 (command "LAYER" "S" "CGBLITHTXT" "")
 (setq p1 (list 236.50 1477.92) p2 (list 0.00 0.00))
 (command "TEXT" "J" "ML" p1   0.75  0.00 "DRK GRY FIRECLAY")
 (command "LAYER" "S" "CGBCMNT" "")
 (setq p1 (list 256.75 1477.92) p2 (list 0.00 0.00))
 (command "TEXT" "J" "ML" p1   0.75  0.00 "")
 (command "LAYER" "S" "CGBMAIN" "")
 (setq p1 (list 214.00 1496.29) p2 (list 220.00 1496.29) p3 (list 220.00 1491.29) p4 (list 214.00 1491.29))
 (command "PLINE" p1 p2 p3 p4 "c")
 (command "HATCH" "ZIGZAG" 5.00 0.00 "L" "")
 (command "COLOR" "BYLAYER")
 (command "LAYER" "S" "CGBLITHCD" "")
 (setq p1 (list 220.00 1493.79) p2 (list 221.35 1477.04))
 (command "LINE" p1 p2 "")
 (setq p1 (list 221.50 1476.67) p2 (list 0.00 0.00))
 (command "TEXT" "J" "ML" p1   0.75  0.00 "322")
 (command "LAYER" "S" "CGBTHK" "")
 (setq p1 (list 226.00 1476.67) p2 (list 0.00 0.00))
 (command "TEXT" "J" "ML" p1   0.75  0.00 "5.00")
 (command "LAYER" "S" "CGBHZID" "")
 (setq p1 (list 230.50 1476.67) p2 (list 0.00 0.00))
 (command "TEXT" "J" "ML" p1   0.75  0.00 "")
 (setq p1 (list 232.75 1476.67) p2 (list 0.00 0.00))
 (command "TEXT" "J" "ML" p1   0.75  0.00 "5451")
 (command "LAYER" "S" "CGBLITHTXT" "")
 (setq p1 (list 236.50 1476.67) p2 (list 0.00 0.00))
 (command "TEXT" "J" "ML" p1   0.75  0.00 "DRK GRY SH+INTERBED SS")
 (command "LAYER" "S" "CGBCMNT" "")
 (setq p1 (list 256.75 1476.67) p2 (list 0.00 0.00))
 (command "TEXT" "J" "ML" p1   0.75  0.00 "CALC")
 (command "LAYER" "S" "CGBMAIN" "")
 (setq p1 (list 214.00 1491.29) p2 (list 220.00 1491.29) p3 (list 220.00 1489.08) p4 (list 214.00 1489.08))
 (command "PLINE" p1 p2 p3 p4 "c")
 (command "HATCH" "ZIGZAG" 5.00 0.00 "L" "")
 (command "COLOR" "BYLAYER")
 (command "LAYER" "S" "CGBLITHCD" "")
 (setq p1 (list 220.00 1490.19) p2 (list 221.35 1475.79))
 (command "LINE" p1 p2 "")
 (setq p1 (list 221.50 1475.42) p2 (list 0.00 0.00))
 (command "TEXT" "J" "ML" p1   0.75  0.00 "322")
 (command "LAYER" "S" "CGBTHK" "")
 (setq p1 (list 226.00 1475.42) p2 (list 0.00 0.00))
 (command "TEXT" "J" "ML" p1   0.75  0.00 "2.21")
 (command "LAYER" "S" "CGBHZID" "")
 (setq p1 (list 230.50 1475.42) p2 (list 0.00 0.00))
 (command "TEXT" "J" "ML" p1   0.75  0.00 "")
 (setq p1 (list 232.75 1475.42) p2 (list 0.00 0.00))
 (command "TEXT" "J" "ML" p1   0.75  0.00 "5451")
 (command "LAYER" "S" "CGBLITHTXT" "")
 (setq p1 (list 236.50 1475.42) p2 (list 0.00 0.00))
 (command "TEXT" "J" "ML" p1   0.75  0.00 "DRK GRY SH+INTERBED SS")
 (command "LAYER" "S" "CGBCMNT" "")
 (setq p1 (list 256.75 1475.42) p2 (list 0.00 0.00))
 (command "TEXT" "J" "ML" p1   0.75  0.00 "SLGHT ANG BED")
 (command "LAYER" "S" "CGBMAIN" "")
 (setq p1 (list 214.00 1489.08) p2 (list 220.00 1489.08) p3 (list 220.00 1488.35) p4 (list 214.00 1488.35))
 (command "PLINE" p1 p2 p3 p4 "c")
 (command "HATCH" "ZIGZAG" 0.50 0.00 "L" "")
 (command "COLOR" "BYLAYER")
 (command "LAYER" "S" "CGBLITHCD" "")
 (setq p1 (list 220.00 1488.72) p2 (list 221.35 1474.54))
 (command "LINE" p1 p2 "")
 (setq p1 (list 221.50 1474.17) p2 (list 0.00 0.00))
 (command "TEXT" "J" "ML" p1   0.75  0.00 "323")
 (command "LAYER" "S" "CGBTHK" "")
 (setq p1 (list 226.00 1474.17) p2 (list 0.00 0.00))
 (command "TEXT" "J" "ML" p1   0.75  0.00 "0.73")
 (command "LAYER" "S" "CGBHZID" "")
 (setq p1 (list 230.50 1474.17) p2 (list 0.00 0.00))
 (command "TEXT" "J" "ML" p1   0.75  0.00 "")
 (setq p1 (list 232.75 1474.17) p2 (list 0.00 0.00))
 (command "TEXT" "J" "ML" p1   0.75  0.00 "5451")
 (command "LAYER" "S" "CGBLITHTXT" "")
 (setq p1 (list 236.50 1474.17) p2 (list 0.00 0.00))
 (command "TEXT" "J" "ML" p1   0.75  0.00 "DRK GRY SH W/SS STKS")
 (command "LAYER" "S" "CGBCMNT" "")
 (setq p1 (list 256.75 1474.17) p2 (list 0.00 0.00))
 (command "TEXT" "J" "ML" p1   0.75  0.00 "")
 (command "LAYER" "S" "CGBMAIN" "")
 (setq p1 (list 214.00 1488.35) p2 (list 220.00 1488.35) p3 (list 220.00 1485.53) p4 (list 214.00 1485.53))
 (command "PLINE" p1 p2 p3 p4 "c")
 (command "HATCH" "ZIGZAG" 2.50 90.00 "L" "")
 (command "COLOR" "BYLAYER")
 (command "LAYER" "S" "CGBLITHCD" "")
 (setq p1 (list 220.00 1486.94) p2 (list 221.35 1473.29))
 (command "LINE" p1 p2 "")
 (setq p1 (list 221.50 1472.92) p2 (list 0.00 0.00))
 (command "TEXT" "J" "ML" p1   0.75  0.00 "328")
 (command "LAYER" "S" "CGBTHK" "")
 (setq p1 (list 226.00 1472.92) p2 (list 0.00 0.00))
 (command "TEXT" "J" "ML" p1   0.75  0.00 "2.82")
 (command "LAYER" "S" "CGBHZID" "")
 (setq p1 (list 230.50 1472.92) p2 (list 0.00 0.00))
 (command "TEXT" "J" "ML" p1   0.75  0.00 "")
 (setq p1 (list 232.75 1472.92) p2 (list 0.00 0.00))
 (command "TEXT" "J" "ML" p1   0.75  0.00 "5451")
 (command "LAYER" "S" "CGBLITHTXT" "")
 (setq p1 (list 236.50 1472.92) p2 (list 0.00 0.00))
 (command "TEXT" "J" "ML" p1   0.75  0.00 "DRK GRY BURROWED SDY SH")
 (command "LAYER" "S" "CGBCMNT" "")
 (setq p1 (list 256.75 1472.92) p2 (list 0.00 0.00))
 (command "TEXT" "J" "ML" p1   0.75  0.00 "")
 (command "LAYER" "S" "CGBMAIN" "")
 (setq p1 (list 214.00 1485.53) p2 (list 220.00 1485.53) p3 (list 220.00 1484.96) p4 (list 214.00 1484.96))
 (command "PLINE" p1 p2 p3 p4 "c")
 (command "HATCH" "ZIGZAG" 0.50 0.00 "L" "")
 (command "COLOR" "BYLAYER")
 (command "LAYER" "S" "CGBLITHCD" "")
 (setq p1 (list 220.00 1485.25) p2 (list 221.35 1472.04))
 (command "LINE" p1 p2 "")
 (setq p1 (list 221.50 1471.67) p2 (list 0.00 0.00))
 (command "TEXT" "J" "ML" p1   0.75  0.00 "804")
 (command "LAYER" "S" "CGBTHK" "")
 (setq p1 (list 226.00 1471.67) p2 (list 0.00 0.00))
 (command "TEXT" "J" "ML" p1   0.75  0.00 "0.57")
 (command "LAYER" "S" "CGBHZID" "")
 (setq p1 (list 230.50 1471.67) p2 (list 0.00 0.00))
 (command "TEXT" "J" "ML" p1   0.75  0.00 "")
 (setq p1 (list 232.75 1471.67) p2 (list 0.00 0.00))
 (command "TEXT" "J" "ML" p1   0.75  0.00 "5451")
 (command "LAYER" "S" "CGBLITHTXT" "")
 (setq p1 (list 236.50 1471.67) p2 (list 0.00 0.00))
 (command "TEXT" "J" "ML" p1   0.75  0.00 "MASS FN GRND SHLY LS")
 (command "LAYER" "S" "CGBCMNT" "")
 (setq p1 (list 256.75 1471.67) p2 (list 0.00 0.00))
 (command "TEXT" "J" "ML" p1   0.75  0.00 "")
 (command "LAYER" "S" "CGBMAIN" "")
 (setq p1 (list 214.00 1484.96) p2 (list 220.00 1484.96) p3 (list 220.00 1483.89) p4 (list 214.00 1483.89))
 (command "PLINE" p1 p2 p3 p4 "c")
 (command "HATCH" "ZIGZAG" 0.50 0.00 "L" "")
 (command "COLOR" "BYLAYER")
 (command "LAYER" "S" "CGBLITHCD" "")
 (setq p1 (list 220.00 1484.43) p2 (list 221.35 1470.79))
 (command "LINE" p1 p2 "")
 (setq p1 (list 221.50 1470.42) p2 (list 0.00 0.00))
 (command "TEXT" "J" "ML" p1   0.75  0.00 "323")
 (command "LAYER" "S" "CGBTHK" "")
 (setq p1 (list 226.00 1470.42) p2 (list 0.00 0.00))
 (command "TEXT" "J" "ML" p1   0.75  0.00 "1.07")
 (command "LAYER" "S" "CGBHZID" "")
 (setq p1 (list 230.50 1470.42) p2 (list 0.00 0.00))
 (command "TEXT" "J" "ML" p1   0.75  0.00 "")
 (setq p1 (list 232.75 1470.42) p2 (list 0.00 0.00))
 (command "TEXT" "J" "ML" p1   0.75  0.00 "5451")
 (command "LAYER" "S" "CGBLITHTXT" "")
 (setq p1 (list 236.50 1470.42) p2 (list 0.00 0.00))
 (command "TEXT" "J" "ML" p1   0.75  0.00 "DRK GRY SH W/SS STKS")
 (command "LAYER" "S" "CGBCMNT" "")
 (setq p1 (list 256.75 1470.42) p2 (list 0.00 0.00))
 (command "TEXT" "J" "ML" p1   0.75  0.00 "")
 (command "LAYER" "S" "CGBMAIN" "")
 (setq p1 (list 214.00 1483.89) p2 (list 220.00 1483.89) p3 (list 220.00 1482.29) p4 (list 214.00 1482.29))
 (command "PLINE" p1 p2 p3 p4 "c")
 (command "HATCH" "ZIGZAG" 0.25 0.00 "L" "")
 (command "COLOR" "BYLAYER")
 (command "LAYER" "S" "CGBLITHCD" "")
 (setq p1 (list 220.00 1483.09) p2 (list 221.35 1469.54))
 (command "LINE" p1 p2 "")
 (setq p1 (list 221.50 1469.17) p2 (list 0.00 0.00))
 (command "TEXT" "J" "ML" p1   0.75  0.00 "327")
 (command "LAYER" "S" "CGBTHK" "")
 (setq p1 (list 226.00 1469.17) p2 (list 0.00 0.00))
 (command "TEXT" "J" "ML" p1   0.75  0.00 "1.60")
 (command "LAYER" "S" "CGBHZID" "")
 (setq p1 (list 230.50 1469.17) p2 (list 0.00 0.00))
 (command "TEXT" "J" "ML" p1   0.75  0.00 "")
 (setq p1 (list 232.75 1469.17) p2 (list 0.00 0.00))
 (command "TEXT" "J" "ML" p1   0.75  0.00 "5451")
 (command "LAYER" "S" "CGBLITHTXT" "")
 (setq p1 (list 236.50 1469.17) p2 (list 0.00 0.00))
 (command "TEXT" "J" "ML" p1   0.75  0.00 "DRK GRY SDY FIRECLAY")
 (command "LAYER" "S" "CGBCMNT" "")
 (setq p1 (list 256.75 1469.17) p2 (list 0.00 0.00))
 (command "TEXT" "J" "ML" p1   0.75  0.00 "")
 (command "LAYER" "S" "CGBMAIN" "")
 (setq p1 (list 213.50 1886.94) p2 (list 214.00 1886.94))
 (command "LINE" p1 p2 "")
 (setq p1 (list 213.13 1886.94) p2 (list 0.00 0.00))
 (command "TEXT" "J" "MR" p1   0.75  0.00 "0.00")
 (setq p1 (list 213.13 1885.82) p2 (list 0.00 0.00))
 (command "TEXT" "J" "MR" p1   0.75  0.00 "3178.43")
 (setq p1 (list 213.50 1876.94) p2 (list 214.00 1876.94))
 (command "LINE" p1 p2 "")
 (setq p1 (list 213.13 1876.94) p2 (list 0.00 0.00))
 (command "TEXT" "J" "MR" p1   0.75  0.00 "10.00")
 (setq p1 (list 213.13 1875.82) p2 (list 0.00 0.00))
 (command "TEXT" "J" "MR" p1   0.75  0.00 "3168.43")
 (setq p1 (list 213.50 1866.94) p2 (list 214.00 1866.94))
 (command "LINE" p1 p2 "")
 (setq p1 (list 213.13 1866.94) p2 (list 0.00 0.00))
 (command "TEXT" "J" "MR" p1   0.75  0.00 "20.00")
 (setq p1 (list 213.13 1865.82) p2 (list 0.00 0.00))
 (command "TEXT" "J" "MR" p1   0.75  0.00 "3158.43")
 (setq p1 (list 213.50 1856.94) p2 (list 214.00 1856.94))
 (command "LINE" p1 p2 "")
 (setq p1 (list 213.13 1856.94) p2 (list 0.00 0.00))
 (command "TEXT" "J" "MR" p1   0.75  0.00 "30.00")
 (setq p1 (list 213.13 1855.82) p2 (list 0.00 0.00))
 (command "TEXT" "J" "MR" p1   0.75  0.00 "3148.43")
 (setq p1 (list 213.50 1846.94) p2 (list 214.00 1846.94))
 (command "LINE" p1 p2 "")
 (setq p1 (list 213.13 1846.94) p2 (list 0.00 0.00))
 (command "TEXT" "J" "MR" p1   0.75  0.00 "40.00")
 (setq p1 (list 213.13 1845.82) p2 (list 0.00 0.00))
 (command "TEXT" "J" "MR" p1   0.75  0.00 "3138.43")
 (setq p1 (list 213.50 1836.94) p2 (list 214.00 1836.94))
 (command "LINE" p1 p2 "")
 (setq p1 (list 213.13 1836.94) p2 (list 0.00 0.00))
 (command "TEXT" "J" "MR" p1   0.75  0.00 "50.00")
 (setq p1 (list 213.13 1835.82) p2 (list 0.00 0.00))
 (command "TEXT" "J" "MR" p1   0.75  0.00 "3128.43")
 (setq p1 (list 213.50 1826.94) p2 (list 214.00 1826.94))
 (command "LINE" p1 p2 "")
 (setq p1 (list 213.13 1826.94) p2 (list 0.00 0.00))
 (command "TEXT" "J" "MR" p1   0.75  0.00 "60.00")
 (setq p1 (list 213.13 1825.82) p2 (list 0.00 0.00))
 (command "TEXT" "J" "MR" p1   0.75  0.00 "3118.43")
 (setq p1 (list 213.50 1816.94) p2 (list 214.00 1816.94))
 (command "LINE" p1 p2 "")
 (setq p1 (list 213.13 1816.94) p2 (list 0.00 0.00))
 (command "TEXT" "J" "MR" p1   0.75  0.00 "70.00")
 (setq p1 (list 213.13 1815.82) p2 (list 0.00 0.00))
 (command "TEXT" "J" "MR" p1   0.75  0.00 "3108.43")
 (setq p1 (list 213.50 1806.94) p2 (list 214.00 1806.94))
 (command "LINE" p1 p2 "")
 (setq p1 (list 213.13 1806.94) p2 (list 0.00 0.00))
 (command "TEXT" "J" "MR" p1   0.75  0.00 "80.00")
 (setq p1 (list 213.13 1805.82) p2 (list 0.00 0.00))
 (command "TEXT" "J" "MR" p1   0.75  0.00 "3098.43")
 (setq p1 (list 213.50 1796.94) p2 (list 214.00 1796.94))
 (command "LINE" p1 p2 "")
 (setq p1 (list 213.13 1796.94) p2 (list 0.00 0.00))
 (command "TEXT" "J" "MR" p1   0.75  0.00 "90.00")
 (setq p1 (list 213.13 1795.82) p2 (list 0.00 0.00))
 (command "TEXT" "J" "MR" p1   0.75  0.00 "3088.43")
 (setq p1 (list 213.50 1786.94) p2 (list 214.00 1786.94))
 (command "LINE" p1 p2 "")
 (setq p1 (list 213.13 1786.94) p2 (list 0.00 0.00))
 (command "TEXT" "J" "MR" p1   0.75  0.00 "100.00")
 (setq p1 (list 213.13 1785.82) p2 (list 0.00 0.00))
 (command "TEXT" "J" "MR" p1   0.75  0.00 "3078.43")
 (setq p1 (list 213.50 1776.94) p2 (list 214.00 1776.94))
 (command "LINE" p1 p2 "")
 (setq p1 (list 213.13 1776.94) p2 (list 0.00 0.00))
 (command "TEXT" "J" "MR" p1   0.75  0.00 "110.00")
 (setq p1 (list 213.13 1775.82) p2 (list 0.00 0.00))
 (command "TEXT" "J" "MR" p1   0.75  0.00 "3068.43")
 (setq p1 (list 213.50 1766.94) p2 (list 214.00 1766.94))
 (command "LINE" p1 p2 "")
 (setq p1 (list 213.13 1766.94) p2 (list 0.00 0.00))
 (command "TEXT" "J" "MR" p1   0.75  0.00 "120.00")
 (setq p1 (list 213.13 1765.82) p2 (list 0.00 0.00))
 (command "TEXT" "J" "MR" p1   0.75  0.00 "3058.43")
 (setq p1 (list 213.50 1756.94) p2 (list 214.00 1756.94))
 (command "LINE" p1 p2 "")
 (setq p1 (list 213.13 1756.94) p2 (list 0.00 0.00))
 (command "TEXT" "J" "MR" p1   0.75  0.00 "130.00")
 (setq p1 (list 213.13 1755.82) p2 (list 0.00 0.00))
 (command "TEXT" "J" "MR" p1   0.75  0.00 "3048.43")
 (setq p1 (list 213.50 1746.94) p2 (list 214.00 1746.94))
 (command "LINE" p1 p2 "")
 (setq p1 (list 213.13 1746.94) p2 (list 0.00 0.00))
 (command "TEXT" "J" "MR" p1   0.75  0.00 "140.00")
 (setq p1 (list 213.13 1745.82) p2 (list 0.00 0.00))
 (command "TEXT" "J" "MR" p1   0.75  0.00 "3038.43")
 (setq p1 (list 213.50 1736.94) p2 (list 214.00 1736.94))
 (command "LINE" p1 p2 "")
 (setq p1 (list 213.13 1736.94) p2 (list 0.00 0.00))
 (command "TEXT" "J" "MR" p1   0.75  0.00 "150.00")
 (setq p1 (list 213.13 1735.82) p2 (list 0.00 0.00))
 (command "TEXT" "J" "MR" p1   0.75  0.00 "3028.43")
 (setq p1 (list 213.50 1726.94) p2 (list 214.00 1726.94))
 (command "LINE" p1 p2 "")
 (setq p1 (list 213.13 1726.94) p2 (list 0.00 0.00))
 (command "TEXT" "J" "MR" p1   0.75  0.00 "160.00")
 (setq p1 (list 213.13 1725.82) p2 (list 0.00 0.00))
 (command "TEXT" "J" "MR" p1   0.75  0.00 "3018.43")
 (setq p1 (list 213.50 1716.94) p2 (list 214.00 1716.94))
 (command "LINE" p1 p2 "")
 (setq p1 (list 213.13 1716.94) p2 (list 0.00 0.00))
 (command "TEXT" "J" "MR" p1   0.75  0.00 "170.00")
 (setq p1 (list 213.13 1715.82) p2 (list 0.00 0.00))
 (command "TEXT" "J" "MR" p1   0.75  0.00 "3008.43")
 (setq p1 (list 213.50 1706.94) p2 (list 214.00 1706.94))
 (command "LINE" p1 p2 "")
 (setq p1 (list 213.13 1706.94) p2 (list 0.00 0.00))
 (command "TEXT" "J" "MR" p1   0.75  0.00 "180.00")
 (setq p1 (list 213.13 1705.82) p2 (list 0.00 0.00))
 (command "TEXT" "J" "MR" p1   0.75  0.00 "2998.43")
 (setq p1 (list 213.50 1696.94) p2 (list 214.00 1696.94))
 (command "LINE" p1 p2 "")
 (setq p1 (list 213.13 1696.94) p2 (list 0.00 0.00))
 (command "TEXT" "J" "MR" p1   0.75  0.00 "190.00")
 (setq p1 (list 213.13 1695.82) p2 (list 0.00 0.00))
 (command "TEXT" "J" "MR" p1   0.75  0.00 "2988.43")
 (setq p1 (list 213.50 1686.94) p2 (list 214.00 1686.94))
 (command "LINE" p1 p2 "")
 (setq p1 (list 213.13 1686.94) p2 (list 0.00 0.00))
 (command "TEXT" "J" "MR" p1   0.75  0.00 "200.00")
 (setq p1 (list 213.13 1685.82) p2 (list 0.00 0.00))
 (command "TEXT" "J" "MR" p1   0.75  0.00 "2978.43")
 (setq p1 (list 213.50 1676.94) p2 (list 214.00 1676.94))
 (command "LINE" p1 p2 "")
 (setq p1 (list 213.13 1676.94) p2 (list 0.00 0.00))
 (command "TEXT" "J" "MR" p1   0.75  0.00 "210.00")
 (setq p1 (list 213.13 1675.82) p2 (list 0.00 0.00))
 (command "TEXT" "J" "MR" p1   0.75  0.00 "2968.43")
 (setq p1 (list 213.50 1666.94) p2 (list 214.00 1666.94))
 (command "LINE" p1 p2 "")
 (setq p1 (list 213.13 1666.94) p2 (list 0.00 0.00))
 (command "TEXT" "J" "MR" p1   0.75  0.00 "220.00")
 (setq p1 (list 213.13 1665.82) p2 (list 0.00 0.00))
 (command "TEXT" "J" "MR" p1   0.75  0.00 "2958.43")
 (setq p1 (list 213.50 1656.94) p2 (list 214.00 1656.94))
 (command "LINE" p1 p2 "")
 (setq p1 (list 213.13 1656.94) p2 (list 0.00 0.00))
 (command "TEXT" "J" "MR" p1   0.75  0.00 "230.00")
 (setq p1 (list 213.13 1655.82) p2 (list 0.00 0.00))
 (command "TEXT" "J" "MR" p1   0.75  0.00 "2948.43")
 (setq p1 (list 213.50 1646.94) p2 (list 214.00 1646.94))
 (command "LINE" p1 p2 "")
 (setq p1 (list 213.13 1646.94) p2 (list 0.00 0.00))
 (command "TEXT" "J" "MR" p1   0.75  0.00 "240.00")
 (setq p1 (list 213.13 1645.82) p2 (list 0.00 0.00))
 (command "TEXT" "J" "MR" p1   0.75  0.00 "2938.43")
 (setq p1 (list 213.50 1636.94) p2 (list 214.00 1636.94))
 (command "LINE" p1 p2 "")
 (setq p1 (list 213.13 1636.94) p2 (list 0.00 0.00))
 (command "TEXT" "J" "MR" p1   0.75  0.00 "250.00")
 (setq p1 (list 213.13 1635.82) p2 (list 0.00 0.00))
 (command "TEXT" "J" "MR" p1   0.75  0.00 "2928.43")
 (setq p1 (list 213.50 1626.94) p2 (list 214.00 1626.94))
 (command "LINE" p1 p2 "")
 (setq p1 (list 213.13 1626.94) p2 (list 0.00 0.00))
 (command "TEXT" "J" "MR" p1   0.75  0.00 "260.00")
 (setq p1 (list 213.13 1625.82) p2 (list 0.00 0.00))
 (command "TEXT" "J" "MR" p1   0.75  0.00 "2918.43")
 (setq p1 (list 213.50 1616.94) p2 (list 214.00 1616.94))
 (command "LINE" p1 p2 "")
 (setq p1 (list 213.13 1616.94) p2 (list 0.00 0.00))
 (command "TEXT" "J" "MR" p1   0.75  0.00 "270.00")
 (setq p1 (list 213.13 1615.82) p2 (list 0.00 0.00))
 (command "TEXT" "J" "MR" p1   0.75  0.00 "2908.43")
 (setq p1 (list 213.50 1606.94) p2 (list 214.00 1606.94))
 (command "LINE" p1 p2 "")
 (setq p1 (list 213.13 1606.94) p2 (list 0.00 0.00))
 (command "TEXT" "J" "MR" p1   0.75  0.00 "280.00")
 (setq p1 (list 213.13 1605.82) p2 (list 0.00 0.00))
 (command "TEXT" "J" "MR" p1   0.75  0.00 "2898.43")
 (setq p1 (list 213.50 1596.94) p2 (list 214.00 1596.94))
 (command "LINE" p1 p2 "")
 (setq p1 (list 213.13 1596.94) p2 (list 0.00 0.00))
 (command "TEXT" "J" "MR" p1   0.75  0.00 "290.00")
 (setq p1 (list 213.13 1595.82) p2 (list 0.00 0.00))
 (command "TEXT" "J" "MR" p1   0.75  0.00 "2888.43")
 (setq p1 (list 213.50 1586.94) p2 (list 214.00 1586.94))
 (command "LINE" p1 p2 "")
 (setq p1 (list 213.13 1586.94) p2 (list 0.00 0.00))
 (command "TEXT" "J" "MR" p1   0.75  0.00 "300.00")
 (setq p1 (list 213.13 1585.82) p2 (list 0.00 0.00))
 (command "TEXT" "J" "MR" p1   0.75  0.00 "2878.43")
 (setq p1 (list 213.50 1576.94) p2 (list 214.00 1576.94))
 (command "LINE" p1 p2 "")
 (setq p1 (list 213.13 1576.94) p2 (list 0.00 0.00))
 (command "TEXT" "J" "MR" p1   0.75  0.00 "310.00")
 (setq p1 (list 213.13 1575.82) p2 (list 0.00 0.00))
 (command "TEXT" "J" "MR" p1   0.75  0.00 "2868.43")
 (setq p1 (list 213.50 1566.94) p2 (list 214.00 1566.94))
 (command "LINE" p1 p2 "")
 (setq p1 (list 213.13 1566.94) p2 (list 0.00 0.00))
 (command "TEXT" "J" "MR" p1   0.75  0.00 "320.00")
 (setq p1 (list 213.13 1565.82) p2 (list 0.00 0.00))
 (command "TEXT" "J" "MR" p1   0.75  0.00 "2858.43")
 (setq p1 (list 213.50 1556.94) p2 (list 214.00 1556.94))
 (command "LINE" p1 p2 "")
 (setq p1 (list 213.13 1556.94) p2 (list 0.00 0.00))
 (command "TEXT" "J" "MR" p1   0.75  0.00 "330.00")
 (setq p1 (list 213.13 1555.82) p2 (list 0.00 0.00))
 (command "TEXT" "J" "MR" p1   0.75  0.00 "2848.43")
 (setq p1 (list 213.50 1546.94) p2 (list 214.00 1546.94))
 (command "LINE" p1 p2 "")
 (setq p1 (list 213.13 1546.94) p2 (list 0.00 0.00))
 (command "TEXT" "J" "MR" p1   0.75  0.00 "340.00")
 (setq p1 (list 213.13 1545.82) p2 (list 0.00 0.00))
 (command "TEXT" "J" "MR" p1   0.75  0.00 "2838.43")
 (setq p1 (list 213.50 1536.94) p2 (list 214.00 1536.94))
 (command "LINE" p1 p2 "")
 (setq p1 (list 213.13 1536.94) p2 (list 0.00 0.00))
 (command "TEXT" "J" "MR" p1   0.75  0.00 "350.00")
 (setq p1 (list 213.13 1535.82) p2 (list 0.00 0.00))
 (command "TEXT" "J" "MR" p1   0.75  0.00 "2828.43")
 (setq p1 (list 213.50 1526.94) p2 (list 214.00 1526.94))
 (command "LINE" p1 p2 "")
 (setq p1 (list 213.13 1526.94) p2 (list 0.00 0.00))
 (command "TEXT" "J" "MR" p1   0.75  0.00 "360.00")
 (setq p1 (list 213.13 1525.82) p2 (list 0.00 0.00))
 (command "TEXT" "J" "MR" p1   0.75  0.00 "2818.43")
 (setq p1 (list 213.50 1516.94) p2 (list 214.00 1516.94))
 (command "LINE" p1 p2 "")
 (setq p1 (list 213.13 1516.94) p2 (list 0.00 0.00))
 (command "TEXT" "J" "MR" p1   0.75  0.00 "370.00")
 (setq p1 (list 213.13 1515.82) p2 (list 0.00 0.00))
 (command "TEXT" "J" "MR" p1   0.75  0.00 "2808.43")
 (setq p1 (list 213.50 1506.94) p2 (list 214.00 1506.94))
 (command "LINE" p1 p2 "")
 (setq p1 (list 213.13 1506.94) p2 (list 0.00 0.00))
 (command "TEXT" "J" "MR" p1   0.75  0.00 "380.00")
 (setq p1 (list 213.13 1505.82) p2 (list 0.00 0.00))
 (command "TEXT" "J" "MR" p1   0.75  0.00 "2798.43")
 (setq p1 (list 213.50 1496.94) p2 (list 214.00 1496.94))
 (command "LINE" p1 p2 "")
 (setq p1 (list 213.13 1496.94) p2 (list 0.00 0.00))
 (command "TEXT" "J" "MR" p1   0.75  0.00 "390.00")
 (setq p1 (list 213.13 1495.82) p2 (list 0.00 0.00))
 (command "TEXT" "J" "MR" p1   0.75  0.00 "2788.43")
 (setq p1 (list 213.50 1482.29) p2 (list 214.00 1482.29))
 (command "LINE" p1 p2 "")
 (setq p1 (list 213.13 1482.29) p2 (list 0.00 0.00))
 (command "TEXT" "J" "MR" p1   0.75  0.00 "404.65")
 (setq p1 (list 213.13 1481.17) p2 (list 0.00 0.00))
 (command "TEXT" "J" "MR" p1   0.75  0.00 "2773.78")
 (command "LAYER" "S" "CGBHLHDR" "")
 (setq p1 (list 207.00 1898.44) p2 (list 207.00 1888.44) p3 (list 227.00 1888.44) p4 (list 227.00 1898.44))
 (command "LINE" p1 p2 p3 p4 "c")
 (setq p1 (list 207.50 1896.69) p2 (list 0.00 0.00))
 (command "TEXT" "J" "ML" p1   1.13  0.00 "Hole:")
 (setq p1 (list 207.50 1894.44) p2 (list 0.00 0.00))
 (command "TEXT" "J" "ML" p1   0.83  0.00 "Easting:")
 (setq p1 (list 207.50 1892.69) p2 (list 0.00 0.00))
 (command "TEXT" "J" "ML" p1   0.83  0.00 "Northing:")
 (setq p1 (list 207.50 1890.94) p2 (list 0.00 0.00))
 (command "TEXT" "J" "ML" p1   0.83  0.00 "Collar Elev:")
 (setq p1 (list 207.50 1889.19) p2 (list 0.00 0.00))
 (command "TEXT" "J" "ML" p1   0.83  0.00 "Drill Depth:")
 (setq p1 (list 226.50 1896.69) p2 (list 0.00 0.00))
 (command "TEXT" "J" "MR" p1   1.13  0.00 "XY-12")
 (setq p1 (list 226.50 1894.44) p2 (list 0.00 0.00))
 (command "TEXT" "J" "MR" p1   0.83  0.00 "4033076.38")
 (setq p1 (list 226.50 1892.69) p2 (list 0.00 0.00))
 (command "TEXT" "J" "MR" p1   0.83  0.00 "259205.45")
 (setq p1 (list 226.50 1890.94) p2 (list 0.00 0.00))
 (command "TEXT" "J" "MR" p1   0.83  0.00 "3178.43")
 (setq p1 (list 226.50 1889.19) p2 (list 0.00 0.00))
 (command "TEXT" "J" "MR" p1   0.83  0.00 "405.01")
 (setq p1 (list 217.00 1888.44) p2 (list 217.00 1886.94))
 (command "LINE" p1 p2 "")
 (command "LAYER" "S" "CGBMAIN" "")
 (setq p1 (list 321.00 1734.29) p2 (list 327.00 1734.29) p3 (list 327.00 1704.29) p4 (list 321.00 1704.29))
 (command "PLINE" p1 p2 p3 p4 "c")
 (command "LINE" p1 p3 "")
 (command "LINE" p2 p4 "")
 (command "COLOR" "BYLAYER")
 (command "LAYER" "S" "CGBLITHCD" "")
 (setq p1 (list 327.00 1719.29) p2 (list 328.35 1719.29))
 (command "LINE" p1 p2 "")
 (setq p1 (list 328.50 1718.92) p2 (list 0.00 0.00))
 (command "TEXT" "J" "ML" p1   0.75  0.00 "001")
 (command "LAYER" "S" "CGBTHK" "")
 (setq p1 (list 333.00 1718.92) p2 (list 0.00 0.00))
 (command "TEXT" "J" "ML" p1   0.75  0.00 "30.00")
 (command "LAYER" "S" "CGBHZID" "")
 (setq p1 (list 337.50 1718.92) p2 (list 0.00 0.00))
 (command "TEXT" "J" "ML" p1   0.75  0.00 "")
 (setq p1 (list 339.75 1718.92) p2 (list 0.00 0.00))
 (command "TEXT" "J" "ML" p1   0.75  0.00 "9990")
 (command "LAYER" "S" "CGBLITHTXT" "")
 (setq p1 (list 343.50 1718.92) p2 (list 0.00 0.00))
 (command "TEXT" "J" "ML" p1   0.75  0.00 "CASING")
 (command "LAYER" "S" "CGBCMNT" "")
 (setq p1 (list 363.75 1718.92) p2 (list 0.00 0.00))
 (command "TEXT" "J" "ML" p1   0.75  0.00 "")
 (command "LAYER" "S" "CGBMAIN" "")
 (setq p1 (list 321.00 1704.29) p2 (list 327.00 1704.29) p3 (list 327.00 1701.83) p4 (list 321.00 1701.83))
 (command "PLINE" p1 p2 p3 p4 "c")
 (command "HATCH" "ZIGZAG" 4.00 45.00 "L" "")
 (command "COLOR" "BYLAYER")
 (command "LAYER" "S" "CGBLITHCD" "")
 (setq p1 (list 327.00 1703.06) p2 (list 328.35 1703.06))
 (command "LINE" p1 p2 "")
 (setq p1 (list 328.50 1702.69) p2 (list 0.00 0.00))
 (command "TEXT" "J" "ML" p1   0.75  0.00 "120")
 (command "LAYER" "S" "CGBTHK" "")
 (setq p1 (list 333.00 1702.69) p2 (list 0.00 0.00))
 (command "TEXT" "J" "ML" p1   0.75  0.00 "2.46")
 (command "LAYER" "S" "CGBHZID" "")
 (setq p1 (list 337.50 1702.69) p2 (list 0.00 0.00))
 (command "TEXT" "J" "ML" p1   0.75  0.00 "")
 (setq p1 (list 339.75 1702.69) p2 (list 0.00 0.00))
 (command "TEXT" "J" "ML" p1   0.75  0.00 "9990")
 (command "LAYER" "S" "CGBLITHTXT" "")
 (setq p1 (list 343.50 1702.69) p2 (list 0.00 0.00))
 (command "TEXT" "J" "ML" p1   0.75  0.00 "DRK GRY SH (UNDIF)")
 (command "LAYER" "S" "CGBCMNT" "")
 (setq p1 (list 363.75 1702.69) p2 (list 0.00 0.00))
 (command "TEXT" "J" "ML" p1   0.75  0.00 "CASING")
 (command "LAYER" "S" "CGBMAIN" "")
 (setq p1 (list 321.00 1701.83) p2 (list 327.00 1701.83) p3 (list 327.00 1689.89) p4 (list 321.00 1689.89))
 (command "PLINE" p1 p2 p3 p4 "c")
 (command "HATCH" "ZIGZAG" 4.00 0.00 "L" "")
 (command "COLOR" "BYLAYER")
 (command "LAYER" "S" "CGBLITHCD" "")
 (setq p1 (list 327.00 1695.86) p2 (list 328.35 1695.86))
 (command "LINE" p1 p2 "")
 (setq p1 (list 328.50 1695.49) p2 (list 0.00 0.00))
 (command "TEXT" "J" "ML" p1   0.75  0.00 "543")
 (command "LAYER" "S" "CGBTHK" "")
 (setq p1 (list 333.00 1695.49) p2 (list 0.00 0.00))
 (command "TEXT" "J" "ML" p1   0.75  0.00 "11.94")
 (command "LAYER" "S" "CGBHZID" "")
 (setq p1 (list 337.50 1695.49) p2 (list 0.00 0.00))
 (command "TEXT" "J" "ML" p1   0.75  0.00 "")
 (setq p1 (list 339.75 1695.49) p2 (list 0.00 0.00))
 (command "TEXT" "J" "ML" p1   0.75  0.00 "9990")
 (command "LAYER" "S" "CGBLITHTXT" "")
 (setq p1 (list 343.50 1695.49) p2 (list 0.00 0.00))
 (command "TEXT" "J" "ML" p1   0.75  0.00 "GRY SS W/SH STKS")
 (command "LAYER" "S" "CGBCMNT" "")
 (setq p1 (list 363.75 1695.49) p2 (list 0.00 0.00))
 (command "TEXT" "J" "ML" p1   0.75  0.00 "WTHRD BRWN CL")
 (command "LAYER" "S" "CGBMAIN" "")
 (setq p1 (list 321.00 1689.89) p2 (list 327.00 1689.89) p3 (list 327.00 1684.89) p4 (list 321.00 1684.89))
 (command "PLINE" p1 p2 p3 p4 "c")
 (command "HATCH" "ZIGZAG" 4.00 0.00 "L" "")
 (command "COLOR" "BYLAYER")
 (command "LAYER" "S" "CGBLITHCD" "")
 (setq p1 (list 327.00 1687.39) p2 (list 328.35 1687.39))
 (command "LINE" p1 p2 "")
 (setq p1 (list 328.50 1687.02) p2 (list 0.00 0.00))
 (command "TEXT" "J" "ML" p1   0.75  0.00 "543")
 (command "LAYER" "S" "CGBTHK" "")
 (setq p1 (list 333.00 1687.02) p2 (list 0.00 0.00))
 (command "TEXT" "J" "ML" p1   0.75  0.00 "5.00")
 (command "LAYER" "S" "CGBHZID" "")
 (setq p1 (list 337.50 1687.02) p2 (list 0.00 0.00))
 (command "TEXT" "J" "ML" p1   0.75  0.00 "")
 (setq p1 (list 339.75 1687.02) p2 (list 0.00 0.00))
 (command "TEXT" "J" "ML" p1   0.75  0.00 "9990")
 (command "LAYER" "S" "CGBLITHTXT" "")
 (setq p1 (list 343.50 1687.02) p2 (list 0.00 0.00))
 (command "TEXT" "J" "ML" p1   0.75  0.00 "GRY SS W/SH STKS")
 (command "LAYER" "S" "CGBCMNT" "")
 (setq p1 (list 363.75 1687.02) p2 (list 0.00 0.00))
 (command "TEXT" "J" "ML" p1   0.75  0.00 "BADLY FRAC")
 (command "LAYER" "S" "CGBMAIN" "")
 (setq p1 (list 321.00 1684.89) p2 (list 327.00 1684.89) p3 (list 327.00 1680.29) p4 (list 321.00 1680.29))
 (command "PLINE" p1 p2 p3 p4 "c")
 (command "HATCH" "ZIGZAG" 4.00 45.00 "L" "")
 (command "COLOR" "BYLAYER")
 (command "LAYER" "S" "CGBLITHCD" "")
 (setq p1 (list 327.00 1682.59) p2 (list 328.35 1682.59))
 (command "LINE" p1 p2 "")
 (setq p1 (list 328.50 1682.22) p2 (list 0.00 0.00))
 (command "TEXT" "J" "ML" p1   0.75  0.00 "120")
 (command "LAYER" "S" "CGBTHK" "")
 (setq p1 (list 333.00 1682.22) p2 (list 0.00 0.00))
 (command "TEXT" "J" "ML" p1   0.75  0.00 "4.60")
 (command "LAYER" "S" "CGBHZID" "")
 (setq p1 (list 337.50 1682.22) p2 (list 0.00 0.00))
 (command "TEXT" "J" "ML" p1   0.75  0.00 "")
 (setq p1 (list 339.75 1682.22) p2 (list 0.00 0.00))
 (command "TEXT" "J" "ML" p1   0.75  0.00 "9990")
 (command "LAYER" "S" "CGBLITHTXT" "")
 (setq p1 (list 343.50 1682.22) p2 (list 0.00 0.00))
 (command "TEXT" "J" "ML" p1   0.75  0.00 "DRK GRY SH (UNDIF)")
 (command "LAYER" "S" "CGBCMNT" "")
 (setq p1 (list 363.75 1682.22) p2 (list 0.00 0.00))
 (command "TEXT" "J" "ML" p1   0.75  0.00 "AS ABOVE")
 (command "LAYER" "S" "CGBMAIN" "")
 (setq p1 (list 321.00 1680.29) p2 (list 327.00 1680.29) p3 (list 327.00 1676.14) p4 (list 321.00 1676.14))
 (command "PLINE" p1 p2 p3 p4 "c")
 (command "HATCH" "ZIGZAG" 4.00 0.00 "L" "")
 (command "COLOR" "BYLAYER")
 (command "LAYER" "S" "CGBLITHCD" "")
 (setq p1 (list 327.00 1678.22) p2 (list 328.35 1678.22))
 (command "LINE" p1 p2 "")
 (setq p1 (list 328.50 1677.84) p2 (list 0.00 0.00))
 (command "TEXT" "J" "ML" p1   0.75  0.00 "124")
 (command "LAYER" "S" "CGBTHK" "")
 (setq p1 (list 333.00 1677.84) p2 (list 0.00 0.00))
 (command "TEXT" "J" "ML" p1   0.75  0.00 "4.15")
 (command "LAYER" "S" "CGBHZID" "")
 (setq p1 (list 337.50 1677.84) p2 (list 0.00 0.00))
 (command "TEXT" "J" "ML" p1   0.75  0.00 "")
 (setq p1 (list 339.75 1677.84) p2 (list 0.00 0.00))
 (command "TEXT" "J" "ML" p1   0.75  0.00 "9990")
 (command "LAYER" "S" "CGBLITHTXT" "")
 (setq p1 (list 343.50 1677.84) p2 (list 0.00 0.00))
 (command "TEXT" "J" "ML" p1   0.75  0.00 "DRK GRY SH")
 (command "LAYER" "S" "CGBCMNT" "")
 (setq p1 (list 363.75 1677.84) p2 (list 0.00 0.00))
 (command "TEXT" "J" "ML" p1   0.75  0.00 "SFT, BADLY BR")
 (command "LAYER" "S" "CGBMAIN" "")
 (setq p1 (list 321.00 1676.14) p2 (list 327.00 1676.14) p3 (list 327.00 1671.29) p4 (list 321.00 1671.29))
 (command "PLINE" p1 p2 p3 p4 "c")
 (command "HATCH" "ZIGZAG" 3.00 0.00 "L" "")
 (command "COLOR" "BYLAYER")
 (command "LAYER" "S" "CGBLITHCD" "")
 (setq p1 (list 327.00 1673.72) p2 (list 328.35 1673.72))
 (command "LINE" p1 p2 "")
 (setq p1 (list 328.50 1673.34) p2 (list 0.00 0.00))
 (command "TEXT" "J" "ML" p1   0.75  0.00 "157")
 (command "LAYER" "S" "CGBTHK" "")
 (setq p1 (list 333.00 1673.34) p2 (list 0.00 0.00))
 (command "TEXT" "J" "ML" p1   0.75  0.00 "4.85")
 (command "LAYER" "S" "CGBHZID" "")
 (setq p1 (list 337.50 1673.34) p2 (list 0.00 0.00))
 (command "TEXT" "J" "ML" p1   0.75  0.00 "")
 (setq p1 (list 339.75 1673.34) p2 (list 0.00 0.00))
 (command "TEXT" "J" "ML" p1   0.75  0.00 "9990")
 (command "LAYER" "S" "CGBLITHTXT" "")
 (setq p1 (list 343.50 1673.34) p2 (list 0.00 0.00))
 (command "TEXT" "J" "ML" p1   0.75  0.00 "RED+GRN CLYSTN")
 (command "LAYER" "S" "CGBCMNT" "")
 (setq p1 (list 363.75 1673.34) p2 (list 0.00 0.00))
 (command "TEXT" "J" "ML" p1   0.75  0.00 "BRKN-CRMB")
 (command "LAYER" "S" "CGBMAIN" "")
 (setq p1 (list 321.00 1671.29) p2 (list 327.00 1671.29) p3 (list 327.00 1671.17) p4 (list 321.00 1671.17))
 (command "PLINE" p1 p2 p3 p4 "c")
 (command "HATCH" "ZIGZAG" 4.00 0.00 "L" "")
 (command "COLOR" "BYLAYER")
 (command "LAYER" "S" "CGBLITHCD" "")
 (setq p1 (list 327.00 1671.23) p2 (list 328.35 1671.23))
 (command "LINE" p1 p2 "")
 (setq p1 (list 328.50 1670.86) p2 (list 0.00 0.00))
 (command "TEXT" "J" "ML" p1   0.75  0.00 "424")
 (command "LAYER" "S" "CGBTHK" "")
 (setq p1 (list 333.00 1670.86) p2 (list 0.00 0.00))
 (command "TEXT" "J" "ML" p1   0.75  0.00 "0.12")
 (command "LAYER" "S" "CGBHZID" "")
 (setq p1 (list 337.50 1670.86) p2 (list 0.00 0.00))
 (command "TEXT" "J" "ML" p1   0.75  0.00 "")
 (setq p1 (list 339.75 1670.86) p2 (list 0.00 0.00))
 (command "TEXT" "J" "ML" p1   0.75  0.00 "9990")
 (command "LAYER" "S" "CGBLITHTXT" "")
 (setq p1 (list 343.50 1670.86) p2 (list 0.00 0.00))
 (command "TEXT" "J" "ML" p1   0.75  0.00 "DRK GRY SDY SH W/LS NODS")
 (command "LAYER" "S" "CGBCMNT" "")
 (setq p1 (list 363.75 1670.86) p2 (list 0.00 0.00))
 (command "TEXT" "J" "ML" p1   0.75  0.00 "V SFT, WTHRD")
 (command "LAYER" "S" "CGBMAIN" "")
 (setq p1 (list 321.00 1671.17) p2 (list 327.00 1671.17) p3 (list 327.00 1669.62) p4 (list 321.00 1669.62))
 (command "PLINE" p1 p2 p3 p4 "c")
 (command "HATCH" "ZIGZAG" 4.00 0.00 "L" "")
 (command "COLOR" "BYLAYER")
 (command "LAYER" "S" "CGBLITHCD" "")
 (setq p1 (list 327.00 1670.40) p2 (list 328.35 1669.15))
 (command "LINE" p1 p2 "")
 (setq p1 (list 328.50 1668.77) p2 (list 0.00 0.00))
 (command "TEXT" "J" "ML" p1   0.75  0.00 "124")
 (command "LAYER" "S" "CGBTHK" "")
 (setq p1 (list 333.00 1668.77) p2 (list 0.00 0.00))
 (command "TEXT" "J" "ML" p1   0.75  0.00 "1.55")
 (command "LAYER" "S" "CGBHZID" "")
 (setq p1 (list 337.50 1668.77) p2 (list 0.00 0.00))
 (command "TEXT" "J" "ML" p1   0.75  0.00 "")
 (setq p1 (list 339.75 1668.77) p2 (list 0.00 0.00))
 (command "TEXT" "J" "ML" p1   0.75  0.00 "9990")
 (command "LAYER" "S" "CGBLITHTXT" "")
 (setq p1 (list 343.50 1668.77) p2 (list 0.00 0.00))
 (command "TEXT" "J" "ML" p1   0.75  0.00 "DRK GRY SH")
 (command "LAYER" "S" "CGBCMNT" "")
 (setq p1 (list 363.75 1668.77) p2 (list 0.00 0.00))
 (command "TEXT" "J" "ML" p1   0.75  0.00 "SFT,DRK,SLC")
 (command "LAYER" "S" "CGBMAIN" "")
 (setq p1 (list 321.00 1669.62) p2 (list 327.00 1669.62) p3 (list 327.00 1663.98) p4 (list 321.00 1663.98))
 (command "PLINE" p1 p2 p3 p4 "c")
 (command "HATCH" "ZIGZAG" 4.00 0.00 "L" "")
 (command "COLOR" "BYLAYER")
 (command "LAYER" "S" "CGBLITHCD" "")
 (setq p1 (list 327.00 1666.80) p2 (list 328.35 1666.80))
 (command "LINE" p1 p2 "")
 (setq p1 (list 328.50 1666.43) p2 (list 0.00 0.00))
 (command "TEXT" "J" "ML" p1   0.75  0.00 "541")
 (command "LAYER" "S" "CGBTHK" "")
 (setq p1 (list 333.00 1666.43) p2 (list 0.00 0.00))
 (command "TEXT" "J" "ML" p1   0.75  0.00 "5.64")
 (command "LAYER" "S" "CGBHZID" "")
 (setq p1 (list 337.50 1666.43) p2 (list 0.00 0.00))
 (command "TEXT" "J" "ML" p1   0.75  0.00 "")
 (setq p1 (list 339.75 1666.43) p2 (list 0.00 0.00))
 (command "TEXT" "J" "ML" p1   0.75  0.00 "9990")
 (command "LAYER" "S" "CGBLITHTXT" "")
 (setq p1 (list 343.50 1666.43) p2 (list 0.00 0.00))
 (command "TEXT" "J" "ML" p1   0.75  0.00 "GRY CROSSBED SS")
 (command "LAYER" "S" "CGBCMNT" "")
 (setq p1 (list 363.75 1666.43) p2 (list 0.00 0.00))
 (command "TEXT" "J" "ML" p1   0.75  0.00 "VERT FRACS, G")
 (command "LAYER" "S" "CGBMAIN" "")
 (setq p1 (list 321.00 1663.98) p2 (list 327.00 1663.98) p3 (list 327.00 1662.69) p4 (list 321.00 1662.69))
 (command "PLINE" p1 p2 p3 p4 "c")
 (command "HATCH" "ZIGZAG" 4.00 0.00 "L" "")
 (command "COLOR" "BYLAYER")
 (command "LAYER" "S" "CGBLITHCD" "")
 (setq p1 (list 327.00 1663.34) p2 (list 328.35 1663.34))
 (command "LINE" p1 p2 "")
 (setq p1 (list 328.50 1662.96) p2 (list 0.00 0.00))
 (command "TEXT" "J" "ML" p1   0.75  0.00 "374")
 (command "LAYER" "S" "CGBTHK" "")
 (setq p1 (list 333.00 1662.96) p2 (list 0.00 0.00))
 (command "TEXT" "J" "ML" p1   0.75  0.00 "1.29")
 (command "LAYER" "S" "CGBHZID" "")
 (setq p1 (list 337.50 1662.96) p2 (list 0.00 0.00))
 (command "TEXT" "J" "ML" p1   0.75  0.00 "")
 (setq p1 (list 339.75 1662.96) p2 (list 0.00 0.00))
 (command "TEXT" "J" "ML" p1   0.75  0.00 "9990")
 (command "LAYER" "S" "CGBLITHTXT" "")
 (setq p1 (list 343.50 1662.96) p2 (list 0.00 0.00))
 (command "TEXT" "J" "ML" p1   0.75  0.00 "GRY/GRN SDY SH")
 (command "LAYER" "S" "CGBCMNT" "")
 (setq p1 (list 363.75 1662.96) p2 (list 0.00 0.00))
 (command "TEXT" "J" "ML" p1   0.75  0.00 "")
 (command "LAYER" "S" "CGBMAIN" "")
 (setq p1 (list 321.00 1662.69) p2 (list 327.00 1662.69) p3 (list 327.00 1661.23) p4 (list 321.00 1661.23))
 (command "PLINE" p1 p2 p3 p4 "c")
 (command "HATCH" "ZIGZAG" 4.00 0.00 "L" "")
 (command "COLOR" "BYLAYER")
 (command "LAYER" "S" "CGBLITHCD" "")
 (setq p1 (list 327.00 1661.96) p2 (list 328.35 1661.96))
 (command "LINE" p1 p2 "")
 (setq p1 (list 328.50 1661.59) p2 (list 0.00 0.00))
 (command "TEXT" "J" "ML" p1   0.75  0.00 "374")
 (command "LAYER" "S" "CGBTHK" "")
 (setq p1 (list 333.00 1661.59) p2 (list 0.00 0.00))
 (command "TEXT" "J" "ML" p1   0.75  0.00 "1.46")
 (command "LAYER" "S" "CGBHZID" "")
 (setq p1 (list 337.50 1661.59) p2 (list 0.00 0.00))
 (command "TEXT" "J" "ML" p1   0.75  0.00 "")
 (setq p1 (list 339.75 1661.59) p2 (list 0.00 0.00))
 (command "TEXT" "J" "ML" p1   0.75  0.00 "9990")
 (command "LAYER" "S" "CGBLITHTXT" "")
 (setq p1 (list 343.50 1661.59) p2 (list 0.00 0.00))
 (command "TEXT" "J" "ML" p1   0.75  0.00 "GRY/GRN SDY SH")
 (command "LAYER" "S" "CGBCMNT" "")
 (setq p1 (list 363.75 1661.59) p2 (list 0.00 0.00))
 (command "TEXT" "J" "ML" p1   0.75  0.00 "BRKN, FRACS")
 (command "LAYER" "S" "CGBMAIN" "")
 (setq p1 (list 321.00 1661.23) p2 (list 327.00 1661.23) p3 (list 327.00 1660.01) p4 (list 321.00 1660.01))
 (command "PLINE" p1 p2 p3 p4 "c")
 (command "HATCH" "ZIGZAG" 4.00 0.00 "L" "")
 (command "COLOR" "BYLAYER")
 (command "LAYER" "S" "CGBLITHCD" "")
 (setq p1 (list 327.00 1660.62) p2 (list 328.35 1660.62))
 (command "LINE" p1 p2 "")
 (setq p1 (list 328.50 1660.25) p2 (list 0.00 0.00))
 (command "TEXT" "J" "ML" p1   0.75  0.00 "544")
 (command "LAYER" "S" "CGBTHK" "")
 (setq p1 (list 333.00 1660.25) p2 (list 0.00 0.00))
 (command "TEXT" "J" "ML" p1   0.75  0.00 "1.22")
 (command "LAYER" "S" "CGBHZID" "")
 (setq p1 (list 337.50 1660.25) p2 (list 0.00 0.00))
 (command "TEXT" "J" "ML" p1   0.75  0.00 "")
 (setq p1 (list 339.75 1660.25) p2 (list 0.00 0.00))
 (command "TEXT" "J" "ML" p1   0.75  0.00 "9990")
 (command "LAYER" "S" "CGBLITHTXT" "")
 (setq p1 (list 343.50 1660.25) p2 (list 0.00 0.00))
 (command "TEXT" "J" "ML" p1   0.75  0.00 "GRY MASS SS")
 (command "LAYER" "S" "CGBCMNT" "")
 (setq p1 (list 363.75 1660.25) p2 (list 0.00 0.00))
 (command "TEXT" "J" "ML" p1   0.75  0.00 "SLC")
 (command "LAYER" "S" "CGBMAIN" "")
 (setq p1 (list 321.00 1660.01) p2 (list 327.00 1660.01) p3 (list 327.00 1658.32) p4 (list 321.00 1658.32))
 (command "PLINE" p1 p2 p3 p4 "c")
 (command "HATCH" "ZIGZAG" 2.50 90.00 "L" "")
 (command "COLOR" "BYLAYER")
 (command "LAYER" "S" "CGBLITHCD" "")
 (setq p1 (list 327.00 1659.17) p2 (list 328.35 1659.17))
 (command "LINE" p1 p2 "")
 (setq p1 (list 328.50 1658.79) p2 (list 0.00 0.00))
 (command "TEXT" "J" "ML" p1   0.75  0.00 "324")
 (command "LAYER" "S" "CGBTHK" "")
 (setq p1 (list 333.00 1658.79) p2 (list 0.00 0.00))
 (command "TEXT" "J" "ML" p1   0.75  0.00 "1.69")
 (command "LAYER" "S" "CGBHZID" "")
 (setq p1 (list 337.50 1658.79) p2 (list 0.00 0.00))
 (command "TEXT" "J" "ML" p1   0.75  0.00 "")
 (setq p1 (list 339.75 1658.79) p2 (list 0.00 0.00))
 (command "TEXT" "J" "ML" p1   0.75  0.00 "9990")
 (command "LAYER" "S" "CGBLITHTXT" "")
 (setq p1 (list 343.50 1658.79) p2 (list 0.00 0.00))
 (command "TEXT" "J" "ML" p1   0.75  0.00 "DRK GRY MASS SDY SH")
 (command "LAYER" "S" "CGBCMNT" "")
 (setq p1 (list 363.75 1658.79) p2 (list 0.00 0.00))
 (command "TEXT" "J" "ML" p1   0.75  0.00 "GB")
 (command "LAYER" "S" "CGBMAIN" "")
 (setq p1 (list 321.00 1658.32) p2 (list 327.00 1658.32) p3 (list 327.00 1654.38) p4 (list 321.00 1654.38))
 (command "PLINE" p1 p2 p3 p4 "c")
 (command "HATCH" "ZIGZAG" 5.00 0.00 "L" "")
 (command "COLOR" "BYLAYER")
 (command "LAYER" "S" "CGBLITHCD" "")
 (setq p1 (list 327.00 1656.35) p2 (list 328.35 1656.35))
 (command "LINE" p1 p2 "")
 (setq p1 (list 328.50 1655.98) p2 (list 0.00 0.00))
 (command "TEXT" "J" "ML" p1   0.75  0.00 "322")
 (command "LAYER" "S" "CGBTHK" "")
 (setq p1 (list 333.00 1655.98) p2 (list 0.00 0.00))
 (command "TEXT" "J" "ML" p1   0.75  0.00 "3.94")
 (command "LAYER" "S" "CGBHZID" "")
 (setq p1 (list 337.50 1655.98) p2 (list 0.00 0.00))
 (command "TEXT" "J" "ML" p1   0.75  0.00 "")
 (setq p1 (list 339.75 1655.98) p2 (list 0.00 0.00))
 (command "TEXT" "J" "ML" p1   0.75  0.00 "9990")
 (command "LAYER" "S" "CGBLITHTXT" "")
 (setq p1 (list 343.50 1655.98) p2 (list 0.00 0.00))
 (command "TEXT" "J" "ML" p1   0.75  0.00 "DRK GRY SH+INTERBED SS")
 (command "LAYER" "S" "CGBCMNT" "")
 (setq p1 (list 363.75 1655.98) p2 (list 0.00 0.00))
 (command "TEXT" "J" "ML" p1   0.75  0.00 "")
 (command "LAYER" "S" "CGBMAIN" "")
 (setq p1 (list 321.00 1654.38) p2 (list 327.00 1654.38) p3 (list 327.00 1652.45) p4 (list 321.00 1652.45))
 (command "PLINE" p1 p2 p3 p4 "c")
 (command "HATCH" "ZIGZAG" 4.00 0.00 "L" "")
 (command "COLOR" "BYLAYER")
 (command "LAYER" "S" "CGBLITHCD" "")
 (setq p1 (list 327.00 1653.42) p2 (list 328.35 1653.42))
 (command "LINE" p1 p2 "")
 (setq p1 (list 328.50 1653.04) p2 (list 0.00 0.00))
 (command "TEXT" "J" "ML" p1   0.75  0.00 "543")
 (command "LAYER" "S" "CGBTHK" "")
 (setq p1 (list 333.00 1653.04) p2 (list 0.00 0.00))
 (command "TEXT" "J" "ML" p1   0.75  0.00 "1.93")
 (command "LAYER" "S" "CGBHZID" "")
 (setq p1 (list 337.50 1653.04) p2 (list 0.00 0.00))
 (command "TEXT" "J" "ML" p1   0.75  0.00 "")
 (setq p1 (list 339.75 1653.04) p2 (list 0.00 0.00))
 (command "TEXT" "J" "ML" p1   0.75  0.00 "9990")
 (command "LAYER" "S" "CGBLITHTXT" "")
 (setq p1 (list 343.50 1653.04) p2 (list 0.00 0.00))
 (command "TEXT" "J" "ML" p1   0.75  0.00 "GRY SS W/SH STKS")
 (command "LAYER" "S" "CGBCMNT" "")
 (setq p1 (list 363.75 1653.04) p2 (list 0.00 0.00))
 (command "TEXT" "J" "ML" p1   0.75  0.00 "SLC")
 (command "LAYER" "S" "CGBMAIN" "")
 (setq p1 (list 321.00 1652.45) p2 (list 327.00 1652.45) p3 (list 327.00 1647.94) p4 (list 321.00 1647.94))
 (command "PLINE" p1 p2 p3 p4 "c")
 (command "HATCH" "ZIGZAG" 5.00 0.00 "L" "")
 (command "COLOR" "BYLAYER")
 (command "LAYER" "S" "CGBLITHCD" "")
 (setq p1 (list 327.00 1650.20) p2 (list 328.35 1650.20))
 (command "LINE" p1 p2 "")
 (setq p1 (list 328.50 1649.82) p2 (list 0.00 0.00))
 (command "TEXT" "J" "ML" p1   0.75  0.00 "322")
 (command "LAYER" "S" "CGBTHK" "")
 (setq p1 (list 333.00 1649.82) p2 (list 0.00 0.00))
 (command "TEXT" "J" "ML" p1   0.75  0.00 "4.51")
 (command "LAYER" "S" "CGBHZID" "")
 (setq p1 (list 337.50 1649.82) p2 (list 0.00 0.00))
 (command "TEXT" "J" "ML" p1   0.75  0.00 "")
 (setq p1 (list 339.75 1649.82) p2 (list 0.00 0.00))
 (command "TEXT" "J" "ML" p1   0.75  0.00 "9990")
 (command "LAYER" "S" "CGBLITHTXT" "")
 (setq p1 (list 343.50 1649.82) p2 (list 0.00 0.00))
 (command "TEXT" "J" "ML" p1   0.75  0.00 "DRK GRY SH+INTERBED SS")
 (command "LAYER" "S" "CGBCMNT" "")
 (setq p1 (list 363.75 1649.82) p2 (list 0.00 0.00))
 (command "TEXT" "J" "ML" p1   0.75  0.00 "FNS DWN")
 (command "LAYER" "S" "CGBMAIN" "")
 (setq p1 (list 321.00 1647.94) p2 (list 327.00 1647.94) p3 (list 327.00 1644.35) p4 (list 321.00 1644.35))
 (command "PLINE" p1 p2 p3 p4 "c")
 (command "HATCH" "ZIGZAG" 2.50 90.00 "L" "")
 (command "COLOR" "BYLAYER")
 (command "LAYER" "S" "CGBLITHCD" "")
 (setq p1 (list 327.00 1646.15) p2 (list 328.35 1646.15))
 (command "LINE" p1 p2 "")
 (setq p1 (list 328.50 1645.77) p2 (list 0.00 0.00))
 (command "TEXT" "J" "ML" p1   0.75  0.00 "324")
 (command "LAYER" "S" "CGBTHK" "")
 (setq p1 (list 333.00 1645.77) p2 (list 0.00 0.00))
 (command "TEXT" "J" "ML" p1   0.75  0.00 "3.59")
 (command "LAYER" "S" "CGBHZID" "")
 (setq p1 (list 337.50 1645.77) p2 (list 0.00 0.00))
 (command "TEXT" "J" "ML" p1   0.75  0.00 "")
 (setq p1 (list 339.75 1645.77) p2 (list 0.00 0.00))
 (command "TEXT" "J" "ML" p1   0.75  0.00 "9990")
 (command "LAYER" "S" "CGBLITHTXT" "")
 (setq p1 (list 343.50 1645.77) p2 (list 0.00 0.00))
 (command "TEXT" "J" "ML" p1   0.75  0.00 "DRK GRY MASS SDY SH")
 (command "LAYER" "S" "CGBCMNT" "")
 (setq p1 (list 363.75 1645.77) p2 (list 0.00 0.00))
 (command "TEXT" "J" "ML" p1   0.75  0.00 "VERT FRAC @ 7")
 (command "LAYER" "S" "CGBMAIN" "")
 (setq p1 (list 321.00 1644.35) p2 (list 327.00 1644.35) p3 (list 327.00 1642.73) p4 (list 321.00 1642.73))
 (command "PLINE" p1 p2 p3 p4 "c")
 (command "HATCH" "ZIGZAG" 2.50 90.00 "L" "")
 (command "COLOR" "BYLAYER")
 (command "LAYER" "S" "CGBLITHCD" "")
 (setq p1 (list 327.00 1643.54) p2 (list 328.35 1643.54))
 (command "LINE" p1 p2 "")
 (setq p1 (list 328.50 1643.17) p2 (list 0.00 0.00))
 (command "TEXT" "J" "ML" p1   0.75  0.00 "324")
 (command "LAYER" "S" "CGBTHK" "")
 (setq p1 (list 333.00 1643.17) p2 (list 0.00 0.00))
 (command "TEXT" "J" "ML" p1   0.75  0.00 "1.62")
 (command "LAYER" "S" "CGBHZID" "")
 (setq p1 (list 337.50 1643.17) p2 (list 0.00 0.00))
 (command "TEXT" "J" "ML" p1   0.75  0.00 "")
 (setq p1 (list 339.75 1643.17) p2 (list 0.00 0.00))
 (command "TEXT" "J" "ML" p1   0.75  0.00 "9990")
 (command "LAYER" "S" "CGBLITHTXT" "")
 (setq p1 (list 343.50 1643.17) p2 (list 0.00 0.00))
 (command "TEXT" "J" "ML" p1   0.75  0.00 "DRK GRY MASS SDY SH")
 (command "LAYER" "S" "CGBCMNT" "")
 (setq p1 (list 363.75 1643.17) p2 (list 0.00 0.00))
 (command "TEXT" "J" "ML" p1   0.75  0.00 "FE STN, FRAC")
 (command "LAYER" "S" "CGBMAIN" "")
 (setq p1 (list 321.00 1642.73) p2 (list 327.00 1642.73) p3 (list 327.00 1638.59) p4 (list 321.00 1638.59))
 (command "PLINE" p1 p2 p3 p4 "c")
 (command "HATCH" "ZIGZAG" 4.00 0.00 "L" "")
 (command "COLOR" "BYLAYER")
 (command "LAYER" "S" "CGBLITHCD" "")
 (setq p1 (list 327.00 1640.66) p2 (list 328.35 1640.66))
 (command "LINE" p1 p2 "")
 (setq p1 (list 328.50 1640.29) p2 (list 0.00 0.00))
 (command "TEXT" "J" "ML" p1   0.75  0.00 "124")
 (command "LAYER" "S" "CGBTHK" "")
 (setq p1 (list 333.00 1640.29) p2 (list 0.00 0.00))
 (command "TEXT" "J" "ML" p1   0.75  0.00 "4.14")
 (command "LAYER" "S" "CGBHZID" "")
 (setq p1 (list 337.50 1640.29) p2 (list 0.00 0.00))
 (command "TEXT" "J" "ML" p1   0.75  0.00 "")
 (setq p1 (list 339.75 1640.29) p2 (list 0.00 0.00))
 (command "TEXT" "J" "ML" p1   0.75  0.00 "9990")
 (command "LAYER" "S" "CGBLITHTXT" "")
 (setq p1 (list 343.50 1640.29) p2 (list 0.00 0.00))
 (command "TEXT" "J" "ML" p1   0.75  0.00 "DRK GRY SH")
 (command "LAYER" "S" "CGBCMNT" "")
 (setq p1 (list 363.75 1640.29) p2 (list 0.00 0.00))
 (command "TEXT" "J" "ML" p1   0.75  0.00 "GB")
 (command "LAYER" "S" "CGBMAIN" "")
 (setq p1 (list 321.00 1638.59) p2 (list 327.00 1638.59) p3 (list 327.00 1634.63) p4 (list 321.00 1634.63))
 (command "PLINE" p1 p2 p3 p4 "c")
 (command "HATCH" "ZIGZAG" 2.50 90.00 "L" "")
 (command "COLOR" "BYLAYER")
 (command "LAYER" "S" "CGBLITHCD" "")
 (setq p1 (list 327.00 1636.61) p2 (list 328.35 1636.61))
 (command "LINE" p1 p2 "")
 (setq p1 (list 328.50 1636.24) p2 (list 0.00 0.00))
 (command "TEXT" "J" "ML" p1   0.75  0.00 "324")
 (command "LAYER" "S" "CGBTHK" "")
 (setq p1 (list 333.00 1636.24) p2 (list 0.00 0.00))
 (command "TEXT" "J" "ML" p1   0.75  0.00 "3.96")
 (command "LAYER" "S" "CGBHZID" "")
 (setq p1 (list 337.50 1636.24) p2 (list 0.00 0.00))
 (command "TEXT" "J" "ML" p1   0.75  0.00 "")
 (setq p1 (list 339.75 1636.24) p2 (list 0.00 0.00))
 (command "TEXT" "J" "ML" p1   0.75  0.00 "9990")
 (command "LAYER" "S" "CGBLITHTXT" "")
 (setq p1 (list 343.50 1636.24) p2 (list 0.00 0.00))
 (command "TEXT" "J" "ML" p1   0.75  0.00 "DRK GRY MASS SDY SH")
 (command "LAYER" "S" "CGBCMNT" "")
 (setq p1 (list 363.75 1636.24) p2 (list 0.00 0.00))
 (command "TEXT" "J" "ML" p1   0.75  0.00 "GB")
 (command "LAYER" "S" "CGBMAIN" "")
 (setq p1 (list 321.00 1634.63) p2 (list 327.00 1634.63) p3 (list 327.00 1632.04) p4 (list 321.00 1632.04))
 (command "PLINE" p1 p2 p3 p4 "c")
 (command "HATCH" "ZIGZAG" 4.00 0.00 "L" "")
 (command "COLOR" "BYLAYER")
 (command "LAYER" "S" "CGBLITHCD" "")
 (setq p1 (list 327.00 1633.34) p2 (list 328.35 1633.34))
 (command "LINE" p1 p2 "")
 (setq p1 (list 328.50 1632.96) p2 (list 0.00 0.00))
 (command "TEXT" "J" "ML" p1   0.75  0.00 "543")
 (command "LAYER" "S" "CGBTHK" "")
 (setq p1 (list 333.00 1632.96) p2 (list 0.00 0.00))
 (command "TEXT" "J" "ML" p1   0.75  0.00 "2.59")
 (command "LAYER" "S" "CGBHZID" "")
 (setq p1 (list 337.50 1632.96) p2 (list 0.00 0.00))
 (command "TEXT" "J" "ML" p1   0.75  0.00 "")
 (setq p1 (list 339.75 1632.96) p2 (list 0.00 0.00))
 (command "TEXT" "J" "ML" p1   0.75  0.00 "9990")
 (command "LAYER" "S" "CGBLITHTXT" "")
 (setq p1 (list 343.50 1632.96) p2 (list 0.00 0.00))
 (command "TEXT" "J" "ML" p1   0.75  0.00 "GRY SS W/SH STKS")
 (command "LAYER" "S" "CGBCMNT" "")
 (setq p1 (list 363.75 1632.96) p2 (list 0.00 0.00))
 (command "TEXT" "J" "ML" p1   0.75  0.00 "GB")
 (command "LAYER" "S" "CGBMAIN" "")
 (setq p1 (list 321.00 1632.04) p2 (list 327.00 1632.04) p3 (list 327.00 1628.45) p4 (list 321.00 1628.45))
 (command "PLINE" p1 p2 p3 p4 "c")
 (command "HATCH" "ZIGZAG" 5.00 0.00 "L" "")
 (command "COLOR" "BYLAYER")
 (command "LAYER" "S" "CGBLITHCD" "")
 (setq p1 (list 327.00 1630.25) p2 (list 328.35 1630.25))
 (command "LINE" p1 p2 "")
 (setq p1 (list 328.50 1629.87) p2 (list 0.00 0.00))
 (command "TEXT" "J" "ML" p1   0.75  0.00 "224")
 (command "LAYER" "S" "CGBTHK" "")
 (setq p1 (list 333.00 1629.87) p2 (list 0.00 0.00))
 (command "TEXT" "J" "ML" p1   0.75  0.00 "3.59")
 (command "LAYER" "S" "CGBHZID" "")
 (setq p1 (list 337.50 1629.87) p2 (list 0.00 0.00))
 (command "TEXT" "J" "ML" p1   0.75  0.00 "")
 (setq p1 (list 339.75 1629.87) p2 (list 0.00 0.00))
 (command "TEXT" "J" "ML" p1   0.75  0.00 "9990")
 (command "LAYER" "S" "CGBLITHTXT" "")
 (setq p1 (list 343.50 1629.87) p2 (list 0.00 0.00))
 (command "TEXT" "J" "ML" p1   0.75  0.00 "DRK GRY SH W/LS NODS")
 (command "LAYER" "S" "CGBCMNT" "")
 (setq p1 (list 363.75 1629.87) p2 (list 0.00 0.00))
 (command "TEXT" "J" "ML" p1   0.75  0.00 "")
 (command "LAYER" "S" "CGBMAIN" "")
 (setq p1 (list 321.00 1628.45) p2 (list 327.00 1628.45) p3 (list 327.00 1625.23) p4 (list 321.00 1625.23))
 (command "PLINE" p1 p2 p3 p4 "c")
 (command "HATCH" "ZIGZAG" 4.00 0.00 "L" "")
 (command "COLOR" "BYLAYER")
 (command "LAYER" "S" "CGBLITHCD" "")
 (setq p1 (list 327.00 1626.84) p2 (list 328.35 1626.84))
 (command "LINE" p1 p2 "")
 (setq p1 (list 328.50 1626.47) p2 (list 0.00 0.00))
 (command "TEXT" "J" "ML" p1   0.75  0.00 "424")
 (command "LAYER" "S" "CGBTHK" "")
 (setq p1 (list 333.00 1626.47) p2 (list 0.00 0.00))
 (command "TEXT" "J" "ML" p1   0.75  0.00 "3.22")
 (command "LAYER" "S" "CGBHZID" "")
 (setq p1 (list 337.50 1626.47) p2 (list 0.00 0.00))
 (command "TEXT" "J" "ML" p1   0.75  0.00 "")
 (setq p1 (list 339.75 1626.47) p2 (list 0.00 0.00))
 (command "TEXT" "J" "ML" p1   0.75  0.00 "9990")
 (command "LAYER" "S" "CGBLITHTXT" "")
 (setq p1 (list 343.50 1626.47) p2 (list 0.00 0.00))
 (command "TEXT" "J" "ML" p1   0.75  0.00 "DRK GRY SDY SH W/LS NODS")
 (command "LAYER" "S" "CGBCMNT" "")
 (setq p1 (list 363.75 1626.47) p2 (list 0.00 0.00))
 (command "TEXT" "J" "ML" p1   0.75  0.00 "")
 (command "LAYER" "S" "CGBMAIN" "")
 (setq p1 (list 321.00 1625.23) p2 (list 327.00 1625.23) p3 (list 327.00 1624.43) p4 (list 321.00 1624.43))
 (command "PLINE" p1 p2 p3 p4 "c")
 (command "HATCH" "ZIGZAG" 4.00 0.00 "L" "")
 (command "COLOR" "BYLAYER")
 (command "LAYER" "S" "CGBLITHCD" "")
 (setq p1 (list 327.00 1624.83) p2 (list 328.35 1624.83))
 (command "LINE" p1 p2 "")
 (setq p1 (list 328.50 1624.46) p2 (list 0.00 0.00))
 (command "TEXT" "J" "ML" p1   0.75  0.00 "124")
 (command "LAYER" "S" "CGBTHK" "")
 (setq p1 (list 333.00 1624.46) p2 (list 0.00 0.00))
 (command "TEXT" "J" "ML" p1   0.75  0.00 "0.80")
 (command "LAYER" "S" "CGBHZID" "")
 (setq p1 (list 337.50 1624.46) p2 (list 0.00 0.00))
 (command "TEXT" "J" "ML" p1   0.75  0.00 "")
 (setq p1 (list 339.75 1624.46) p2 (list 0.00 0.00))
 (command "TEXT" "J" "ML" p1   0.75  0.00 "9990")
 (command "LAYER" "S" "CGBLITHTXT" "")
 (setq p1 (list 343.50 1624.46) p2 (list 0.00 0.00))
 (command "TEXT" "J" "ML" p1   0.75  0.00 "DRK GRY SH")
 (command "LAYER" "S" "CGBCMNT" "")
 (setq p1 (list 363.75 1624.46) p2 (list 0.00 0.00))
 (command "TEXT" "J" "ML" p1   0.75  0.00 "SFT, SLX")
 (command "LAYER" "S" "CGBMAIN" "")
 (setq p1 (list 321.00 1624.43) p2 (list 327.00 1624.43) p3 (list 327.00 1623.73) p4 (list 321.00 1623.73))
 (command "PLINE" p1 p2 p3 p4 "c")
 (command "HATCH" "ZIGZAG" 4.00 0.00 "L" "")
 (command "COLOR" "BYLAYER")
 (command "LAYER" "S" "CGBLITHCD" "")
 (setq p1 (list 327.00 1624.08) p2 (list 328.35 1622.83))
 (command "LINE" p1 p2 "")
 (setq p1 (list 328.50 1622.46) p2 (list 0.00 0.00))
 (command "TEXT" "J" "ML" p1   0.75  0.00 "124")
 (command "LAYER" "S" "CGBTHK" "")
 (setq p1 (list 333.00 1622.46) p2 (list 0.00 0.00))
 (command "TEXT" "J" "ML" p1   0.75  0.00 "0.70")
 (command "LAYER" "S" "CGBHZID" "")
 (setq p1 (list 337.50 1622.46) p2 (list 0.00 0.00))
 (command "TEXT" "J" "ML" p1   0.75  0.00 "")
 (setq p1 (list 339.75 1622.46) p2 (list 0.00 0.00))
 (command "TEXT" "J" "ML" p1   0.75  0.00 "9990")
 (command "LAYER" "S" "CGBLITHTXT" "")
 (setq p1 (list 343.50 1622.46) p2 (list 0.00 0.00))
 (command "TEXT" "J" "ML" p1   0.75  0.00 "DRK GRY SH")
 (command "LAYER" "S" "CGBCMNT" "")
 (setq p1 (list 363.75 1622.46) p2 (list 0.00 0.00))
 (command "TEXT" "J" "ML" p1   0.75  0.00 "SFT")
 (command "LAYER" "S" "CGBMAIN" "")
 (setq p1 (list 321.00 1623.73) p2 (list 327.00 1623.73) p3 (list 327.00 1621.85) p4 (list 321.00 1621.85))
 (command "PLINE" p1 p2 p3 p4 "c")
 (command "HATCH" "ZIGZAG" 4.00 0.00 "L" "")
 (command "COLOR" "BYLAYER")
 (command "LAYER" "S" "CGBLITHCD" "")
 (setq p1 (list 327.00 1622.79) p2 (list 328.35 1621.58))
 (command "LINE" p1 p2 "")
 (setq p1 (list 328.50 1621.21) p2 (list 0.00 0.00))
 (command "TEXT" "J" "ML" p1   0.75  0.00 "424")
 (command "LAYER" "S" "CGBTHK" "")
 (setq p1 (list 333.00 1621.21) p2 (list 0.00 0.00))
 (command "TEXT" "J" "ML" p1   0.75  0.00 "1.88")
 (command "LAYER" "S" "CGBHZID" "")
 (setq p1 (list 337.50 1621.21) p2 (list 0.00 0.00))
 (command "TEXT" "J" "ML" p1   0.75  0.00 "")
 (setq p1 (list 339.75 1621.21) p2 (list 0.00 0.00))
 (command "TEXT" "J" "ML" p1   0.75  0.00 "9990")
 (command "LAYER" "S" "CGBLITHTXT" "")
 (setq p1 (list 343.50 1621.21) p2 (list 0.00 0.00))
 (command "TEXT" "J" "ML" p1   0.75  0.00 "DRK GRY SDY SH W/LS NODS")
 (command "LAYER" "S" "CGBCMNT" "")
 (setq p1 (list 363.75 1621.21) p2 (list 0.00 0.00))
 (command "TEXT" "J" "ML" p1   0.75  0.00 "W/ NODS")
 (command "LAYER" "S" "CGBMAIN" "")
 (setq p1 (list 321.00 1621.85) p2 (list 327.00 1621.85) p3 (list 327.00 1613.01) p4 (list 321.00 1613.01))
 (command "PLINE" p1 p2 p3 p4 "c")
 (command "HATCH" "ZIGZAG" 5.00 0.00 "L" "")
 (command "COLOR" "BYLAYER")
 (command "LAYER" "S" "CGBLITHCD" "")
 (setq p1 (list 327.00 1617.43) p2 (list 328.35 1617.43))
 (command "LINE" p1 p2 "")
 (setq p1 (list 328.50 1617.06) p2 (list 0.00 0.00))
 (command "TEXT" "J" "ML" p1   0.75  0.00 "224")
 (command "LAYER" "S" "CGBTHK" "")
 (setq p1 (list 333.00 1617.06) p2 (list 0.00 0.00))
 (command "TEXT" "J" "ML" p1   0.75  0.00 "8.84")
 (command "LAYER" "S" "CGBHZID" "")
 (setq p1 (list 337.50 1617.06) p2 (list 0.00 0.00))
 (command "TEXT" "J" "ML" p1   0.75  0.00 "")
 (setq p1 (list 339.75 1617.06) p2 (list 0.00 0.00))
 (command "TEXT" "J" "ML" p1   0.75  0.00 "9990")
 (command "LAYER" "S" "CGBLITHTXT" "")
 (setq p1 (list 343.50 1617.06) p2 (list 0.00 0.00))
 (command "TEXT" "J" "ML" p1   0.75  0.00 "DRK GRY SH W/LS NODS")
 (command "LAYER" "S" "CGBCMNT" "")
 (setq p1 (list 363.75 1617.06) p2 (list 0.00 0.00))
 (command "TEXT" "J" "ML" p1   0.75  0.00 "SFT, MTTLD, S")
 (command "LAYER" "S" "CGBMAIN" "")
 (setq p1 (list 321.00 1613.01) p2 (list 327.00 1613.01) p3 (list 327.00 1612.78) p4 (list 321.00 1612.78))
 (command "PLINE" p1 p2 p3 p4 "c")
 (command "HATCH" "ZIGZAG" 4.00 0.00 "L" "")
 (command "COLOR" "BYLAYER")
 (command "LAYER" "S" "CGBLITHCD" "")
 (setq p1 (list 327.00 1612.90) p2 (list 328.35 1612.90))
 (command "LINE" p1 p2 "")
 (setq p1 (list 328.50 1612.52) p2 (list 0.00 0.00))
 (command "TEXT" "J" "ML" p1   0.75  0.00 "124")
 (command "LAYER" "S" "CGBTHK" "")
 (setq p1 (list 333.00 1612.52) p2 (list 0.00 0.00))
 (command "TEXT" "J" "ML" p1   0.75  0.00 "0.23")
 (command "LAYER" "S" "CGBHZID" "")
 (setq p1 (list 337.50 1612.52) p2 (list 0.00 0.00))
 (command "TEXT" "J" "ML" p1   0.75  0.00 "")
 (setq p1 (list 339.75 1612.52) p2 (list 0.00 0.00))
 (command "TEXT" "J" "ML" p1   0.75  0.00 "9990")
 (command "LAYER" "S" "CGBLITHTXT" "")
 (setq p1 (list 343.50 1612.52) p2 (list 0.00 0.00))
 (command "TEXT" "J" "ML" p1   0.75  0.00 "DRK GRY SH")
 (command "LAYER" "S" "CGBCMNT" "")
 (setq p1 (list 363.75 1612.52) p2 (list 0.00 0.00))
 (command "TEXT" "J" "ML" p1   0.75  0.00 "SFT, DRK")
 (command "LAYER" "S" "CGBMAIN" "")
 (setq p1 (list 321.00 1612.78) p2 (list 327.00 1612.78) p3 (list 327.00 1609.59) p4 (list 321.00 1609.59))
 (command "PLINE" p1 p2 p3 p4 "c")
 (command "HATCH" "ZIGZAG" 3.00 0.00 "L" "")
 (command "COLOR" "BYLAYER")
 (command "LAYER" "S" "CGBLITHCD" "")
 (setq p1 (list 327.00 1611.19) p2 (list 328.35 1611.19))
 (command "LINE" p1 p2 "")
 (setq p1 (list 328.50 1610.81) p2 (list 0.00 0.00))
 (command "TEXT" "J" "ML" p1   0.75  0.00 "154")
 (command "LAYER" "S" "CGBTHK" "")
 (setq p1 (list 333.00 1610.81) p2 (list 0.00 0.00))
 (command "TEXT" "J" "ML" p1   0.75  0.00 "3.19")
 (command "LAYER" "S" "CGBHZID" "")
 (setq p1 (list 337.50 1610.81) p2 (list 0.00 0.00))
 (command "TEXT" "J" "ML" p1   0.75  0.00 "")
 (setq p1 (list 339.75 1610.81) p2 (list 0.00 0.00))
 (command "TEXT" "J" "ML" p1   0.75  0.00 "9990")
 (command "LAYER" "S" "CGBLITHTXT" "")
 (setq p1 (list 343.50 1610.81) p2 (list 0.00 0.00))
 (command "TEXT" "J" "ML" p1   0.75  0.00 "RED+GRN SH")
 (command "LAYER" "S" "CGBCMNT" "")
 (setq p1 (list 363.75 1610.81) p2 (list 0.00 0.00))
 (command "TEXT" "J" "ML" p1   0.75  0.00 "CRMB, SLX")
 (command "LAYER" "S" "CGBMAIN" "")
 (setq p1 (list 321.00 1609.59) p2 (list 327.00 1609.59) p3 (list 327.00 1608.59) p4 (list 321.00 1608.59))
 (command "PLINE" p1 p2 p3 p4 "c")
 (command "HATCH" "ZIGZAG" 4.00 0.00 "L" "")
 (command "COLOR" "BYLAYER")
 (command "LAYER" "S" "CGBLITHCD" "")
 (setq p1 (list 327.00 1609.09) p2 (list 328.35 1609.09))
 (command "LINE" p1 p2 "")
 (setq p1 (list 328.50 1608.72) p2 (list 0.00 0.00))
 (command "TEXT" "J" "ML" p1   0.75  0.00 "125")
 (command "LAYER" "S" "CGBTHK" "")
 (setq p1 (list 333.00 1608.72) p2 (list 0.00 0.00))
 (command "TEXT" "J" "ML" p1   0.75  0.00 "1.00")
 (command "LAYER" "S" "CGBHZID" "")
 (setq p1 (list 337.50 1608.72) p2 (list 0.00 0.00))
 (command "TEXT" "J" "ML" p1   0.75  0.00 "")
 (setq p1 (list 339.75 1608.72) p2 (list 0.00 0.00))
 (command "TEXT" "J" "ML" p1   0.75  0.00 "9990")
 (command "LAYER" "S" "CGBLITHTXT" "")
 (setq p1 (list 343.50 1608.72) p2 (list 0.00 0.00))
 (command "TEXT" "J" "ML" p1   0.75  0.00 "DRK GRY CHRND SH")
 (command "LAYER" "S" "CGBCMNT" "")
 (setq p1 (list 363.75 1608.72) p2 (list 0.00 0.00))
 (command "TEXT" "J" "ML" p1   0.75  0.00 "")
 (command "LAYER" "S" "CGBMAIN" "")
 (setq p1 (list 321.00 1608.59) p2 (list 327.00 1608.59) p3 (list 327.00 1603.45) p4 (list 321.00 1603.45))
 (command "PLINE" p1 p2 p3 p4 "c")
 (command "HATCH" "ZIGZAG" 3.00 0.00 "L" "")
 (command "COLOR" "BYLAYER")
 (command "LAYER" "S" "CGBLITHCD" "")
 (setq p1 (list 327.00 1606.02) p2 (list 328.35 1606.02))
 (command "LINE" p1 p2 "")
 (setq p1 (list 328.50 1605.65) p2 (list 0.00 0.00))
 (command "TEXT" "J" "ML" p1   0.75  0.00 "154")
 (command "LAYER" "S" "CGBTHK" "")
 (setq p1 (list 333.00 1605.65) p2 (list 0.00 0.00))
 (command "TEXT" "J" "ML" p1   0.75  0.00 "5.14")
 (command "LAYER" "S" "CGBHZID" "")
 (setq p1 (list 337.50 1605.65) p2 (list 0.00 0.00))
 (command "TEXT" "J" "ML" p1   0.75  0.00 "")
 (setq p1 (list 339.75 1605.65) p2 (list 0.00 0.00))
 (command "TEXT" "J" "ML" p1   0.75  0.00 "9990")
 (command "LAYER" "S" "CGBLITHTXT" "")
 (setq p1 (list 343.50 1605.65) p2 (list 0.00 0.00))
 (command "TEXT" "J" "ML" p1   0.75  0.00 "RED+GRN SH")
 (command "LAYER" "S" "CGBCMNT" "")
 (setq p1 (list 363.75 1605.65) p2 (list 0.00 0.00))
 (command "TEXT" "J" "ML" p1   0.75  0.00 "SLX")
 (command "LAYER" "S" "CGBMAIN" "")
 (setq p1 (list 321.00 1603.45) p2 (list 327.00 1603.45) p3 (list 327.00 1601.94) p4 (list 321.00 1601.94))
 (command "PLINE" p1 p2 p3 p4 "c")
 (command "HATCH" "ZIGZAG" 5.00 0.00 "L" "")
 (command "COLOR" "BYLAYER")
 (command "LAYER" "S" "CGBLITHCD" "")
 (setq p1 (list 327.00 1602.70) p2 (list 328.35 1602.70))
 (command "LINE" p1 p2 "")
 (setq p1 (list 328.50 1602.32) p2 (list 0.00 0.00))
 (command "TEXT" "J" "ML" p1   0.75  0.00 "137")
 (command "LAYER" "S" "CGBTHK" "")
 (setq p1 (list 333.00 1602.32) p2 (list 0.00 0.00))
 (command "TEXT" "J" "ML" p1   0.75  0.00 "1.51")
 (command "LAYER" "S" "CGBHZID" "")
 (setq p1 (list 337.50 1602.32) p2 (list 0.00 0.00))
 (command "TEXT" "J" "ML" p1   0.75  0.00 "")
 (setq p1 (list 339.75 1602.32) p2 (list 0.00 0.00))
 (command "TEXT" "J" "ML" p1   0.75  0.00 "9990")
 (command "LAYER" "S" "CGBLITHTXT" "")
 (setq p1 (list 343.50 1602.32) p2 (list 0.00 0.00))
 (command "TEXT" "J" "ML" p1   0.75  0.00 "LT GRY GRN FIRECLAY")
 (command "LAYER" "S" "CGBCMNT" "")
 (setq p1 (list 363.75 1602.32) p2 (list 0.00 0.00))
 (command "TEXT" "J" "ML" p1   0.75  0.00 "")
 (command "LAYER" "S" "CGBMAIN" "")
 (setq p1 (list 321.00 1601.94) p2 (list 327.00 1601.94) p3 (list 327.00 1600.14) p4 (list 321.00 1600.14))
 (command "PLINE" p1 p2 p3 p4 "c")
 (command "HATCH" "ZIGZAG" 0.25 0.00 "L" "")
 (command "COLOR" "BYLAYER")
 (command "LAYER" "S" "CGBLITHCD" "")
 (setq p1 (list 327.00 1601.04) p2 (list 328.35 1601.04))
 (command "LINE" p1 p2 "")
 (setq p1 (list 328.50 1600.67) p2 (list 0.00 0.00))
 (command "TEXT" "J" "ML" p1   0.75  0.00 "327")
 (command "LAYER" "S" "CGBTHK" "")
 (setq p1 (list 333.00 1600.67) p2 (list 0.00 0.00))
 (command "TEXT" "J" "ML" p1   0.75  0.00 "1.80")
 (command "LAYER" "S" "CGBHZID" "")
 (setq p1 (list 337.50 1600.67) p2 (list 0.00 0.00))
 (command "TEXT" "J" "ML" p1   0.75  0.00 "")
 (setq p1 (list 339.75 1600.67) p2 (list 0.00 0.00))
 (command "TEXT" "J" "ML" p1   0.75  0.00 "9990")
 (command "LAYER" "S" "CGBLITHTXT" "")
 (setq p1 (list 343.50 1600.67) p2 (list 0.00 0.00))
 (command "TEXT" "J" "ML" p1   0.75  0.00 "DRK GRY SDY FIRECLAY")
 (command "LAYER" "S" "CGBCMNT" "")
 (setq p1 (list 363.75 1600.67) p2 (list 0.00 0.00))
 (command "TEXT" "J" "ML" p1   0.75  0.00 "")
 (command "LAYER" "S" "CGBMAIN" "")
 (setq p1 (list 321.00 1600.14) p2 (list 327.00 1600.14) p3 (list 327.00 1597.23) p4 (list 321.00 1597.23))
 (command "PLINE" p1 p2 p3 p4 "c")
 (command "HATCH" "ZIGZAG" 0.50 0.00 "L" "")
 (command "COLOR" "BYLAYER")
 (command "LAYER" "S" "CGBLITHCD" "")
 (setq p1 (list 327.00 1598.69) p2 (list 328.35 1598.69))
 (command "LINE" p1 p2 "")
 (setq p1 (list 328.50 1598.31) p2 (list 0.00 0.00))
 (command "TEXT" "J" "ML" p1   0.75  0.00 "323")
 (command "LAYER" "S" "CGBTHK" "")
 (setq p1 (list 333.00 1598.31) p2 (list 0.00 0.00))
 (command "TEXT" "J" "ML" p1   0.75  0.00 "2.91")
 (command "LAYER" "S" "CGBHZID" "")
 (setq p1 (list 337.50 1598.31) p2 (list 0.00 0.00))
 (command "TEXT" "J" "ML" p1   0.75  0.00 "")
 (setq p1 (list 339.75 1598.31) p2 (list 0.00 0.00))
 (command "TEXT" "J" "ML" p1   0.75  0.00 "9990")
 (command "LAYER" "S" "CGBLITHTXT" "")
 (setq p1 (list 343.50 1598.31) p2 (list 0.00 0.00))
 (command "TEXT" "J" "ML" p1   0.75  0.00 "DRK GRY SH W/SS STKS")
 (command "LAYER" "S" "CGBCMNT" "")
 (setq p1 (list 363.75 1598.31) p2 (list 0.00 0.00))
 (command "TEXT" "J" "ML" p1   0.75  0.00 "")
 (command "LAYER" "S" "CGBMAIN" "")
 (setq p1 (list 321.00 1597.23) p2 (list 327.00 1597.23) p3 (list 327.00 1594.03) p4 (list 321.00 1594.03))
 (command "PLINE" p1 p2 p3 p4 "c")
 (command "HATCH" "ZIGZAG" 4.00 0.00 "L" "")
 (command "COLOR" "BYLAYER")
 (command "LAYER" "S" "CGBLITHCD" "")
 (setq p1 (list 327.00 1595.63) p2 (list 328.35 1595.63))
 (command "LINE" p1 p2 "")
 (setq p1 (list 328.50 1595.26) p2 (list 0.00 0.00))
 (command "TEXT" "J" "ML" p1   0.75  0.00 "125")
 (command "LAYER" "S" "CGBTHK" "")
 (setq p1 (list 333.00 1595.26) p2 (list 0.00 0.00))
 (command "TEXT" "J" "ML" p1   0.75  0.00 "3.20")
 (command "LAYER" "S" "CGBHZID" "")
 (setq p1 (list 337.50 1595.26) p2 (list 0.00 0.00))
 (command "TEXT" "J" "ML" p1   0.75  0.00 "")
 (setq p1 (list 339.75 1595.26) p2 (list 0.00 0.00))
 (command "TEXT" "J" "ML" p1   0.75  0.00 "9990")
 (command "LAYER" "S" "CGBLITHTXT" "")
 (setq p1 (list 343.50 1595.26) p2 (list 0.00 0.00))
 (command "TEXT" "J" "ML" p1   0.75  0.00 "DRK GRY CHRND SH")
 (command "LAYER" "S" "CGBCMNT" "")
 (setq p1 (list 363.75 1595.26) p2 (list 0.00 0.00))
 (command "TEXT" "J" "ML" p1   0.75  0.00 "SFT")
 (command "LAYER" "S" "CGBMAIN" "")
 (setq p1 (list 321.00 1594.03) p2 (list 327.00 1594.03) p3 (list 327.00 1587.92) p4 (list 321.00 1587.92))
 (command "PLINE" p1 p2 p3 p4 "c")
 (command "HATCH" "ZIGZAG" 4.00 0.00 "L" "")
 (command "COLOR" "BYLAYER")
 (command "LAYER" "S" "CGBLITHCD" "")
 (setq p1 (list 327.00 1590.98) p2 (list 328.35 1590.98))
 (command "LINE" p1 p2 "")
 (setq p1 (list 328.50 1590.60) p2 (list 0.00 0.00))
 (command "TEXT" "J" "ML" p1   0.75  0.00 "444")
 (command "LAYER" "S" "CGBTHK" "")
 (setq p1 (list 333.00 1590.60) p2 (list 0.00 0.00))
 (command "TEXT" "J" "ML" p1   0.75  0.00 "6.11")
 (command "LAYER" "S" "CGBHZID" "")
 (setq p1 (list 337.50 1590.60) p2 (list 0.00 0.00))
 (command "TEXT" "J" "ML" p1   0.75  0.00 "")
 (setq p1 (list 339.75 1590.60) p2 (list 0.00 0.00))
 (command "TEXT" "J" "ML" p1   0.75  0.00 "9990")
 (command "LAYER" "S" "CGBLITHTXT" "")
 (setq p1 (list 343.50 1590.60) p2 (list 0.00 0.00))
 (command "TEXT" "J" "ML" p1   0.75  0.00 "GRN SDY SH W/LS NODS")
 (command "LAYER" "S" "CGBCMNT" "")
 (setq p1 (list 363.75 1590.60) p2 (list 0.00 0.00))
 (command "TEXT" "J" "ML" p1   0.75  0.00 "")
 (command "LAYER" "S" "CGBMAIN" "")
 (setq p1 (list 321.00 1587.92) p2 (list 327.00 1587.92) p3 (list 327.00 1585.71) p4 (list 321.00 1585.71))
 (command "PLINE" p1 p2 p3 p4 "c")
 (command "HATCH" "ZIGZAG" 0.50 0.00 "L" "")
 (command "COLOR" "BYLAYER")
 (command "LAYER" "S" "CGBLITHCD" "")
 (setq p1 (list 327.00 1586.82) p2 (list 328.35 1586.82))
 (command "LINE" p1 p2 "")
 (setq p1 (list 328.50 1586.44) p2 (list 0.00 0.00))
 (command "TEXT" "J" "ML" p1   0.75  0.00 "806")
 (command "LAYER" "S" "CGBTHK" "")
 (setq p1 (list 333.00 1586.44) p2 (list 0.00 0.00))
 (command "TEXT" "J" "ML" p1   0.75  0.00 "2.21")
 (command "LAYER" "S" "CGBHZID" "")
 (setq p1 (list 337.50 1586.44) p2 (list 0.00 0.00))
 (command "TEXT" "J" "ML" p1   0.75  0.00 "")
 (setq p1 (list 339.75 1586.44) p2 (list 0.00 0.00))
 (command "TEXT" "J" "ML" p1   0.75  0.00 "9990")
 (command "LAYER" "S" "CGBLITHTXT" "")
 (setq p1 (list 343.50 1586.44) p2 (list 0.00 0.00))
 (command "TEXT" "J" "ML" p1   0.75  0.00 "FN GRND SHLY LS W/LS NODS")
 (command "LAYER" "S" "CGBCMNT" "")
 (setq p1 (list 363.75 1586.44) p2 (list 0.00 0.00))
 (command "TEXT" "J" "ML" p1   0.75  0.00 "GREEN")
 (command "LAYER" "S" "CGBMAIN" "")
 (setq p1 (list 321.00 1585.71) p2 (list 327.00 1585.71) p3 (list 327.00 1583.39) p4 (list 321.00 1583.39))
 (command "PLINE" p1 p2 p3 p4 "c")
 (command "HATCH" "ZIGZAG" 4.00 0.00 "L" "")
 (command "COLOR" "BYLAYER")
 (command "LAYER" "S" "CGBLITHCD" "")
 (setq p1 (list 327.00 1584.55) p2 (list 328.35 1584.55))
 (command "LINE" p1 p2 "")
 (setq p1 (list 328.50 1584.18) p2 (list 0.00 0.00))
 (command "TEXT" "J" "ML" p1   0.75  0.00 "444")
 (command "LAYER" "S" "CGBTHK" "")
 (setq p1 (list 333.00 1584.18) p2 (list 0.00 0.00))
 (command "TEXT" "J" "ML" p1   0.75  0.00 "2.32")
 (command "LAYER" "S" "CGBHZID" "")
 (setq p1 (list 337.50 1584.18) p2 (list 0.00 0.00))
 (command "TEXT" "J" "ML" p1   0.75  0.00 "")
 (setq p1 (list 339.75 1584.18) p2 (list 0.00 0.00))
 (command "TEXT" "J" "ML" p1   0.75  0.00 "9990")
 (command "LAYER" "S" "CGBLITHTXT" "")
 (setq p1 (list 343.50 1584.18) p2 (list 0.00 0.00))
 (command "TEXT" "J" "ML" p1   0.75  0.00 "GRN SDY SH W/LS NODS")
 (command "LAYER" "S" "CGBCMNT" "")
 (setq p1 (list 363.75 1584.18) p2 (list 0.00 0.00))
 (command "TEXT" "J" "ML" p1   0.75  0.00 "GB")
 (command "LAYER" "S" "CGBMAIN" "")
 (setq p1 (list 321.00 1583.39) p2 (list 327.00 1583.39) p3 (list 327.00 1578.11) p4 (list 321.00 1578.11))
 (command "PLINE" p1 p2 p3 p4 "c")
 (command "HATCH" "ZIGZAG" 4.00 0.00 "L" "")
 (command "COLOR" "BYLAYER")
 (command "LAYER" "S" "CGBLITHCD" "")
 (setq p1 (list 327.00 1580.75) p2 (list 328.35 1580.75))
 (command "LINE" p1 p2 "")
 (setq p1 (list 328.50 1580.38) p2 (list 0.00 0.00))
 (command "TEXT" "J" "ML" p1   0.75  0.00 "374")
 (command "LAYER" "S" "CGBTHK" "")
 (setq p1 (list 333.00 1580.38) p2 (list 0.00 0.00))
 (command "TEXT" "J" "ML" p1   0.75  0.00 "5.28")
 (command "LAYER" "S" "CGBHZID" "")
 (setq p1 (list 337.50 1580.38) p2 (list 0.00 0.00))
 (command "TEXT" "J" "ML" p1   0.75  0.00 "")
 (setq p1 (list 339.75 1580.38) p2 (list 0.00 0.00))
 (command "TEXT" "J" "ML" p1   0.75  0.00 "9990")
 (command "LAYER" "S" "CGBLITHTXT" "")
 (setq p1 (list 343.50 1580.38) p2 (list 0.00 0.00))
 (command "TEXT" "J" "ML" p1   0.75  0.00 "GRY/GRN SDY SH")
 (command "LAYER" "S" "CGBCMNT" "")
 (setq p1 (list 363.75 1580.38) p2 (list 0.00 0.00))
 (command "TEXT" "J" "ML" p1   0.75  0.00 "GB")
 (command "LAYER" "S" "CGBMAIN" "")
 (setq p1 (list 321.00 1578.11) p2 (list 327.00 1578.11) p3 (list 327.00 1576.45) p4 (list 321.00 1576.45))
 (command "PLINE" p1 p2 p3 p4 "c")
 (command "HATCH" "ZIGZAG" 10.00 0.00 "L" "")
 (command "COLOR" "BYLAYER")
 (command "LAYER" "S" "CGBLITHCD" "")
 (setq p1 (list 327.00 1577.28) p2 (list 328.35 1577.28))
 (command "LINE" p1 p2 "")
 (setq p1 (list 328.50 1576.91) p2 (list 0.00 0.00))
 (command "TEXT" "J" "ML" p1   0.75  0.00 "372")
 (command "LAYER" "S" "CGBTHK" "")
 (setq p1 (list 333.00 1576.91) p2 (list 0.00 0.00))
 (command "TEXT" "J" "ML" p1   0.75  0.00 "1.66")
 (command "LAYER" "S" "CGBHZID" "")
 (setq p1 (list 337.50 1576.91) p2 (list 0.00 0.00))
 (command "TEXT" "J" "ML" p1   0.75  0.00 "")
 (setq p1 (list 339.75 1576.91) p2 (list 0.00 0.00))
 (command "TEXT" "J" "ML" p1   0.75  0.00 "9990")
 (command "LAYER" "S" "CGBLITHTXT" "")
 (setq p1 (list 343.50 1576.91) p2 (list 0.00 0.00))
 (command "TEXT" "J" "ML" p1   0.75  0.00 "GRY/GRN SH+INTERBED SS")
 (command "LAYER" "S" "CGBCMNT" "")
 (setq p1 (list 363.75 1576.91) p2 (list 0.00 0.00))
 (command "TEXT" "J" "ML" p1   0.75  0.00 "GB")
 (command "LAYER" "S" "CGBMAIN" "")
 (setq p1 (list 321.00 1576.45) p2 (list 327.00 1576.45) p3 (list 327.00 1574.03) p4 (list 321.00 1574.03))
 (command "PLINE" p1 p2 p3 p4 "c")
 (command "HATCH" "ZIGZAG" 4.00 0.00 "L" "")
 (command "COLOR" "BYLAYER")
 (command "LAYER" "S" "CGBLITHCD" "")
 (setq p1 (list 327.00 1575.24) p2 (list 328.35 1575.24))
 (command "LINE" p1 p2 "")
 (setq p1 (list 328.50 1574.87) p2 (list 0.00 0.00))
 (command "TEXT" "J" "ML" p1   0.75  0.00 "544")
 (command "LAYER" "S" "CGBTHK" "")
 (setq p1 (list 333.00 1574.87) p2 (list 0.00 0.00))
 (command "TEXT" "J" "ML" p1   0.75  0.00 "2.42")
 (command "LAYER" "S" "CGBHZID" "")
 (setq p1 (list 337.50 1574.87) p2 (list 0.00 0.00))
 (command "TEXT" "J" "ML" p1   0.75  0.00 "")
 (setq p1 (list 339.75 1574.87) p2 (list 0.00 0.00))
 (command "TEXT" "J" "ML" p1   0.75  0.00 "9990")
 (command "LAYER" "S" "CGBLITHTXT" "")
 (setq p1 (list 343.50 1574.87) p2 (list 0.00 0.00))
 (command "TEXT" "J" "ML" p1   0.75  0.00 "GRY MASS SS")
 (command "LAYER" "S" "CGBCMNT" "")
 (setq p1 (list 363.75 1574.87) p2 (list 0.00 0.00))
 (command "TEXT" "J" "ML" p1   0.75  0.00 "")
 (command "LAYER" "S" "CGBMAIN" "")
 (setq p1 (list 321.00 1574.03) p2 (list 327.00 1574.03) p3 (list 327.00 1573.25) p4 (list 321.00 1573.25))
 (command "PLINE" p1 p2 p3 p4 "c")
 (command "HATCH" "ZIGZAG" 4.00 0.00 "L" "")
 (command "COLOR" "BYLAYER")
 (command "LAYER" "S" "CGBLITHCD" "")
 (setq p1 (list 327.00 1573.64) p2 (list 328.35 1573.64))
 (command "LINE" p1 p2 "")
 (setq p1 (list 328.50 1573.27) p2 (list 0.00 0.00))
 (command "TEXT" "J" "ML" p1   0.75  0.00 "544")
 (command "LAYER" "S" "CGBTHK" "")
 (setq p1 (list 333.00 1573.27) p2 (list 0.00 0.00))
 (command "TEXT" "J" "ML" p1   0.75  0.00 "0.78")
 (command "LAYER" "S" "CGBHZID" "")
 (setq p1 (list 337.50 1573.27) p2 (list 0.00 0.00))
 (command "TEXT" "J" "ML" p1   0.75  0.00 "")
 (setq p1 (list 339.75 1573.27) p2 (list 0.00 0.00))
 (command "TEXT" "J" "ML" p1   0.75  0.00 "9990")
 (command "LAYER" "S" "CGBLITHTXT" "")
 (setq p1 (list 343.50 1573.27) p2 (list 0.00 0.00))
 (command "TEXT" "J" "ML" p1   0.75  0.00 "GRY MASS SS")
 (command "LAYER" "S" "CGBCMNT" "")
 (setq p1 (list 363.75 1573.27) p2 (list 0.00 0.00))
 (command "TEXT" "J" "ML" p1   0.75  0.00 "SLC")
 (command "LAYER" "S" "CGBMAIN" "")
 (setq p1 (list 321.00 1573.25) p2 (list 327.00 1573.25) p3 (list 327.00 1565.57) p4 (list 321.00 1565.57))
 (command "PLINE" p1 p2 p3 p4 "c")
 (command "HATCH" "ZIGZAG" 4.00 0.00 "L" "")
 (command "COLOR" "BYLAYER")
 (command "LAYER" "S" "CGBLITHCD" "")
 (setq p1 (list 327.00 1569.41) p2 (list 328.35 1569.41))
 (command "LINE" p1 p2 "")
 (setq p1 (list 328.50 1569.04) p2 (list 0.00 0.00))
 (command "TEXT" "J" "ML" p1   0.75  0.00 "124")
 (command "LAYER" "S" "CGBTHK" "")
 (setq p1 (list 333.00 1569.04) p2 (list 0.00 0.00))
 (command "TEXT" "J" "ML" p1   0.75  0.00 "7.68")
 (command "LAYER" "S" "CGBHZID" "")
 (setq p1 (list 337.50 1569.04) p2 (list 0.00 0.00))
 (command "TEXT" "J" "ML" p1   0.75  0.00 "")
 (setq p1 (list 339.75 1569.04) p2 (list 0.00 0.00))
 (command "TEXT" "J" "ML" p1   0.75  0.00 "9990")
 (command "LAYER" "S" "CGBLITHTXT" "")
 (setq p1 (list 343.50 1569.04) p2 (list 0.00 0.00))
 (command "TEXT" "J" "ML" p1   0.75  0.00 "DRK GRY SH")
 (command "LAYER" "S" "CGBCMNT" "")
 (setq p1 (list 363.75 1569.04) p2 (list 0.00 0.00))
 (command "TEXT" "J" "ML" p1   0.75  0.00 "FEW ROOTS/BUR")
 (command "LAYER" "S" "CGBMAIN" "")
 (setq p1 (list 321.00 1565.57) p2 (list 327.00 1565.57) p3 (list 327.00 1558.03) p4 (list 321.00 1558.03))
 (command "PLINE" p1 p2 p3 p4 "c")
 (command "HATCH" "ZIGZAG" 0.50 0.00 "L" "")
 (command "COLOR" "BYLAYER")
 (command "LAYER" "S" "CGBLITHCD" "")
 (setq p1 (list 327.00 1561.80) p2 (list 328.35 1561.80))
 (command "LINE" p1 p2 "")
 (setq p1 (list 328.50 1561.43) p2 (list 0.00 0.00))
 (command "TEXT" "J" "ML" p1   0.75  0.00 "323")
 (command "LAYER" "S" "CGBTHK" "")
 (setq p1 (list 333.00 1561.43) p2 (list 0.00 0.00))
 (command "TEXT" "J" "ML" p1   0.75  0.00 "7.54")
 (command "LAYER" "S" "CGBHZID" "")
 (setq p1 (list 337.50 1561.43) p2 (list 0.00 0.00))
 (command "TEXT" "J" "ML" p1   0.75  0.00 "")
 (setq p1 (list 339.75 1561.43) p2 (list 0.00 0.00))
 (command "TEXT" "J" "ML" p1   0.75  0.00 "6951")
 (command "LAYER" "S" "CGBLITHTXT" "")
 (setq p1 (list 343.50 1561.43) p2 (list 0.00 0.00))
 (command "TEXT" "J" "ML" p1   0.75  0.00 "DRK GRY SH W/SS STKS")
 (command "LAYER" "S" "CGBCMNT" "")
 (setq p1 (list 363.75 1561.43) p2 (list 0.00 0.00))
 (command "TEXT" "J" "ML" p1   0.75  0.00 "RIP, SID LAY,")
 (command "LAYER" "S" "CGBMAIN" "")
 (setq p1 (list 321.00 1558.03) p2 (list 327.00 1558.03) p3 (list 327.00 1553.83) p4 (list 321.00 1553.83))
 (command "PLINE" p1 p2 p3 p4 "c")
 (command "HATCH" "ZIGZAG" 2.50 90.00 "L" "")
 (command "COLOR" "BYLAYER")
 (command "LAYER" "S" "CGBLITHCD" "")
 (setq p1 (list 327.00 1555.93) p2 (list 328.35 1555.93))
 (command "LINE" p1 p2 "")
 (setq p1 (list 328.50 1555.56) p2 (list 0.00 0.00))
 (command "TEXT" "J" "ML" p1   0.75  0.00 "324")
 (command "LAYER" "S" "CGBTHK" "")
 (setq p1 (list 333.00 1555.56) p2 (list 0.00 0.00))
 (command "TEXT" "J" "ML" p1   0.75  0.00 "4.20")
 (command "LAYER" "S" "CGBHZID" "")
 (setq p1 (list 337.50 1555.56) p2 (list 0.00 0.00))
 (command "TEXT" "J" "ML" p1   0.75  0.00 "")
 (setq p1 (list 339.75 1555.56) p2 (list 0.00 0.00))
 (command "TEXT" "J" "ML" p1   0.75  0.00 "6951")
 (command "LAYER" "S" "CGBLITHTXT" "")
 (setq p1 (list 343.50 1555.56) p2 (list 0.00 0.00))
 (command "TEXT" "J" "ML" p1   0.75  0.00 "DRK GRY MASS SDY SH")
 (command "LAYER" "S" "CGBCMNT" "")
 (setq p1 (list 363.75 1555.56) p2 (list 0.00 0.00))
 (command "TEXT" "J" "ML" p1   0.75  0.00 "W SID LAYRS")
 (command "LAYER" "S" "CGBMAIN" "")
 (command "LAYER" "S" "CGBLITHCD" "")
 (setq p1 (list 327.00 1553.83) p2 (list 328.35 1553.83))
 (command "LINE" p1 p2 "")
 (setq p1 (list 328.50 1553.46) p2 (list 0.00 0.00))
 (command "TEXT" "J" "ML" p1   0.75  0.00 "021")
 (command "LAYER" "S" "CGBTHK" "")
 (setq p1 (list 333.00 1553.46) p2 (list 0.00 0.00))
 (command "TEXT" "J" "ML" p1   0.75  0.00 "0.00")
 (command "LAYER" "S" "CGBHZID" "")
 (setq p1 (list 337.50 1553.46) p2 (list 0.00 0.00))
 (command "TEXT" "J" "ML" p1   0.75  0.00 "")
 (setq p1 (list 339.75 1553.46) p2 (list 0.00 0.00))
 (command "TEXT" "J" "ML" p1   0.75  0.00 "7000")
 (command "LAYER" "S" "CGBLITHTXT" "")
 (setq p1 (list 343.50 1553.46) p2 (list 0.00 0.00))
 (command "TEXT" "J" "ML" p1   0.75  0.00 "COMMON BANDED COAL")
 (command "LAYER" "S" "CGBCMNT" "")
 (setq p1 (list 363.75 1553.46) p2 (list 0.00 0.00))
 (command "TEXT" "J" "ML" p1   0.75  0.00 "MAH HRZN ??")
 (command "LAYER" "S" "CGBMAIN" "")
 (setq p1 (list 321.00 1553.83) p2 (list 327.00 1553.83) p3 (list 327.00 1553.68) p4 (list 321.00 1553.68))
 (command "PLINE" p1 p2 p3 p4 "c")
 (command "HATCH" "ZIGZAG" 2.50 90.00 "L" "")
 (command "COLOR" "BYLAYER")
 (command "LAYER" "S" "CGBLITHCD" "")
 (setq p1 (list 327.00 1553.76) p2 (list 328.35 1552.51))
 (command "LINE" p1 p2 "")
 (setq p1 (list 328.50 1552.13) p2 (list 0.00 0.00))
 (command "TEXT" "J" "ML" p1   0.75  0.00 "324")
 (command "LAYER" "S" "CGBTHK" "")
 (setq p1 (list 333.00 1552.13) p2 (list 0.00 0.00))
 (command "TEXT" "J" "ML" p1   0.75  0.00 "0.15")
 (command "LAYER" "S" "CGBHZID" "")
 (setq p1 (list 337.50 1552.13) p2 (list 0.00 0.00))
 (command "TEXT" "J" "ML" p1   0.75  0.00 "")
 (setq p1 (list 339.75 1552.13) p2 (list 0.00 0.00))
 (command "TEXT" "J" "ML" p1   0.75  0.00 "6951")
 (command "LAYER" "S" "CGBLITHTXT" "")
 (setq p1 (list 343.50 1552.13) p2 (list 0.00 0.00))
 (command "TEXT" "J" "ML" p1   0.75  0.00 "DRK GRY MASS SDY SH")
 (command "LAYER" "S" "CGBCMNT" "")
 (setq p1 (list 363.75 1552.13) p2 (list 0.00 0.00))
 (command "TEXT" "J" "ML" p1   0.75  0.00 "GB")
 (command "LAYER" "S" "CGBMAIN" "")
 (setq p1 (list 321.00 1553.68) p2 (list 327.00 1553.68) p3 (list 327.00 1545.38) p4 (list 321.00 1545.38))
 (command "PLINE" p1 p2 p3 p4 "c")
 (command "HATCH" "ZIGZAG" 5.00 0.00 "L" "")
 (command "COLOR" "BYLAYER")
 (command "LAYER" "S" "CGBLITHCD" "")
 (setq p1 (list 327.00 1549.53) p2 (list 328.35 1549.53))
 (command "LINE" p1 p2 "")
 (setq p1 (list 328.50 1549.16) p2 (list 0.00 0.00))
 (command "TEXT" "J" "ML" p1   0.75  0.00 "322")
 (command "LAYER" "S" "CGBTHK" "")
 (setq p1 (list 333.00 1549.16) p2 (list 0.00 0.00))
 (command "TEXT" "J" "ML" p1   0.75  0.00 "8.30")
 (command "LAYER" "S" "CGBHZID" "")
 (setq p1 (list 337.50 1549.16) p2 (list 0.00 0.00))
 (command "TEXT" "J" "ML" p1   0.75  0.00 "")
 (setq p1 (list 339.75 1549.16) p2 (list 0.00 0.00))
 (command "TEXT" "J" "ML" p1   0.75  0.00 "6951")
 (command "LAYER" "S" "CGBLITHTXT" "")
 (setq p1 (list 343.50 1549.16) p2 (list 0.00 0.00))
 (command "TEXT" "J" "ML" p1   0.75  0.00 "DRK GRY SH+INTERBED SS")
 (command "LAYER" "S" "CGBCMNT" "")
 (setq p1 (list 363.75 1549.16) p2 (list 0.00 0.00))
 (command "TEXT" "J" "ML" p1   0.75  0.00 "ANG RIP, GB")
 (command "LAYER" "S" "CGBMAIN" "")
 (setq p1 (list 321.00 1545.38) p2 (list 327.00 1545.38) p3 (list 327.00 1541.83) p4 (list 321.00 1541.83))
 (command "PLINE" p1 p2 p3 p4 "c")
 (command "HATCH" "ZIGZAG" 2.00 45.00 "L" "")
 (command "COLOR" "BYLAYER")
 (command "LAYER" "S" "CGBLITHCD" "")
 (setq p1 (list 327.00 1543.61) p2 (list 328.35 1543.61))
 (command "LINE" p1 p2 "")
 (setq p1 (list 328.50 1543.23) p2 (list 0.00 0.00))
 (command "TEXT" "J" "ML" p1   0.75  0.00 "013")
 (command "LAYER" "S" "CGBTHK" "")
 (setq p1 (list 333.00 1543.23) p2 (list 0.00 0.00))
 (command "TEXT" "J" "ML" p1   0.75  0.00 "3.55")
 (command "LAYER" "S" "CGBHZID" "")
 (setq p1 (list 337.50 1543.23) p2 (list 0.00 0.00))
 (command "TEXT" "J" "ML" p1   0.75  0.00 "")
 (setq p1 (list 339.75 1543.23) p2 (list 0.00 0.00))
 (command "TEXT" "J" "ML" p1   0.75  0.00 "6951")
 (command "LAYER" "S" "CGBLITHTXT" "")
 (setq p1 (list 343.50 1543.23) p2 (list 0.00 0.00))
 (command "TEXT" "J" "ML" p1   0.75  0.00 "SLUMPED SH")
 (command "LAYER" "S" "CGBCMNT" "")
 (setq p1 (list 363.75 1543.23) p2 (list 0.00 0.00))
 (command "TEXT" "J" "ML" p1   0.75  0.00 "ANG BEDS W/SI")
 (command "LAYER" "S" "CGBMAIN" "")
 (setq p1 (list 321.00 1541.83) p2 (list 327.00 1541.83) p3 (list 327.00 1540.08) p4 (list 321.00 1540.08))
 (command "PLINE" p1 p2 p3 p4 "c")
 (command "HATCH" "ZIGZAG" 4.00 0.00 "L" "")
 (command "COLOR" "BYLAYER")
 (command "LAYER" "S" "CGBLITHCD" "")
 (setq p1 (list 327.00 1540.96) p2 (list 328.35 1540.96))
 (command "LINE" p1 p2 "")
 (setq p1 (list 328.50 1540.58) p2 (list 0.00 0.00))
 (command "TEXT" "J" "ML" p1   0.75  0.00 "124")
 (command "LAYER" "S" "CGBTHK" "")
 (setq p1 (list 333.00 1540.58) p2 (list 0.00 0.00))
 (command "TEXT" "J" "ML" p1   0.75  0.00 "1.75")
 (command "LAYER" "S" "CGBHZID" "")
 (setq p1 (list 337.50 1540.58) p2 (list 0.00 0.00))
 (command "TEXT" "J" "ML" p1   0.75  0.00 "")
 (setq p1 (list 339.75 1540.58) p2 (list 0.00 0.00))
 (command "TEXT" "J" "ML" p1   0.75  0.00 "6951")
 (command "LAYER" "S" "CGBLITHTXT" "")
 (setq p1 (list 343.50 1540.58) p2 (list 0.00 0.00))
 (command "TEXT" "J" "ML" p1   0.75  0.00 "DRK GRY SH")
 (command "LAYER" "S" "CGBCMNT" "")
 (setq p1 (list 363.75 1540.58) p2 (list 0.00 0.00))
 (command "TEXT" "J" "ML" p1   0.75  0.00 "BADLY BRKN")
 (command "LAYER" "S" "CGBMAIN" "")
 (setq p1 (list 321.00 1540.08) p2 (list 327.00 1540.08) p3 (list 327.00 1539.22) p4 (list 321.00 1539.22))
 (command "PLINE" p1 p2 p3 p4 "c")
 (command "HATCH" "ZIGZAG" 4.00 0.00 "L" "")
 (command "COLOR" "BYLAYER")
 (command "LAYER" "S" "CGBLITHCD" "")
 (setq p1 (list 327.00 1539.65) p2 (list 328.35 1539.65))
 (command "LINE" p1 p2 "")
 (setq p1 (list 328.50 1539.28) p2 (list 0.00 0.00))
 (command "TEXT" "J" "ML" p1   0.75  0.00 "124")
 (command "LAYER" "S" "CGBTHK" "")
 (setq p1 (list 333.00 1539.28) p2 (list 0.00 0.00))
 (command "TEXT" "J" "ML" p1   0.75  0.00 "0.86")
 (command "LAYER" "S" "CGBHZID" "")
 (setq p1 (list 337.50 1539.28) p2 (list 0.00 0.00))
 (command "TEXT" "J" "ML" p1   0.75  0.00 "")
 (setq p1 (list 339.75 1539.28) p2 (list 0.00 0.00))
 (command "TEXT" "J" "ML" p1   0.75  0.00 "6951")
 (command "LAYER" "S" "CGBLITHTXT" "")
 (setq p1 (list 343.50 1539.28) p2 (list 0.00 0.00))
 (command "TEXT" "J" "ML" p1   0.75  0.00 "DRK GRY SH")
 (command "LAYER" "S" "CGBCMNT" "")
 (setq p1 (list 363.75 1539.28) p2 (list 0.00 0.00))
 (command "TEXT" "J" "ML" p1   0.75  0.00 "BRKN")
 (command "LAYER" "S" "CGBMAIN" "")
 (setq p1 (list 321.00 1539.22) p2 (list 327.00 1539.22) p3 (list 327.00 1538.51) p4 (list 321.00 1538.51))
 (command "PLINE" p1 p2 p3 p4 "c")
 (command "HATCH" "ZIGZAG" 0.25 0.00 "L" "")
 (command "COLOR" "BYLAYER")
 (command "LAYER" "S" "CGBLITHCD" "")
 (setq p1 (list 327.00 1538.87) p2 (list 328.35 1537.62))
 (command "LINE" p1 p2 "")
 (setq p1 (list 328.50 1537.24) p2 (list 0.00 0.00))
 (command "TEXT" "J" "ML" p1   0.75  0.00 "127")
 (command "LAYER" "S" "CGBTHK" "")
 (setq p1 (list 333.00 1537.24) p2 (list 0.00 0.00))
 (command "TEXT" "J" "ML" p1   0.75  0.00 "0.71")
 (command "LAYER" "S" "CGBHZID" "")
 (setq p1 (list 337.50 1537.24) p2 (list 0.00 0.00))
 (command "TEXT" "J" "ML" p1   0.75  0.00 "")
 (setq p1 (list 339.75 1537.24) p2 (list 0.00 0.00))
 (command "TEXT" "J" "ML" p1   0.75  0.00 "6951")
 (command "LAYER" "S" "CGBLITHTXT" "")
 (setq p1 (list 343.50 1537.24) p2 (list 0.00 0.00))
 (command "TEXT" "J" "ML" p1   0.75  0.00 "DRK GRY FIRECLAY")
 (command "LAYER" "S" "CGBCMNT" "")
 (setq p1 (list 363.75 1537.24) p2 (list 0.00 0.00))
 (command "TEXT" "J" "ML" p1   0.75  0.00 "VV SFT, PLSTI")
 (command "LAYER" "S" "CGBMAIN" "")
 (setq p1 (list 321.00 1538.51) p2 (list 327.00 1538.51) p3 (list 327.00 1537.37) p4 (list 321.00 1537.37))
 (command "PLINE" p1 p2 p3 p4 "c")
 (command "HATCH" "ZIGZAG" 4.00 0.00 "L" "")
 (command "COLOR" "BYLAYER")
 (command "LAYER" "S" "CGBLITHCD" "")
 (setq p1 (list 327.00 1537.94) p2 (list 328.35 1536.37))
 (command "LINE" p1 p2 "")
 (setq p1 (list 328.50 1535.99) p2 (list 0.00 0.00))
 (command "TEXT" "J" "ML" p1   0.75  0.00 "424")
 (command "LAYER" "S" "CGBTHK" "")
 (setq p1 (list 333.00 1535.99) p2 (list 0.00 0.00))
 (command "TEXT" "J" "ML" p1   0.75  0.00 "1.14")
 (command "LAYER" "S" "CGBHZID" "")
 (setq p1 (list 337.50 1535.99) p2 (list 0.00 0.00))
 (command "TEXT" "J" "ML" p1   0.75  0.00 "")
 (setq p1 (list 339.75 1535.99) p2 (list 0.00 0.00))
 (command "TEXT" "J" "ML" p1   0.75  0.00 "6951")
 (command "LAYER" "S" "CGBLITHTXT" "")
 (setq p1 (list 343.50 1535.99) p2 (list 0.00 0.00))
 (command "TEXT" "J" "ML" p1   0.75  0.00 "DRK GRY SDY SH W/LS NODS")
 (command "LAYER" "S" "CGBCMNT" "")
 (setq p1 (list 363.75 1535.99) p2 (list 0.00 0.00))
 (command "TEXT" "J" "ML" p1   0.75  0.00 "CRSHD, GB")
 (command "LAYER" "S" "CGBMAIN" "")
 (command "LAYER" "S" "CGBLITHCD" "")
 (setq p1 (list 327.00 1537.37) p2 (list 328.35 1535.12))
 (command "LINE" p1 p2 "")
 (setq p1 (list 328.50 1534.74) p2 (list 0.00 0.00))
 (command "TEXT" "J" "ML" p1   0.75  0.00 "322")
 (command "LAYER" "S" "CGBTHK" "")
 (setq p1 (list 333.00 1534.74) p2 (list 0.00 0.00))
 (command "TEXT" "J" "ML" p1   0.75  0.00 "0.00")
 (command "LAYER" "S" "CGBHZID" "")
 (setq p1 (list 337.50 1534.74) p2 (list 0.00 0.00))
 (command "TEXT" "J" "ML" p1   0.75  0.00 "")
 (setq p1 (list 339.75 1534.74) p2 (list 0.00 0.00))
 (command "TEXT" "J" "ML" p1   0.75  0.00 "6951")
 (command "LAYER" "S" "CGBLITHTXT" "")
 (setq p1 (list 343.50 1534.74) p2 (list 0.00 0.00))
 (command "TEXT" "J" "ML" p1   0.75  0.00 "DRK GRY SH+INTERBED SS")
 (command "LAYER" "S" "CGBCMNT" "")
 (setq p1 (list 363.75 1534.74) p2 (list 0.00 0.00))
 (command "TEXT" "J" "ML" p1   0.75  0.00 "LMH SS = 0")
 (command "LAYER" "S" "CGBMAIN" "")
 (setq p1 (list 321.00 1537.37) p2 (list 327.00 1537.37) p3 (list 327.00 1534.03) p4 (list 321.00 1534.03))
 (command "PLINE" p1 p2 p3 p4 "c")
 (command "HATCH" "ZIGZAG" 2.50 90.00 "L" "")
 (command "COLOR" "BYLAYER")
 (command "LAYER" "S" "CGBLITHCD" "")
 (setq p1 (list 327.00 1535.70) p2 (list 328.35 1533.87))
 (command "LINE" p1 p2 "")
 (setq p1 (list 328.50 1533.49) p2 (list 0.00 0.00))
 (command "TEXT" "J" "ML" p1   0.75  0.00 "325")
 (command "LAYER" "S" "CGBTHK" "")
 (setq p1 (list 333.00 1533.49) p2 (list 0.00 0.00))
 (command "TEXT" "J" "ML" p1   0.75  0.00 "3.34")
 (command "LAYER" "S" "CGBHZID" "")
 (setq p1 (list 337.50 1533.49) p2 (list 0.00 0.00))
 (command "TEXT" "J" "ML" p1   0.75  0.00 "")
 (setq p1 (list 339.75 1533.49) p2 (list 0.00 0.00))
 (command "TEXT" "J" "ML" p1   0.75  0.00 "6951")
 (command "LAYER" "S" "CGBLITHTXT" "")
 (setq p1 (list 343.50 1533.49) p2 (list 0.00 0.00))
 (command "TEXT" "J" "ML" p1   0.75  0.00 "DRK GRY MASS CHRND SDY SH")
 (command "LAYER" "S" "CGBCMNT" "")
 (setq p1 (list 363.75 1533.49) p2 (list 0.00 0.00))
 (command "TEXT" "J" "ML" p1   0.75  0.00 "")
 (command "LAYER" "S" "CGBMAIN" "")
 (setq p1 (list 321.00 1534.03) p2 (list 327.00 1534.03) p3 (list 327.00 1532.22) p4 (list 321.00 1532.22))
 (command "PLINE" p1 p2 p3 p4 "c")
 (command "HATCH" "ZIGZAG" 4.00 0.00 "L" "")
 (command "COLOR" "BYLAYER")
 (command "LAYER" "S" "CGBLITHCD" "")
 (setq p1 (list 327.00 1533.13) p2 (list 328.35 1532.62))
 (command "LINE" p1 p2 "")
 (setq p1 (list 328.50 1532.24) p2 (list 0.00 0.00))
 (command "TEXT" "J" "ML" p1   0.75  0.00 "125")
 (command "LAYER" "S" "CGBTHK" "")
 (setq p1 (list 333.00 1532.24) p2 (list 0.00 0.00))
 (command "TEXT" "J" "ML" p1   0.75  0.00 "1.81")
 (command "LAYER" "S" "CGBHZID" "")
 (setq p1 (list 337.50 1532.24) p2 (list 0.00 0.00))
 (command "TEXT" "J" "ML" p1   0.75  0.00 "")
 (setq p1 (list 339.75 1532.24) p2 (list 0.00 0.00))
 (command "TEXT" "J" "ML" p1   0.75  0.00 "6951")
 (command "LAYER" "S" "CGBLITHTXT" "")
 (setq p1 (list 343.50 1532.24) p2 (list 0.00 0.00))
 (command "TEXT" "J" "ML" p1   0.75  0.00 "DRK GRY CHRND SH")
 (command "LAYER" "S" "CGBCMNT" "")
 (setq p1 (list 363.75 1532.24) p2 (list 0.00 0.00))
 (command "TEXT" "J" "ML" p1   0.75  0.00 "SFT, DRK")
 (command "LAYER" "S" "CGBMAIN" "")
 (setq p1 (list 321.00 1532.22) p2 (list 327.00 1532.22) p3 (list 327.00 1529.91) p4 (list 321.00 1529.91))
 (command "PLINE" p1 p2 p3 p4 "c")
 (command "HATCH" "ZIGZAG" 4.00 0.00 "L" "")
 (command "COLOR" "BYLAYER")
 (command "LAYER" "S" "CGBLITHCD" "")
 (setq p1 (list 327.00 1531.07) p2 (list 328.35 1531.07))
 (command "LINE" p1 p2 "")
 (setq p1 (list 328.50 1530.69) p2 (list 0.00 0.00))
 (command "TEXT" "J" "ML" p1   0.75  0.00 "124")
 (command "LAYER" "S" "CGBTHK" "")
 (setq p1 (list 333.00 1530.69) p2 (list 0.00 0.00))
 (command "TEXT" "J" "ML" p1   0.75  0.00 "2.31")
 (command "LAYER" "S" "CGBHZID" "")
 (setq p1 (list 337.50 1530.69) p2 (list 0.00 0.00))
 (command "TEXT" "J" "ML" p1   0.75  0.00 "")
 (setq p1 (list 339.75 1530.69) p2 (list 0.00 0.00))
 (command "TEXT" "J" "ML" p1   0.75  0.00 "6951")
 (command "LAYER" "S" "CGBLITHTXT" "")
 (setq p1 (list 343.50 1530.69) p2 (list 0.00 0.00))
 (command "TEXT" "J" "ML" p1   0.75  0.00 "DRK GRY SH")
 (command "LAYER" "S" "CGBCMNT" "")
 (setq p1 (list 363.75 1530.69) p2 (list 0.00 0.00))
 (command "TEXT" "J" "ML" p1   0.75  0.00 "SFT")
 (command "LAYER" "S" "CGBMAIN" "")
 (setq p1 (list 321.00 1529.91) p2 (list 327.00 1529.91) p3 (list 327.00 1525.28) p4 (list 321.00 1525.28))
 (command "PLINE" p1 p2 p3 p4 "c")
 (command "HATCH" "ZIGZAG" 5.00 0.00 "L" "")
 (command "COLOR" "BYLAYER")
 (command "LAYER" "S" "CGBLITHCD" "")
 (setq p1 (list 327.00 1527.60) p2 (list 328.35 1527.60))
 (command "LINE" p1 p2 "")
 (setq p1 (list 328.50 1527.22) p2 (list 0.00 0.00))
 (command "TEXT" "J" "ML" p1   0.75  0.00 "332")
 (command "LAYER" "S" "CGBTHK" "")
 (setq p1 (list 333.00 1527.22) p2 (list 0.00 0.00))
 (command "TEXT" "J" "ML" p1   0.75  0.00 "4.63")
 (command "LAYER" "S" "CGBHZID" "")
 (setq p1 (list 337.50 1527.22) p2 (list 0.00 0.00))
 (command "TEXT" "J" "ML" p1   0.75  0.00 "")
 (setq p1 (list 339.75 1527.22) p2 (list 0.00 0.00))
 (command "TEXT" "J" "ML" p1   0.75  0.00 "6951")
 (command "LAYER" "S" "CGBLITHTXT" "")
 (setq p1 (list 343.50 1527.22) p2 (list 0.00 0.00))
 (command "TEXT" "J" "ML" p1   0.75  0.00 "LT GRY GRN SH+INTERBED SS")
 (command "LAYER" "S" "CGBCMNT" "")
 (setq p1 (list 363.75 1527.22) p2 (list 0.00 0.00))
 (command "TEXT" "J" "ML" p1   0.75  0.00 "ABDNT BURS")
 (command "LAYER" "S" "CGBMAIN" "")
 (setq p1 (list 321.00 1525.28) p2 (list 327.00 1525.28) p3 (list 327.00 1524.72) p4 (list 321.00 1524.72))
 (command "PLINE" p1 p2 p3 p4 "c")
 (command "HATCH" "ZIGZAG" 4.00 0.00 "L" "")
 (command "COLOR" "BYLAYER")
 (command "LAYER" "S" "CGBLITHCD" "")
 (setq p1 (list 327.00 1525.00) p2 (list 328.35 1525.00))
 (command "LINE" p1 p2 "")
 (setq p1 (list 328.50 1524.63) p2 (list 0.00 0.00))
 (command "TEXT" "J" "ML" p1   0.75  0.00 "563")
 (command "LAYER" "S" "CGBTHK" "")
 (setq p1 (list 333.00 1524.63) p2 (list 0.00 0.00))
 (command "TEXT" "J" "ML" p1   0.75  0.00 "0.56")
 (command "LAYER" "S" "CGBHZID" "")
 (setq p1 (list 337.50 1524.63) p2 (list 0.00 0.00))
 (command "TEXT" "J" "ML" p1   0.75  0.00 "")
 (setq p1 (list 339.75 1524.63) p2 (list 0.00 0.00))
 (command "TEXT" "J" "ML" p1   0.75  0.00 "6700")
 (command "LAYER" "S" "CGBLITHTXT" "")
 (setq p1 (list 343.50 1524.63) p2 (list 0.00 0.00))
 (command "TEXT" "J" "ML" p1   0.75  0.00 "HARD SS W/SH STKS")
 (command "LAYER" "S" "CGBCMNT" "")
 (setq p1 (list 363.75 1524.63) p2 (list 0.00 0.00))
 (command "TEXT" "J" "ML" p1   0.75  0.00 "SLC")
 (command "LAYER" "S" "CGBMAIN" "")
 (setq p1 (list 321.00 1524.72) p2 (list 327.00 1524.72) p3 (list 327.00 1518.56) p4 (list 321.00 1518.56))
 (command "PLINE" p1 p2 p3 p4 "c")
 (command "HATCH" "ZIGZAG" 5.00 0.00 "L" "")
 (command "COLOR" "BYLAYER")
 (command "LAYER" "S" "CGBLITHCD" "")
 (setq p1 (list 327.00 1521.64) p2 (list 328.35 1521.64))
 (command "LINE" p1 p2 "")
 (setq p1 (list 328.50 1521.27) p2 (list 0.00 0.00))
 (command "TEXT" "J" "ML" p1   0.75  0.00 "332")
 (command "LAYER" "S" "CGBTHK" "")
 (setq p1 (list 333.00 1521.27) p2 (list 0.00 0.00))
 (command "TEXT" "J" "ML" p1   0.75  0.00 "6.16")
 (command "LAYER" "S" "CGBHZID" "")
 (setq p1 (list 337.50 1521.27) p2 (list 0.00 0.00))
 (command "TEXT" "J" "ML" p1   0.75  0.00 "")
 (setq p1 (list 339.75 1521.27) p2 (list 0.00 0.00))
 (command "TEXT" "J" "ML" p1   0.75  0.00 "6651")
 (command "LAYER" "S" "CGBLITHTXT" "")
 (setq p1 (list 343.50 1521.27) p2 (list 0.00 0.00))
 (command "TEXT" "J" "ML" p1   0.75  0.00 "LT GRY GRN SH+INTERBED SS")
 (command "LAYER" "S" "CGBCMNT" "")
 (setq p1 (list 363.75 1521.27) p2 (list 0.00 0.00))
 (command "TEXT" "J" "ML" p1   0.75  0.00 "INTERBEDS SFT")
 (command "LAYER" "S" "CGBMAIN" "")
 (setq p1 (list 321.00 1518.56) p2 (list 327.00 1518.56) p3 (list 327.00 1517.97) p4 (list 321.00 1517.97))
 (command "PLINE" p1 p2 p3 p4 "c")
 (command "HATCH" "ZIGZAG" 2.50 90.00 "L" "")
 (command "COLOR" "BYLAYER")
 (command "LAYER" "S" "CGBLITHCD" "")
 (setq p1 (list 327.00 1518.27) p2 (list 328.35 1518.27))
 (command "LINE" p1 p2 "")
 (setq p1 (list 328.50 1517.89) p2 (list 0.00 0.00))
 (command "TEXT" "J" "ML" p1   0.75  0.00 "328")
 (command "LAYER" "S" "CGBTHK" "")
 (setq p1 (list 333.00 1517.89) p2 (list 0.00 0.00))
 (command "TEXT" "J" "ML" p1   0.75  0.00 "0.59")
 (command "LAYER" "S" "CGBHZID" "")
 (setq p1 (list 337.50 1517.89) p2 (list 0.00 0.00))
 (command "TEXT" "J" "ML" p1   0.75  0.00 "")
 (setq p1 (list 339.75 1517.89) p2 (list 0.00 0.00))
 (command "TEXT" "J" "ML" p1   0.75  0.00 "6651")
 (command "LAYER" "S" "CGBLITHTXT" "")
 (setq p1 (list 343.50 1517.89) p2 (list 0.00 0.00))
 (command "TEXT" "J" "ML" p1   0.75  0.00 "DRK GRY BURROWED SDY SH")
 (command "LAYER" "S" "CGBCMNT" "")
 (setq p1 (list 363.75 1517.89) p2 (list 0.00 0.00))
 (command "TEXT" "J" "ML" p1   0.75  0.00 "SFT, ANG BEDS")
 (command "LAYER" "S" "CGBMAIN" "")
 (setq p1 (list 321.00 1517.97) p2 (list 327.00 1517.97) p3 (list 327.00 1514.52) p4 (list 321.00 1514.52))
 (command "PLINE" p1 p2 p3 p4 "c")
 (command "HATCH" "ZIGZAG" 5.00 0.00 "L" "")
 (command "COLOR" "BYLAYER")
 (command "LAYER" "S" "CGBLITHCD" "")
 (setq p1 (list 327.00 1516.25) p2 (list 328.35 1516.25))
 (command "LINE" p1 p2 "")
 (setq p1 (list 328.50 1515.87) p2 (list 0.00 0.00))
 (command "TEXT" "J" "ML" p1   0.75  0.00 "322")
 (command "LAYER" "S" "CGBTHK" "")
 (setq p1 (list 333.00 1515.87) p2 (list 0.00 0.00))
 (command "TEXT" "J" "ML" p1   0.75  0.00 "3.45")
 (command "LAYER" "S" "CGBHZID" "")
 (setq p1 (list 337.50 1515.87) p2 (list 0.00 0.00))
 (command "TEXT" "J" "ML" p1   0.75  0.00 "")
 (setq p1 (list 339.75 1515.87) p2 (list 0.00 0.00))
 (command "TEXT" "J" "ML" p1   0.75  0.00 "6651")
 (command "LAYER" "S" "CGBLITHTXT" "")
 (setq p1 (list 343.50 1515.87) p2 (list 0.00 0.00))
 (command "TEXT" "J" "ML" p1   0.75  0.00 "DRK GRY SH+INTERBED SS")
 (command "LAYER" "S" "CGBCMNT" "")
 (setq p1 (list 363.75 1515.87) p2 (list 0.00 0.00))
 (command "TEXT" "J" "ML" p1   0.75  0.00 "SHLY BEDS SFT")
 (command "LAYER" "S" "CGBMAIN" "")
 (setq p1 (list 321.00 1514.52) p2 (list 327.00 1514.52) p3 (list 327.00 1513.74) p4 (list 321.00 1513.74))
 (command "PLINE" p1 p2 p3 p4 "c")
 (command "HATCH" "ZIGZAG" 2.00 45.00 "L" "")
 (command "COLOR" "BYLAYER")
 (command "LAYER" "S" "CGBLITHCD" "")
 (setq p1 (list 327.00 1514.13) p2 (list 328.35 1514.13))
 (command "LINE" p1 p2 "")
 (setq p1 (list 328.50 1513.76) p2 (list 0.00 0.00))
 (command "TEXT" "J" "ML" p1   0.75  0.00 "312")
 (command "LAYER" "S" "CGBTHK" "")
 (setq p1 (list 333.00 1513.76) p2 (list 0.00 0.00))
 (command "TEXT" "J" "ML" p1   0.75  0.00 "0.78")
 (command "LAYER" "S" "CGBHZID" "")
 (setq p1 (list 337.50 1513.76) p2 (list 0.00 0.00))
 (command "TEXT" "J" "ML" p1   0.75  0.00 "")
 (setq p1 (list 339.75 1513.76) p2 (list 0.00 0.00))
 (command "TEXT" "J" "ML" p1   0.75  0.00 "6651")
 (command "LAYER" "S" "CGBLITHTXT" "")
 (setq p1 (list 343.50 1513.76) p2 (list 0.00 0.00))
 (command "TEXT" "J" "ML" p1   0.75  0.00 "BLK SH+INTERBED SS")
 (command "LAYER" "S" "CGBCMNT" "")
 (setq p1 (list 363.75 1513.76) p2 (list 0.00 0.00))
 (command "TEXT" "J" "ML" p1   0.75  0.00 "BRKN W/SLX")
 (command "LAYER" "S" "CGBMAIN" "")
 (setq p1 (list 321.00 1513.74) p2 (list 327.00 1513.74) p3 (list 327.00 1512.14) p4 (list 321.00 1512.14))
 (command "PLINE" p1 p2 p3 p4 "c")
 (command "HATCH" "ZIGZAG" 4.00 0.00 "L" "")
 (command "COLOR" "BYLAYER")
 (command "LAYER" "S" "CGBLITHCD" "")
 (setq p1 (list 327.00 1512.94) p2 (list 328.35 1511.69))
 (command "LINE" p1 p2 "")
 (setq p1 (list 328.50 1511.32) p2 (list 0.00 0.00))
 (command "TEXT" "J" "ML" p1   0.75  0.00 "122")
 (command "LAYER" "S" "CGBTHK" "")
 (setq p1 (list 333.00 1511.32) p2 (list 0.00 0.00))
 (command "TEXT" "J" "ML" p1   0.75  0.00 "1.60")
 (command "LAYER" "S" "CGBHZID" "")
 (setq p1 (list 337.50 1511.32) p2 (list 0.00 0.00))
 (command "TEXT" "J" "ML" p1   0.75  0.00 "")
 (setq p1 (list 339.75 1511.32) p2 (list 0.00 0.00))
 (command "TEXT" "J" "ML" p1   0.75  0.00 "6651")
 (command "LAYER" "S" "CGBLITHTXT" "")
 (setq p1 (list 343.50 1511.32) p2 (list 0.00 0.00))
 (command "TEXT" "J" "ML" p1   0.75  0.00 "DK GRY LAYERED SH")
 (command "LAYER" "S" "CGBCMNT" "")
 (setq p1 (list 363.75 1511.32) p2 (list 0.00 0.00))
 (command "TEXT" "J" "ML" p1   0.75  0.00 "BRKN W/ SLX")
 (command "LAYER" "S" "CGBMAIN" "")
 (setq p1 (list 321.00 1512.14) p2 (list 327.00 1512.14) p3 (list 327.00 1510.55) p4 (list 321.00 1510.55))
 (command "PLINE" p1 p2 p3 p4 "c")
 (command "HATCH" "ZIGZAG" 2.00 45.00 "L" "")
 (command "COLOR" "BYLAYER")
 (command "LAYER" "S" "CGBLITHCD" "")
 (setq p1 (list 327.00 1511.35) p2 (list 328.35 1510.44))
 (command "LINE" p1 p2 "")
 (setq p1 (list 328.50 1510.07) p2 (list 0.00 0.00))
 (command "TEXT" "J" "ML" p1   0.75  0.00 "312")
 (command "LAYER" "S" "CGBTHK" "")
 (setq p1 (list 333.00 1510.07) p2 (list 0.00 0.00))
 (command "TEXT" "J" "ML" p1   0.75  0.00 "1.59")
 (command "LAYER" "S" "CGBHZID" "")
 (setq p1 (list 337.50 1510.07) p2 (list 0.00 0.00))
 (command "TEXT" "J" "ML" p1   0.75  0.00 "")
 (setq p1 (list 339.75 1510.07) p2 (list 0.00 0.00))
 (command "TEXT" "J" "ML" p1   0.75  0.00 "6651")
 (command "LAYER" "S" "CGBLITHTXT" "")
 (setq p1 (list 343.50 1510.07) p2 (list 0.00 0.00))
 (command "TEXT" "J" "ML" p1   0.75  0.00 "BLK SH+INTERBED SS")
 (command "LAYER" "S" "CGBCMNT" "")
 (setq p1 (list 363.75 1510.07) p2 (list 0.00 0.00))
 (command "TEXT" "J" "ML" p1   0.75  0.00 "SLC, BURS, SF")
 (command "LAYER" "S" "CGBMAIN" "")
 (setq p1 (list 321.00 1510.55) p2 (list 327.00 1510.55) p3 (list 327.00 1509.16) p4 (list 321.00 1509.16))
 (command "PLINE" p1 p2 p3 p4 "c")
 (command "HATCH" "ZIGZAG" 4.00 0.00 "L" "")
 (command "COLOR" "BYLAYER")
 (command "LAYER" "S" "CGBLITHCD" "")
 (setq p1 (list 327.00 1509.86) p2 (list 328.35 1509.19))
 (command "LINE" p1 p2 "")
 (setq p1 (list 328.50 1508.82) p2 (list 0.00 0.00))
 (command "TEXT" "J" "ML" p1   0.75  0.00 "124")
 (command "LAYER" "S" "CGBTHK" "")
 (setq p1 (list 333.00 1508.82) p2 (list 0.00 0.00))
 (command "TEXT" "J" "ML" p1   0.75  0.00 "1.39")
 (command "LAYER" "S" "CGBHZID" "")
 (setq p1 (list 337.50 1508.82) p2 (list 0.00 0.00))
 (command "TEXT" "J" "ML" p1   0.75  0.00 "")
 (setq p1 (list 339.75 1508.82) p2 (list 0.00 0.00))
 (command "TEXT" "J" "ML" p1   0.75  0.00 "6351")
 (command "LAYER" "S" "CGBLITHTXT" "")
 (setq p1 (list 343.50 1508.82) p2 (list 0.00 0.00))
 (command "TEXT" "J" "ML" p1   0.75  0.00 "DRK GRY SH")
 (command "LAYER" "S" "CGBCMNT" "")
 (setq p1 (list 363.75 1508.82) p2 (list 0.00 0.00))
 (command "TEXT" "J" "ML" p1   0.75  0.00 "DRK,BRKN @ BA")
 (command "LAYER" "S" "CGBMAIN" "")
 (command "LAYER" "S" "CGBLITHCD" "")
 (setq p1 (list 327.00 1509.16) p2 (list 328.35 1507.94))
 (command "LINE" p1 p2 "")
 (setq p1 (list 328.50 1507.57) p2 (list 0.00 0.00))
 (command "TEXT" "J" "ML" p1   0.75  0.00 "500")
 (command "LAYER" "S" "CGBTHK" "")
 (setq p1 (list 333.00 1507.57) p2 (list 0.00 0.00))
 (command "TEXT" "J" "ML" p1   0.75  0.00 "0.00")
 (command "LAYER" "S" "CGBHZID" "")
 (setq p1 (list 337.50 1507.57) p2 (list 0.00 0.00))
 (command "TEXT" "J" "ML" p1   0.75  0.00 "")
 (setq p1 (list 339.75 1507.57) p2 (list 0.00 0.00))
 (command "TEXT" "J" "ML" p1   0.75  0.00 "6400")
 (command "LAYER" "S" "CGBLITHTXT" "")
 (setq p1 (list 343.50 1507.57) p2 (list 0.00 0.00))
 (command "TEXT" "J" "ML" p1   0.75  0.00 "SS")
 (command "LAYER" "S" "CGBCMNT" "")
 (setq p1 (list 363.75 1507.57) p2 (list 0.00 0.00))
 (command "TEXT" "J" "ML" p1   0.75  0.00 "")
 (command "LAYER" "S" "CGBMAIN" "")
 (setq p1 (list 321.00 1509.16) p2 (list 327.00 1509.16) p3 (list 327.00 1507.56) p4 (list 321.00 1507.56))
 (command "PLINE" p1 p2 p3 p4 "c")
 (command "HATCH" "ZIGZAG" 4.00 22.50 "L" "")
 (command "COLOR" "BYLAYER")
 (command "LAYER" "S" "CGBLITHCD" "")
 (setq p1 (list 327.00 1508.36) p2 (list 328.35 1506.69))
 (command "LINE" p1 p2 "")
 (setq p1 (list 328.50 1506.32) p2 (list 0.00 0.00))
 (command "TEXT" "J" "ML" p1   0.75  0.00 "114")
 (command "LAYER" "S" "CGBTHK" "")
 (setq p1 (list 333.00 1506.32) p2 (list 0.00 0.00))
 (command "TEXT" "J" "ML" p1   0.75  0.00 "1.60")
 (command "LAYER" "S" "CGBHZID" "")
 (setq p1 (list 337.50 1506.32) p2 (list 0.00 0.00))
 (command "TEXT" "J" "ML" p1   0.75  0.00 "")
 (setq p1 (list 339.75 1506.32) p2 (list 0.00 0.00))
 (command "TEXT" "J" "ML" p1   0.75  0.00 "6351")
 (command "LAYER" "S" "CGBLITHTXT" "")
 (setq p1 (list 343.50 1506.32) p2 (list 0.00 0.00))
 (command "TEXT" "J" "ML" p1   0.75  0.00 "BLK SH")
 (command "LAYER" "S" "CGBCMNT" "")
 (setq p1 (list 363.75 1506.32) p2 (list 0.00 0.00))
 (command "TEXT" "J" "ML" p1   0.75  0.00 "BRKN,SLX,PYT")
 (command "LAYER" "S" "CGBMAIN" "")
 (setq p1 (list 321.00 1507.56) p2 (list 327.00 1507.56) p3 (list 327.00 1507.23) p4 (list 321.00 1507.23))
 (command "PLINE" p1 p2 p3 p4 "c")
 (command "HATCH" "ZIGZAG" 0.40 45.00 "L" "")
 (command "COLOR" "BYLAYER")
 (command "LAYER" "S" "CGBLITHCD" "")
 (setq p1 (list 327.00 1507.40) p2 (list 328.35 1505.44))
 (command "LINE" p1 p2 "")
 (setq p1 (list 328.50 1505.07) p2 (list 0.00 0.00))
 (command "TEXT" "J" "ML" p1   0.75  0.00 "023")
 (command "LAYER" "S" "CGBTHK" "")
 (setq p1 (list 333.00 1505.07) p2 (list 0.00 0.00))
 (command "TEXT" "J" "ML" p1   0.75  0.00 "0.33")
 (command "LAYER" "S" "CGBHZID" "")
 (setq p1 (list 337.50 1505.07) p2 (list 0.00 0.00))
 (command "TEXT" "J" "ML" p1   0.75  0.00 "")
 (setq p1 (list 339.75 1505.07) p2 (list 0.00 0.00))
 (command "TEXT" "J" "ML" p1   0.75  0.00 "6000")
 (command "LAYER" "S" "CGBLITHTXT" "")
 (setq p1 (list 343.50 1505.07) p2 (list 0.00 0.00))
 (command "TEXT" "J" "ML" p1   0.75  0.00 "COAL W/BONE STKS")
 (command "LAYER" "S" "CGBCMNT" "")
 (setq p1 (list 363.75 1505.07) p2 (list 0.00 0.00))
 (command "TEXT" "J" "ML" p1   0.75  0.00 "PYRT ABDNT")
 (command "LAYER" "S" "CGBMAIN" "")
 (setq p1 (list 321.00 1507.23) p2 (list 327.00 1507.23) p3 (list 327.00 1507.05) p4 (list 321.00 1507.05))
 (command "PLINE" p1 p2 p3 p4 "c")
 (command "HATCH" "ZIGZAG" 4.00 22.50 "L" "")
 (command "COLOR" "BYLAYER")
 (command "LAYER" "S" "CGBLITHCD" "")
 (setq p1 (list 327.00 1507.14) p2 (list 328.35 1504.19))
 (command "LINE" p1 p2 "")
 (setq p1 (list 328.50 1503.82) p2 (list 0.00 0.00))
 (command "TEXT" "J" "ML" p1   0.75  0.00 "114")
 (command "LAYER" "S" "CGBTHK" "")
 (setq p1 (list 333.00 1503.82) p2 (list 0.00 0.00))
 (command "TEXT" "J" "ML" p1   0.75  0.00 "0.18")
 (command "LAYER" "S" "CGBHZID" "")
 (setq p1 (list 337.50 1503.82) p2 (list 0.00 0.00))
 (command "TEXT" "J" "ML" p1   0.75  0.00 "")
 (setq p1 (list 339.75 1503.82) p2 (list 0.00 0.00))
 (command "TEXT" "J" "ML" p1   0.75  0.00 "6000")
 (command "LAYER" "S" "CGBLITHTXT" "")
 (setq p1 (list 343.50 1503.82) p2 (list 0.00 0.00))
 (command "TEXT" "J" "ML" p1   0.75  0.00 "BLK SH")
 (command "LAYER" "S" "CGBCMNT" "")
 (setq p1 (list 363.75 1503.82) p2 (list 0.00 0.00))
 (command "TEXT" "J" "ML" p1   0.75  0.00 "DULL W/ PYRT")
 (command "LAYER" "S" "CGBMAIN" "")
 (setq p1 (list 321.00 1507.05) p2 (list 327.00 1507.05) p3 (list 327.00 1506.55) p4 (list 321.00 1506.55))
 (command "PLINE" p1 p2 p3 p4 "c")
 (command "HATCH" "ZIGZAG" 1.00 45.00 "L" "")
 (command "COLOR" "BYLAYER")
 (command "LAYER" "S" "CGBLITHCD" "")
 (setq p1 (list 327.00 1506.80) p2 (list 328.35 1502.94))
 (command "LINE" p1 p2 "")
 (setq p1 (list 328.50 1502.57) p2 (list 0.00 0.00))
 (command "TEXT" "J" "ML" p1   0.75  0.00 "028")
 (command "LAYER" "S" "CGBTHK" "")
 (setq p1 (list 333.00 1502.57) p2 (list 0.00 0.00))
 (command "TEXT" "J" "ML" p1   0.75  0.00 "0.50")
 (command "LAYER" "S" "CGBHZID" "")
 (setq p1 (list 337.50 1502.57) p2 (list 0.00 0.00))
 (command "TEXT" "J" "ML" p1   0.75  0.00 "")
 (setq p1 (list 339.75 1502.57) p2 (list 0.00 0.00))
 (command "TEXT" "J" "ML" p1   0.75  0.00 "6000")
 (command "LAYER" "S" "CGBLITHTXT" "")
 (setq p1 (list 343.50 1502.57) p2 (list 0.00 0.00))
 (command "TEXT" "J" "ML" p1   0.75  0.00 "COAL W/SH STKS")
 (command "LAYER" "S" "CGBCMNT" "")
 (setq p1 (list 363.75 1502.57) p2 (list 0.00 0.00))
 (command "TEXT" "J" "ML" p1   0.75  0.00 "DULL W PYRT")
 (command "LAYER" "S" "CGBMAIN" "")
 (setq p1 (list 321.00 1506.55) p2 (list 327.00 1506.55) p3 (list 327.00 1505.29) p4 (list 321.00 1505.29))
 (command "PLINE" p1 p2 p3 p4 "c")
 (command "COLOR" "BLUE")
 (command "SOLID" p1 p2 p4 p3 "")
 (command "COLOR" "BYLAYER")
 (command "LAYER" "S" "CGBLITHCD" "")
 (setq p1 (list 327.00 1505.92) p2 (list 328.35 1501.69))
 (command "LINE" p1 p2 "")
 (setq p1 (list 328.50 1501.32) p2 (list 0.00 0.00))
 (command "TEXT" "J" "ML" p1   0.75  0.00 "021")
 (command "LAYER" "S" "CGBTHK" "")
 (setq p1 (list 333.00 1501.32) p2 (list 0.00 0.00))
 (command "TEXT" "J" "ML" p1   0.75  0.00 "1.26")
 (command "LAYER" "S" "CGBHZID" "")
 (setq p1 (list 337.50 1501.32) p2 (list 0.00 0.00))
 (command "TEXT" "J" "ML" p1   0.75  0.00 "")
 (setq p1 (list 339.75 1501.32) p2 (list 0.00 0.00))
 (command "TEXT" "J" "ML" p1   0.75  0.00 "6000")
 (command "LAYER" "S" "CGBLITHTXT" "")
 (setq p1 (list 343.50 1501.32) p2 (list 0.00 0.00))
 (command "TEXT" "J" "ML" p1   0.75  0.00 "COMMON BANDED COAL")
 (command "LAYER" "S" "CGBCMNT" "")
 (setq p1 (list 363.75 1501.32) p2 (list 0.00 0.00))
 (command "TEXT" "J" "ML" p1   0.75  0.00 "CRMBLD VITRAI")
 (command "LAYER" "S" "CGBMAIN" "")
 (setq p1 (list 321.00 1505.29) p2 (list 327.00 1505.29) p3 (list 327.00 1505.25) p4 (list 321.00 1505.25))
 (command "PLINE" p1 p2 p3 p4 "c")
 (command "HATCH" "ZIGZAG" 0.30 0.00 "L" "")
 (command "COLOR" "BYLAYER")
 (command "LAYER" "S" "CGBLITHCD" "")
 (setq p1 (list 327.00 1505.27) p2 (list 328.35 1500.44))
 (command "LINE" p1 p2 "")
 (setq p1 (list 328.50 1500.07) p2 (list 0.00 0.00))
 (command "TEXT" "J" "ML" p1   0.75  0.00 "034")
 (command "LAYER" "S" "CGBTHK" "")
 (setq p1 (list 333.00 1500.07) p2 (list 0.00 0.00))
 (command "TEXT" "J" "ML" p1   0.75  0.00 "0.04")
 (command "LAYER" "S" "CGBHZID" "")
 (setq p1 (list 337.50 1500.07) p2 (list 0.00 0.00))
 (command "TEXT" "J" "ML" p1   0.75  0.00 "")
 (setq p1 (list 339.75 1500.07) p2 (list 0.00 0.00))
 (command "TEXT" "J" "ML" p1   0.75  0.00 "6000")
 (command "LAYER" "S" "CGBLITHTXT" "")
 (setq p1 (list 343.50 1500.07) p2 (list 0.00 0.00))
 (command "TEXT" "J" "ML" p1   0.75  0.00 "BONE")
 (command "LAYER" "S" "CGBCMNT" "")
 (setq p1 (list 363.75 1500.07) p2 (list 0.00 0.00))
 (command "TEXT" "J" "ML" p1   0.75  0.00 "DULL")
 (command "LAYER" "S" "CGBMAIN" "")
 (setq p1 (list 321.00 1505.25) p2 (list 327.00 1505.25) p3 (list 327.00 1505.18) p4 (list 321.00 1505.18))
 (command "PLINE" p1 p2 p3 p4 "c")
 (command "COLOR" "BLUE")
 (command "SOLID" p1 p2 p4 p3 "")
 (command "COLOR" "BYLAYER")
 (command "LAYER" "S" "CGBLITHCD" "")
 (setq p1 (list 327.00 1505.22) p2 (list 328.35 1499.19))
 (command "LINE" p1 p2 "")
 (setq p1 (list 328.50 1498.82) p2 (list 0.00 0.00))
 (command "TEXT" "J" "ML" p1   0.75  0.00 "021")
 (command "LAYER" "S" "CGBTHK" "")
 (setq p1 (list 333.00 1498.82) p2 (list 0.00 0.00))
 (command "TEXT" "J" "ML" p1   0.75  0.00 "0.07")
 (command "LAYER" "S" "CGBHZID" "")
 (setq p1 (list 337.50 1498.82) p2 (list 0.00 0.00))
 (command "TEXT" "J" "ML" p1   0.75  0.00 "")
 (setq p1 (list 339.75 1498.82) p2 (list 0.00 0.00))
 (command "TEXT" "J" "ML" p1   0.75  0.00 "6000")
 (command "LAYER" "S" "CGBLITHTXT" "")
 (setq p1 (list 343.50 1498.82) p2 (list 0.00 0.00))
 (command "TEXT" "J" "ML" p1   0.75  0.00 "COMMON BANDED COAL")
 (command "LAYER" "S" "CGBCMNT" "")
 (setq p1 (list 363.75 1498.82) p2 (list 0.00 0.00))
 (command "TEXT" "J" "ML" p1   0.75  0.00 "THK VIT BND")
 (command "LAYER" "S" "CGBMAIN" "")
 (setq p1 (list 321.00 1505.18) p2 (list 327.00 1505.18) p3 (list 327.00 1505.08) p4 (list 321.00 1505.08))
 (command "PLINE" p1 p2 p3 p4 "c")
 (command "HATCH" "ZIGZAG" 4.00 22.50 "L" "")
 (command "COLOR" "BYLAYER")
 (command "LAYER" "S" "CGBLITHCD" "")
 (setq p1 (list 327.00 1505.13) p2 (list 328.35 1497.94))
 (command "LINE" p1 p2 "")
 (setq p1 (list 328.50 1497.57) p2 (list 0.00 0.00))
 (command "TEXT" "J" "ML" p1   0.75  0.00 "114")
 (command "LAYER" "S" "CGBTHK" "")
 (setq p1 (list 333.00 1497.57) p2 (list 0.00 0.00))
 (command "TEXT" "J" "ML" p1   0.75  0.00 "0.10")
 (command "LAYER" "S" "CGBHZID" "")
 (setq p1 (list 337.50 1497.57) p2 (list 0.00 0.00))
 (command "TEXT" "J" "ML" p1   0.75  0.00 "")
 (setq p1 (list 339.75 1497.57) p2 (list 0.00 0.00))
 (command "TEXT" "J" "ML" p1   0.75  0.00 "6000")
 (command "LAYER" "S" "CGBLITHTXT" "")
 (setq p1 (list 343.50 1497.57) p2 (list 0.00 0.00))
 (command "TEXT" "J" "ML" p1   0.75  0.00 "BLK SH")
 (command "LAYER" "S" "CGBCMNT" "")
 (setq p1 (list 363.75 1497.57) p2 (list 0.00 0.00))
 (command "TEXT" "J" "ML" p1   0.75  0.00 "DULL, BONEY")
 (command "LAYER" "S" "CGBMAIN" "")
 (setq p1 (list 321.00 1505.08) p2 (list 327.00 1505.08) p3 (list 327.00 1504.84) p4 (list 321.00 1504.84))
 (command "PLINE" p1 p2 p3 p4 "c")
 (command "HATCH" "ZIGZAG" 0.40 45.00 "L" "")
 (command "COLOR" "BYLAYER")
 (command "LAYER" "S" "CGBLITHCD" "")
 (setq p1 (list 327.00 1504.96) p2 (list 328.35 1496.69))
 (command "LINE" p1 p2 "")
 (setq p1 (list 328.50 1496.32) p2 (list 0.00 0.00))
 (command "TEXT" "J" "ML" p1   0.75  0.00 "023")
 (command "LAYER" "S" "CGBTHK" "")
 (setq p1 (list 333.00 1496.32) p2 (list 0.00 0.00))
 (command "TEXT" "J" "ML" p1   0.75  0.00 "0.24")
 (command "LAYER" "S" "CGBHZID" "")
 (setq p1 (list 337.50 1496.32) p2 (list 0.00 0.00))
 (command "TEXT" "J" "ML" p1   0.75  0.00 "")
 (setq p1 (list 339.75 1496.32) p2 (list 0.00 0.00))
 (command "TEXT" "J" "ML" p1   0.75  0.00 "6000")
 (command "LAYER" "S" "CGBLITHTXT" "")
 (setq p1 (list 343.50 1496.32) p2 (list 0.00 0.00))
 (command "TEXT" "J" "ML" p1   0.75  0.00 "COAL W/BONE STKS")
 (command "LAYER" "S" "CGBCMNT" "")
 (setq p1 (list 363.75 1496.32) p2 (list 0.00 0.00))
 (command "TEXT" "J" "ML" p1   0.75  0.00 "DULL W FEW VI")
 (command "LAYER" "S" "CGBMAIN" "")
 (setq p1 (list 321.00 1504.84) p2 (list 327.00 1504.84) p3 (list 327.00 1504.73) p4 (list 321.00 1504.73))
 (command "PLINE" p1 p2 p3 p4 "c")
 (command "HATCH" "ZIGZAG" 4.00 22.50 "L" "")
 (command "COLOR" "BYLAYER")
 (command "LAYER" "S" "CGBLITHCD" "")
 (setq p1 (list 327.00 1504.79) p2 (list 328.35 1495.44))
 (command "LINE" p1 p2 "")
 (setq p1 (list 328.50 1495.07) p2 (list 0.00 0.00))
 (command "TEXT" "J" "ML" p1   0.75  0.00 "114")
 (command "LAYER" "S" "CGBTHK" "")
 (setq p1 (list 333.00 1495.07) p2 (list 0.00 0.00))
 (command "TEXT" "J" "ML" p1   0.75  0.00 "0.11")
 (command "LAYER" "S" "CGBHZID" "")
 (setq p1 (list 337.50 1495.07) p2 (list 0.00 0.00))
 (command "TEXT" "J" "ML" p1   0.75  0.00 "")
 (setq p1 (list 339.75 1495.07) p2 (list 0.00 0.00))
 (command "TEXT" "J" "ML" p1   0.75  0.00 "5951")
 (command "LAYER" "S" "CGBLITHTXT" "")
 (setq p1 (list 343.50 1495.07) p2 (list 0.00 0.00))
 (command "TEXT" "J" "ML" p1   0.75  0.00 "BLK SH")
 (command "LAYER" "S" "CGBCMNT" "")
 (setq p1 (list 363.75 1495.07) p2 (list 0.00 0.00))
 (command "TEXT" "J" "ML" p1   0.75  0.00 "DULL BONEY")
 (command "LAYER" "S" "CGBMAIN" "")
 (setq p1 (list 321.00 1504.73) p2 (list 327.00 1504.73) p3 (list 327.00 1504.68) p4 (list 321.00 1504.68))
 (command "PLINE" p1 p2 p3 p4 "c")
 (command "COLOR" "BLUE")
 (command "SOLID" p1 p2 p4 p3 "")
 (command "COLOR" "BYLAYER")
 (command "LAYER" "S" "CGBLITHCD" "")
 (setq p1 (list 327.00 1504.71) p2 (list 328.35 1494.19))
 (command "LINE" p1 p2 "")
 (setq p1 (list 328.50 1493.82) p2 (list 0.00 0.00))
 (command "TEXT" "J" "ML" p1   0.75  0.00 "021")
 (command "LAYER" "S" "CGBTHK" "")
 (setq p1 (list 333.00 1493.82) p2 (list 0.00 0.00))
 (command "TEXT" "J" "ML" p1   0.75  0.00 "0.05")
 (command "LAYER" "S" "CGBHZID" "")
 (setq p1 (list 337.50 1493.82) p2 (list 0.00 0.00))
 (command "TEXT" "J" "ML" p1   0.75  0.00 "")
 (setq p1 (list 339.75 1493.82) p2 (list 0.00 0.00))
 (command "TEXT" "J" "ML" p1   0.75  0.00 "5951")
 (command "LAYER" "S" "CGBLITHTXT" "")
 (setq p1 (list 343.50 1493.82) p2 (list 0.00 0.00))
 (command "TEXT" "J" "ML" p1   0.75  0.00 "COMMON BANDED COAL")
 (command "LAYER" "S" "CGBCMNT" "")
 (setq p1 (list 363.75 1493.82) p2 (list 0.00 0.00))
 (command "TEXT" "J" "ML" p1   0.75  0.00 "THK VIT BND")
 (command "LAYER" "S" "CGBMAIN" "")
 (setq p1 (list 321.00 1504.68) p2 (list 327.00 1504.68) p3 (list 327.00 1504.03) p4 (list 321.00 1504.03))
 (command "PLINE" p1 p2 p3 p4 "c")
 (command "HATCH" "ZIGZAG" 6.00 0.00 "L" "")
 (command "COLOR" "BYLAYER")
 (command "LAYER" "S" "CGBLITHCD" "")
 (setq p1 (list 327.00 1504.36) p2 (list 328.35 1492.94))
 (command "LINE" p1 p2 "")
 (setq p1 (list 328.50 1492.57) p2 (list 0.00 0.00))
 (command "TEXT" "J" "ML" p1   0.75  0.00 "113")
 (command "LAYER" "S" "CGBTHK" "")
 (setq p1 (list 333.00 1492.57) p2 (list 0.00 0.00))
 (command "TEXT" "J" "ML" p1   0.75  0.00 "0.65")
 (command "LAYER" "S" "CGBHZID" "")
 (setq p1 (list 337.50 1492.57) p2 (list 0.00 0.00))
 (command "TEXT" "J" "ML" p1   0.75  0.00 "")
 (setq p1 (list 339.75 1492.57) p2 (list 0.00 0.00))
 (command "TEXT" "J" "ML" p1   0.75  0.00 "5951")
 (command "LAYER" "S" "CGBLITHTXT" "")
 (setq p1 (list 343.50 1492.57) p2 (list 0.00 0.00))
 (command "TEXT" "J" "ML" p1   0.75  0.00 "BLK SH W/COAL STKS")
 (command "LAYER" "S" "CGBCMNT" "")
 (setq p1 (list 363.75 1492.57) p2 (list 0.00 0.00))
 (command "TEXT" "J" "ML" p1   0.75  0.00 "DULL W/THIN S")
 (command "LAYER" "S" "CGBMAIN" "")
 (setq p1 (list 321.00 1504.03) p2 (list 327.00 1504.03) p3 (list 327.00 1503.37) p4 (list 321.00 1503.37))
 (command "PLINE" p1 p2 p3 p4 "c")
 (command "COLOR" "BLUE")
 (command "SOLID" p1 p2 p4 p3 "")
 (command "COLOR" "BYLAYER")
 (command "LAYER" "S" "CGBLITHCD" "")
 (setq p1 (list 327.00 1503.70) p2 (list 328.35 1491.69))
 (command "LINE" p1 p2 "")
 (setq p1 (list 328.50 1491.32) p2 (list 0.00 0.00))
 (command "TEXT" "J" "ML" p1   0.75  0.00 "021")
 (command "LAYER" "S" "CGBTHK" "")
 (setq p1 (list 333.00 1491.32) p2 (list 0.00 0.00))
 (command "TEXT" "J" "ML" p1   0.75  0.00 "0.66")
 (command "LAYER" "S" "CGBHZID" "")
 (setq p1 (list 337.50 1491.32) p2 (list 0.00 0.00))
 (command "TEXT" "J" "ML" p1   0.75  0.00 "")
 (setq p1 (list 339.75 1491.32) p2 (list 0.00 0.00))
 (command "TEXT" "J" "ML" p1   0.75  0.00 "5500")
 (command "LAYER" "S" "CGBLITHTXT" "")
 (setq p1 (list 343.50 1491.32) p2 (list 0.00 0.00))
 (command "TEXT" "J" "ML" p1   0.75  0.00 "COMMON BANDED COAL")
 (command "LAYER" "S" "CGBCMNT" "")
 (setq p1 (list 363.75 1491.32) p2 (list 0.00 0.00))
 (command "TEXT" "J" "ML" p1   0.75  0.00 "GT, GB, MOST")
 (command "LAYER" "S" "CGBMAIN" "")
 (setq p1 (list 321.00 1503.37) p2 (list 327.00 1503.37) p3 (list 327.00 1503.20) p4 (list 321.00 1503.20))
 (command "PLINE" p1 p2 p3 p4 "c")
 (command "HATCH" "ZIGZAG" 0.30 0.00 "L" "")
 (command "COLOR" "BYLAYER")
 (command "LAYER" "S" "CGBLITHCD" "")
 (setq p1 (list 327.00 1503.29) p2 (list 328.35 1490.44))
 (command "LINE" p1 p2 "")
 (setq p1 (list 328.50 1490.07) p2 (list 0.00 0.00))
 (command "TEXT" "J" "ML" p1   0.75  0.00 "034")
 (command "LAYER" "S" "CGBTHK" "")
 (setq p1 (list 333.00 1490.07) p2 (list 0.00 0.00))
 (command "TEXT" "J" "ML" p1   0.75  0.00 "0.17")
 (command "LAYER" "S" "CGBHZID" "")
 (setq p1 (list 337.50 1490.07) p2 (list 0.00 0.00))
 (command "TEXT" "J" "ML" p1   0.75  0.00 "")
 (setq p1 (list 339.75 1490.07) p2 (list 0.00 0.00))
 (command "TEXT" "J" "ML" p1   0.75  0.00 "5500")
 (command "LAYER" "S" "CGBLITHTXT" "")
 (setq p1 (list 343.50 1490.07) p2 (list 0.00 0.00))
 (command "TEXT" "J" "ML" p1   0.75  0.00 "BONE")
 (command "LAYER" "S" "CGBCMNT" "")
 (setq p1 (list 363.75 1490.07) p2 (list 0.00 0.00))
 (command "TEXT" "J" "ML" p1   0.75  0.00 "DULL")
 (command "LAYER" "S" "CGBMAIN" "")
 (setq p1 (list 321.00 1503.20) p2 (list 327.00 1503.20) p3 (list 327.00 1502.41) p4 (list 321.00 1502.41))
 (command "PLINE" p1 p2 p3 p4 "c")
 (command "HATCH" "ZIGZAG" 0.40 45.00 "L" "")
 (command "COLOR" "BYLAYER")
 (command "LAYER" "S" "CGBLITHCD" "")
 (setq p1 (list 327.00 1502.81) p2 (list 328.35 1489.19))
 (command "LINE" p1 p2 "")
 (setq p1 (list 328.50 1488.82) p2 (list 0.00 0.00))
 (command "TEXT" "J" "ML" p1   0.75  0.00 "022")
 (command "LAYER" "S" "CGBTHK" "")
 (setq p1 (list 333.00 1488.82) p2 (list 0.00 0.00))
 (command "TEXT" "J" "ML" p1   0.75  0.00 "0.79")
 (command "LAYER" "S" "CGBHZID" "")
 (setq p1 (list 337.50 1488.82) p2 (list 0.00 0.00))
 (command "TEXT" "J" "ML" p1   0.75  0.00 "")
 (setq p1 (list 339.75 1488.82) p2 (list 0.00 0.00))
 (command "TEXT" "J" "ML" p1   0.75  0.00 "5500")
 (command "LAYER" "S" "CGBLITHTXT" "")
 (setq p1 (list 343.50 1488.82) p2 (list 0.00 0.00))
 (command "TEXT" "J" "ML" p1   0.75  0.00 "COAL W/BONE LAYERS")
 (command "LAYER" "S" "CGBCMNT" "")
 (setq p1 (list 363.75 1488.82) p2 (list 0.00 0.00))
 (command "TEXT" "J" "ML" p1   0.75  0.00 "PYRT, DULL W/")
 (command "LAYER" "S" "CGBMAIN" "")
 (setq p1 (list 321.00 1502.41) p2 (list 327.00 1502.41) p3 (list 327.00 1502.26) p4 (list 321.00 1502.26))
 (command "PLINE" p1 p2 p3 p4 "c")
 (command "HATCH" "ZIGZAG" 0.30 0.00 "L" "")
 (command "COLOR" "BYLAYER")
 (command "LAYER" "S" "CGBLITHCD" "")
 (setq p1 (list 327.00 1502.34) p2 (list 328.35 1487.94))
 (command "LINE" p1 p2 "")
 (setq p1 (list 328.50 1487.57) p2 (list 0.00 0.00))
 (command "TEXT" "J" "ML" p1   0.75  0.00 "034")
 (command "LAYER" "S" "CGBTHK" "")
 (setq p1 (list 333.00 1487.57) p2 (list 0.00 0.00))
 (command "TEXT" "J" "ML" p1   0.75  0.00 "0.15")
 (command "LAYER" "S" "CGBHZID" "")
 (setq p1 (list 337.50 1487.57) p2 (list 0.00 0.00))
 (command "TEXT" "J" "ML" p1   0.75  0.00 "")
 (setq p1 (list 339.75 1487.57) p2 (list 0.00 0.00))
 (command "TEXT" "J" "ML" p1   0.75  0.00 "5500")
 (command "LAYER" "S" "CGBLITHTXT" "")
 (setq p1 (list 343.50 1487.57) p2 (list 0.00 0.00))
 (command "TEXT" "J" "ML" p1   0.75  0.00 "BONE")
 (command "LAYER" "S" "CGBCMNT" "")
 (setq p1 (list 363.75 1487.57) p2 (list 0.00 0.00))
 (command "TEXT" "J" "ML" p1   0.75  0.00 "BLCKY,DULL, G")
 (command "LAYER" "S" "CGBMAIN" "")
 (setq p1 (list 321.00 1502.26) p2 (list 327.00 1502.26) p3 (list 327.00 1501.71) p4 (list 321.00 1501.71))
 (command "PLINE" p1 p2 p3 p4 "c")
 (command "COLOR" "BLUE")
 (command "SOLID" p1 p2 p4 p3 "")
 (command "COLOR" "BYLAYER")
 (command "LAYER" "S" "CGBLITHCD" "")
 (setq p1 (list 327.00 1501.99) p2 (list 328.35 1486.69))
 (command "LINE" p1 p2 "")
 (setq p1 (list 328.50 1486.32) p2 (list 0.00 0.00))
 (command "TEXT" "J" "ML" p1   0.75  0.00 "021")
 (command "LAYER" "S" "CGBTHK" "")
 (setq p1 (list 333.00 1486.32) p2 (list 0.00 0.00))
 (command "TEXT" "J" "ML" p1   0.75  0.00 "0.55")
 (command "LAYER" "S" "CGBHZID" "")
 (setq p1 (list 337.50 1486.32) p2 (list 0.00 0.00))
 (command "TEXT" "J" "ML" p1   0.75  0.00 "")
 (setq p1 (list 339.75 1486.32) p2 (list 0.00 0.00))
 (command "TEXT" "J" "ML" p1   0.75  0.00 "5500")
 (command "LAYER" "S" "CGBLITHTXT" "")
 (setq p1 (list 343.50 1486.32) p2 (list 0.00 0.00))
 (command "TEXT" "J" "ML" p1   0.75  0.00 "COMMON BANDED COAL")
 (command "LAYER" "S" "CGBCMNT" "")
 (setq p1 (list 363.75 1486.32) p2 (list 0.00 0.00))
 (command "TEXT" "J" "ML" p1   0.75  0.00 "VIT W/DULL LA")
 (command "LAYER" "S" "CGBMAIN" "")
 (setq p1 (list 321.00 1501.71) p2 (list 327.00 1501.71) p3 (list 327.00 1501.50) p4 (list 321.00 1501.50))
 (command "PLINE" p1 p2 p3 p4 "c")
 (command "HATCH" "ZIGZAG" 0.30 0.00 "L" "")
 (command "COLOR" "BYLAYER")
 (command "LAYER" "S" "CGBLITHCD" "")
 (setq p1 (list 327.00 1501.61) p2 (list 328.35 1485.44))
 (command "LINE" p1 p2 "")
 (setq p1 (list 328.50 1485.07) p2 (list 0.00 0.00))
 (command "TEXT" "J" "ML" p1   0.75  0.00 "034")
 (command "LAYER" "S" "CGBTHK" "")
 (setq p1 (list 333.00 1485.07) p2 (list 0.00 0.00))
 (command "TEXT" "J" "ML" p1   0.75  0.00 "0.21")
 (command "LAYER" "S" "CGBHZID" "")
 (setq p1 (list 337.50 1485.07) p2 (list 0.00 0.00))
 (command "TEXT" "J" "ML" p1   0.75  0.00 "")
 (setq p1 (list 339.75 1485.07) p2 (list 0.00 0.00))
 (command "TEXT" "J" "ML" p1   0.75  0.00 "5500")
 (command "LAYER" "S" "CGBLITHTXT" "")
 (setq p1 (list 343.50 1485.07) p2 (list 0.00 0.00))
 (command "TEXT" "J" "ML" p1   0.75  0.00 "BONE")
 (command "LAYER" "S" "CGBCMNT" "")
 (setq p1 (list 363.75 1485.07) p2 (list 0.00 0.00))
 (command "TEXT" "J" "ML" p1   0.75  0.00 "DULL, GB")
 (command "LAYER" "S" "CGBMAIN" "")
 (setq p1 (list 321.00 1501.50) p2 (list 327.00 1501.50) p3 (list 327.00 1501.08) p4 (list 321.00 1501.08))
 (command "PLINE" p1 p2 p3 p4 "c")
 (command "HATCH" "ZIGZAG" 0.40 45.00 "L" "")
 (command "COLOR" "BYLAYER")
 (command "LAYER" "S" "CGBLITHCD" "")
 (setq p1 (list 327.00 1501.29) p2 (list 328.35 1484.19))
 (command "LINE" p1 p2 "")
 (setq p1 (list 328.50 1483.82) p2 (list 0.00 0.00))
 (command "TEXT" "J" "ML" p1   0.75  0.00 "023")
 (command "LAYER" "S" "CGBTHK" "")
 (setq p1 (list 333.00 1483.82) p2 (list 0.00 0.00))
 (command "TEXT" "J" "ML" p1   0.75  0.00 "0.42")
 (command "LAYER" "S" "CGBHZID" "")
 (setq p1 (list 337.50 1483.82) p2 (list 0.00 0.00))
 (command "TEXT" "J" "ML" p1   0.75  0.00 "")
 (setq p1 (list 339.75 1483.82) p2 (list 0.00 0.00))
 (command "TEXT" "J" "ML" p1   0.75  0.00 "5500")
 (command "LAYER" "S" "CGBLITHTXT" "")
 (setq p1 (list 343.50 1483.82) p2 (list 0.00 0.00))
 (command "TEXT" "J" "ML" p1   0.75  0.00 "COAL W/BONE STKS")
 (command "LAYER" "S" "CGBCMNT" "")
 (setq p1 (list 363.75 1483.82) p2 (list 0.00 0.00))
 (command "TEXT" "J" "ML" p1   0.75  0.00 "DULL W/VIT BN")
 (command "LAYER" "S" "CGBMAIN" "")
 (setq p1 (list 321.00 1501.08) p2 (list 327.00 1501.08) p3 (list 327.00 1500.95) p4 (list 321.00 1500.95))
 (command "PLINE" p1 p2 p3 p4 "c")
 (command "HATCH" "ZIGZAG" 0.80 0.00 "L" "")
 (command "COLOR" "BYLAYER")
 (command "LAYER" "S" "CGBLITHCD" "")
 (setq p1 (list 327.00 1501.02) p2 (list 328.35 1482.94))
 (command "LINE" p1 p2 "")
 (setq p1 (list 328.50 1482.57) p2 (list 0.00 0.00))
 (command "TEXT" "J" "ML" p1   0.75  0.00 "029")
 (command "LAYER" "S" "CGBTHK" "")
 (setq p1 (list 333.00 1482.57) p2 (list 0.00 0.00))
 (command "TEXT" "J" "ML" p1   0.75  0.00 "0.13")
 (command "LAYER" "S" "CGBHZID" "")
 (setq p1 (list 337.50 1482.57) p2 (list 0.00 0.00))
 (command "TEXT" "J" "ML" p1   0.75  0.00 "")
 (setq p1 (list 339.75 1482.57) p2 (list 0.00 0.00))
 (command "TEXT" "J" "ML" p1   0.75  0.00 "5500")
 (command "LAYER" "S" "CGBLITHTXT" "")
 (setq p1 (list 343.50 1482.57) p2 (list 0.00 0.00))
 (command "TEXT" "J" "ML" p1   0.75  0.00 "COAL W/PYRITE STKS")
 (command "LAYER" "S" "CGBCMNT" "")
 (setq p1 (list 363.75 1482.57) p2 (list 0.00 0.00))
 (command "TEXT" "J" "ML" p1   0.75  0.00 "DULL W/PYRT")
 (command "LAYER" "S" "CGBMAIN" "")
 (setq p1 (list 321.00 1500.95) p2 (list 327.00 1500.95) p3 (list 327.00 1500.00) p4 (list 321.00 1500.00))
 (command "PLINE" p1 p2 p3 p4 "c")
 (command "HATCH" "ZIGZAG" 0.30 22.50 "L" "")
 (command "COLOR" "BYLAYER")
 (command "LAYER" "S" "CGBLITHCD" "")
 (setq p1 (list 327.00 1500.48) p2 (list 328.35 1481.69))
 (command "LINE" p1 p2 "")
 (setq p1 (list 328.50 1481.32) p2 (list 0.00 0.00))
 (command "TEXT" "J" "ML" p1   0.75  0.00 "027")
 (command "LAYER" "S" "CGBTHK" "")
 (setq p1 (list 333.00 1481.32) p2 (list 0.00 0.00))
 (command "TEXT" "J" "ML" p1   0.75  0.00 "0.95")
 (command "LAYER" "S" "CGBHZID" "")
 (setq p1 (list 337.50 1481.32) p2 (list 0.00 0.00))
 (command "TEXT" "J" "ML" p1   0.75  0.00 "")
 (setq p1 (list 339.75 1481.32) p2 (list 0.00 0.00))
 (command "TEXT" "J" "ML" p1   0.75  0.00 "5500")
 (command "LAYER" "S" "CGBLITHTXT" "")
 (setq p1 (list 343.50 1481.32) p2 (list 0.00 0.00))
 (command "TEXT" "J" "ML" p1   0.75  0.00 "COAL W/SH LAYERS")
 (command "LAYER" "S" "CGBCMNT" "")
 (setq p1 (list 363.75 1481.32) p2 (list 0.00 0.00))
 (command "TEXT" "J" "ML" p1   0.75  0.00 "BRIGHT W/DULL")
 (command "LAYER" "S" "CGBMAIN" "")
 (setq p1 (list 321.00 1500.00) p2 (list 327.00 1500.00) p3 (list 327.00 1499.74) p4 (list 321.00 1499.74))
 (command "PLINE" p1 p2 p3 p4 "c")
 (command "HATCH" "ZIGZAG" 0.25 0.00 "L" "")
 (command "COLOR" "BYLAYER")
 (command "LAYER" "S" "CGBLITHCD" "")
 (setq p1 (list 327.00 1499.87) p2 (list 328.35 1480.44))
 (command "LINE" p1 p2 "")
 (setq p1 (list 328.50 1480.07) p2 (list 0.00 0.00))
 (command "TEXT" "J" "ML" p1   0.75  0.00 "127")
 (command "LAYER" "S" "CGBTHK" "")
 (setq p1 (list 333.00 1480.07) p2 (list 0.00 0.00))
 (command "TEXT" "J" "ML" p1   0.75  0.00 "0.26")
 (command "LAYER" "S" "CGBHZID" "")
 (setq p1 (list 337.50 1480.07) p2 (list 0.00 0.00))
 (command "TEXT" "J" "ML" p1   0.75  0.00 "")
 (setq p1 (list 339.75 1480.07) p2 (list 0.00 0.00))
 (command "TEXT" "J" "ML" p1   0.75  0.00 "5451")
 (command "LAYER" "S" "CGBLITHTXT" "")
 (setq p1 (list 343.50 1480.07) p2 (list 0.00 0.00))
 (command "TEXT" "J" "ML" p1   0.75  0.00 "DRK GRY FIRECLAY")
 (command "LAYER" "S" "CGBCMNT" "")
 (setq p1 (list 363.75 1480.07) p2 (list 0.00 0.00))
 (command "TEXT" "J" "ML" p1   0.75  0.00 "SILTY")
 (command "LAYER" "S" "CGBMAIN" "")
 (setq p1 (list 321.00 1499.74) p2 (list 327.00 1499.74) p3 (list 327.00 1499.30) p4 (list 321.00 1499.30))
 (command "PLINE" p1 p2 p3 p4 "c")
 (command "HATCH" "ZIGZAG" 0.25 0.00 "L" "")
 (command "COLOR" "BYLAYER")
 (command "LAYER" "S" "CGBLITHCD" "")
 (setq p1 (list 327.00 1499.52) p2 (list 328.35 1479.19))
 (command "LINE" p1 p2 "")
 (setq p1 (list 328.50 1478.82) p2 (list 0.00 0.00))
 (command "TEXT" "J" "ML" p1   0.75  0.00 "327")
 (command "LAYER" "S" "CGBTHK" "")
 (setq p1 (list 333.00 1478.82) p2 (list 0.00 0.00))
 (command "TEXT" "J" "ML" p1   0.75  0.00 "0.44")
 (command "LAYER" "S" "CGBHZID" "")
 (setq p1 (list 337.50 1478.82) p2 (list 0.00 0.00))
 (command "TEXT" "J" "ML" p1   0.75  0.00 "")
 (setq p1 (list 339.75 1478.82) p2 (list 0.00 0.00))
 (command "TEXT" "J" "ML" p1   0.75  0.00 "5451")
 (command "LAYER" "S" "CGBLITHTXT" "")
 (setq p1 (list 343.50 1478.82) p2 (list 0.00 0.00))
 (command "TEXT" "J" "ML" p1   0.75  0.00 "DRK GRY SDY FIRECLAY")
 (command "LAYER" "S" "CGBCMNT" "")
 (setq p1 (list 363.75 1478.82) p2 (list 0.00 0.00))
 (command "TEXT" "J" "ML" p1   0.75  0.00 "M SFT")
 (command "LAYER" "S" "CGBMAIN" "")
 (setq p1 (list 321.00 1499.30) p2 (list 327.00 1499.30) p3 (list 327.00 1494.30) p4 (list 321.00 1494.30))
 (command "PLINE" p1 p2 p3 p4 "c")
 (command "HATCH" "ZIGZAG" 0.25 0.00 "L" "")
 (command "COLOR" "BYLAYER")
 (command "LAYER" "S" "CGBLITHCD" "")
 (setq p1 (list 327.00 1496.80) p2 (list 328.35 1477.94))
 (command "LINE" p1 p2 "")
 (setq p1 (list 328.50 1477.57) p2 (list 0.00 0.00))
 (command "TEXT" "J" "ML" p1   0.75  0.00 "127")
 (command "LAYER" "S" "CGBTHK" "")
 (setq p1 (list 333.00 1477.57) p2 (list 0.00 0.00))
 (command "TEXT" "J" "ML" p1   0.75  0.00 "5.00")
 (command "LAYER" "S" "CGBHZID" "")
 (setq p1 (list 337.50 1477.57) p2 (list 0.00 0.00))
 (command "TEXT" "J" "ML" p1   0.75  0.00 "")
 (setq p1 (list 339.75 1477.57) p2 (list 0.00 0.00))
 (command "TEXT" "J" "ML" p1   0.75  0.00 "5451")
 (command "LAYER" "S" "CGBLITHTXT" "")
 (setq p1 (list 343.50 1477.57) p2 (list 0.00 0.00))
 (command "TEXT" "J" "ML" p1   0.75  0.00 "DRK GRY FIRECLAY")
 (command "LAYER" "S" "CGBCMNT" "")
 (setq p1 (list 363.75 1477.57) p2 (list 0.00 0.00))
 (command "TEXT" "J" "ML" p1   0.75  0.00 "ROOTED")
 (command "LAYER" "S" "CGBMAIN" "")
 (setq p1 (list 321.00 1494.30) p2 (list 327.00 1494.30) p3 (list 327.00 1494.20) p4 (list 321.00 1494.20))
 (command "PLINE" p1 p2 p3 p4 "c")
 (command "HATCH" "ZIGZAG" 4.00 22.50 "L" "")
 (command "COLOR" "BYLAYER")
 (command "LAYER" "S" "CGBLITHCD" "")
 (setq p1 (list 327.00 1494.25) p2 (list 328.35 1476.69))
 (command "LINE" p1 p2 "")
 (setq p1 (list 328.50 1476.32) p2 (list 0.00 0.00))
 (command "TEXT" "J" "ML" p1   0.75  0.00 "114")
 (command "LAYER" "S" "CGBTHK" "")
 (setq p1 (list 333.00 1476.32) p2 (list 0.00 0.00))
 (command "TEXT" "J" "ML" p1   0.75  0.00 "0.10")
 (command "LAYER" "S" "CGBHZID" "")
 (setq p1 (list 337.50 1476.32) p2 (list 0.00 0.00))
 (command "TEXT" "J" "ML" p1   0.75  0.00 "")
 (setq p1 (list 339.75 1476.32) p2 (list 0.00 0.00))
 (command "TEXT" "J" "ML" p1   0.75  0.00 "5451")
 (command "LAYER" "S" "CGBLITHTXT" "")
 (setq p1 (list 343.50 1476.32) p2 (list 0.00 0.00))
 (command "TEXT" "J" "ML" p1   0.75  0.00 "BLK SH")
 (command "LAYER" "S" "CGBCMNT" "")
 (setq p1 (list 363.75 1476.32) p2 (list 0.00 0.00))
 (command "TEXT" "J" "ML" p1   0.75  0.00 "PYRT")
 (command "LAYER" "S" "CGBMAIN" "")
 (setq p1 (list 320.50 1734.29) p2 (list 321.00 1734.29))
 (command "LINE" p1 p2 "")
 (setq p1 (list 320.13 1734.29) p2 (list 0.00 0.00))
 (command "TEXT" "J" "MR" p1   0.75  0.00 "0.00")
 (setq p1 (list 320.13 1733.17) p2 (list 0.00 0.00))
 (command "TEXT" "J" "MR" p1   0.75  0.00 "3048.68")
 (setq p1 (list 320.50 1724.29) p2 (list 321.00 1724.29))
 (command "LINE" p1 p2 "")
 (setq p1 (list 320.13 1724.29) p2 (list 0.00 0.00))
 (command "TEXT" "J" "MR" p1   0.75  0.00 "10.00")
 (setq p1 (list 320.13 1723.17) p2 (list 0.00 0.00))
 (command "TEXT" "J" "MR" p1   0.75  0.00 "3038.68")
 (setq p1 (list 320.50 1714.29) p2 (list 321.00 1714.29))
 (command "LINE" p1 p2 "")
 (setq p1 (list 320.13 1714.29) p2 (list 0.00 0.00))
 (command "TEXT" "J" "MR" p1   0.75  0.00 "20.00")
 (setq p1 (list 320.13 1713.17) p2 (list 0.00 0.00))
 (command "TEXT" "J" "MR" p1   0.75  0.00 "3028.68")
 (setq p1 (list 320.50 1704.29) p2 (list 321.00 1704.29))
 (command "LINE" p1 p2 "")
 (setq p1 (list 320.13 1704.29) p2 (list 0.00 0.00))
 (command "TEXT" "J" "MR" p1   0.75  0.00 "30.00")
 (setq p1 (list 320.13 1703.17) p2 (list 0.00 0.00))
 (command "TEXT" "J" "MR" p1   0.75  0.00 "3018.68")
 (setq p1 (list 320.50 1694.29) p2 (list 321.00 1694.29))
 (command "LINE" p1 p2 "")
 (setq p1 (list 320.13 1694.29) p2 (list 0.00 0.00))
 (command "TEXT" "J" "MR" p1   0.75  0.00 "40.00")
 (setq p1 (list 320.13 1693.17) p2 (list 0.00 0.00))
 (command "TEXT" "J" "MR" p1   0.75  0.00 "3008.68")
 (setq p1 (list 320.50 1684.29) p2 (list 321.00 1684.29))
 (command "LINE" p1 p2 "")
 (setq p1 (list 320.13 1684.29) p2 (list 0.00 0.00))
 (command "TEXT" "J" "MR" p1   0.75  0.00 "50.00")
 (setq p1 (list 320.13 1683.17) p2 (list 0.00 0.00))
 (command "TEXT" "J" "MR" p1   0.75  0.00 "2998.68")
 (setq p1 (list 320.50 1674.29) p2 (list 321.00 1674.29))
 (command "LINE" p1 p2 "")
 (setq p1 (list 320.13 1674.29) p2 (list 0.00 0.00))
 (command "TEXT" "J" "MR" p1   0.75  0.00 "60.00")
 (setq p1 (list 320.13 1673.17) p2 (list 0.00 0.00))
 (command "TEXT" "J" "MR" p1   0.75  0.00 "2988.68")
 (setq p1 (list 320.50 1664.29) p2 (list 321.00 1664.29))
 (command "LINE" p1 p2 "")
 (setq p1 (list 320.13 1664.29) p2 (list 0.00 0.00))
 (command "TEXT" "J" "MR" p1   0.75  0.00 "70.00")
 (setq p1 (list 320.13 1663.17) p2 (list 0.00 0.00))
 (command "TEXT" "J" "MR" p1   0.75  0.00 "2978.68")
 (setq p1 (list 320.50 1654.29) p2 (list 321.00 1654.29))
 (command "LINE" p1 p2 "")
 (setq p1 (list 320.13 1654.29) p2 (list 0.00 0.00))
 (command "TEXT" "J" "MR" p1   0.75  0.00 "80.00")
 (setq p1 (list 320.13 1653.17) p2 (list 0.00 0.00))
 (command "TEXT" "J" "MR" p1   0.75  0.00 "2968.68")
 (setq p1 (list 320.50 1644.29) p2 (list 321.00 1644.29))
 (command "LINE" p1 p2 "")
 (setq p1 (list 320.13 1644.29) p2 (list 0.00 0.00))
 (command "TEXT" "J" "MR" p1   0.75  0.00 "90.00")
 (setq p1 (list 320.13 1643.17) p2 (list 0.00 0.00))
 (command "TEXT" "J" "MR" p1   0.75  0.00 "2958.68")
 (setq p1 (list 320.50 1634.29) p2 (list 321.00 1634.29))
 (command "LINE" p1 p2 "")
 (setq p1 (list 320.13 1634.29) p2 (list 0.00 0.00))
 (command "TEXT" "J" "MR" p1   0.75  0.00 "100.00")
 (setq p1 (list 320.13 1633.17) p2 (list 0.00 0.00))
 (command "TEXT" "J" "MR" p1   0.75  0.00 "2948.68")
 (setq p1 (list 320.50 1624.29) p2 (list 321.00 1624.29))
 (command "LINE" p1 p2 "")
 (setq p1 (list 320.13 1624.29) p2 (list 0.00 0.00))
 (command "TEXT" "J" "MR" p1   0.75  0.00 "110.00")
 (setq p1 (list 320.13 1623.17) p2 (list 0.00 0.00))
 (command "TEXT" "J" "MR" p1   0.75  0.00 "2938.68")
 (setq p1 (list 320.50 1614.29) p2 (list 321.00 1614.29))
 (command "LINE" p1 p2 "")
 (setq p1 (list 320.13 1614.29) p2 (list 0.00 0.00))
 (command "TEXT" "J" "MR" p1   0.75  0.00 "120.00")
 (setq p1 (list 320.13 1613.17) p2 (list 0.00 0.00))
 (command "TEXT" "J" "MR" p1   0.75  0.00 "2928.68")
 (setq p1 (list 320.50 1604.29) p2 (list 321.00 1604.29))
 (command "LINE" p1 p2 "")
 (setq p1 (list 320.13 1604.29) p2 (list 0.00 0.00))
 (command "TEXT" "J" "MR" p1   0.75  0.00 "130.00")
 (setq p1 (list 320.13 1603.17) p2 (list 0.00 0.00))
 (command "TEXT" "J" "MR" p1   0.75  0.00 "2918.68")
 (setq p1 (list 320.50 1594.29) p2 (list 321.00 1594.29))
 (command "LINE" p1 p2 "")
 (setq p1 (list 320.13 1594.29) p2 (list 0.00 0.00))
 (command "TEXT" "J" "MR" p1   0.75  0.00 "140.00")
 (setq p1 (list 320.13 1593.17) p2 (list 0.00 0.00))
 (command "TEXT" "J" "MR" p1   0.75  0.00 "2908.68")
 (setq p1 (list 320.50 1584.29) p2 (list 321.00 1584.29))
 (command "LINE" p1 p2 "")
 (setq p1 (list 320.13 1584.29) p2 (list 0.00 0.00))
 (command "TEXT" "J" "MR" p1   0.75  0.00 "150.00")
 (setq p1 (list 320.13 1583.17) p2 (list 0.00 0.00))
 (command "TEXT" "J" "MR" p1   0.75  0.00 "2898.68")
 (setq p1 (list 320.50 1574.29) p2 (list 321.00 1574.29))
 (command "LINE" p1 p2 "")
 (setq p1 (list 320.13 1574.29) p2 (list 0.00 0.00))
 (command "TEXT" "J" "MR" p1   0.75  0.00 "160.00")
 (setq p1 (list 320.13 1573.17) p2 (list 0.00 0.00))
 (command "TEXT" "J" "MR" p1   0.75  0.00 "2888.68")
 (setq p1 (list 320.50 1564.29) p2 (list 321.00 1564.29))
 (command "LINE" p1 p2 "")
 (setq p1 (list 320.13 1564.29) p2 (list 0.00 0.00))
 (command "TEXT" "J" "MR" p1   0.75  0.00 "170.00")
 (setq p1 (list 320.13 1563.17) p2 (list 0.00 0.00))
 (command "TEXT" "J" "MR" p1   0.75  0.00 "2878.68")
 (setq p1 (list 320.50 1554.29) p2 (list 321.00 1554.29))
 (command "LINE" p1 p2 "")
 (setq p1 (list 320.13 1554.29) p2 (list 0.00 0.00))
 (command "TEXT" "J" "MR" p1   0.75  0.00 "180.00")
 (setq p1 (list 320.13 1553.17) p2 (list 0.00 0.00))
 (command "TEXT" "J" "MR" p1   0.75  0.00 "2868.68")
 (setq p1 (list 320.50 1544.29) p2 (list 321.00 1544.29))
 (command "LINE" p1 p2 "")
 (setq p1 (list 320.13 1544.29) p2 (list 0.00 0.00))
 (command "TEXT" "J" "MR" p1   0.75  0.00 "190.00")
 (setq p1 (list 320.13 1543.17) p2 (list 0.00 0.00))
 (command "TEXT" "J" "MR" p1   0.75  0.00 "2858.68")
 (setq p1 (list 320.50 1534.29) p2 (list 321.00 1534.29))
 (command "LINE" p1 p2 "")
 (setq p1 (list 320.13 1534.29) p2 (list 0.00 0.00))
 (command "TEXT" "J" "MR" p1   0.75  0.00 "200.00")
 (setq p1 (list 320.13 1533.17) p2 (list 0.00 0.00))
 (command "TEXT" "J" "MR" p1   0.75  0.00 "2848.68")
 (setq p1 (list 320.50 1524.29) p2 (list 321.00 1524.29))
 (command "LINE" p1 p2 "")
 (setq p1 (list 320.13 1524.29) p2 (list 0.00 0.00))
 (command "TEXT" "J" "MR" p1   0.75  0.00 "210.00")
 (setq p1 (list 320.13 1523.17) p2 (list 0.00 0.00))
 (command "TEXT" "J" "MR" p1   0.75  0.00 "2838.68")
 (setq p1 (list 320.50 1514.29) p2 (list 321.00 1514.29))
 (command "LINE" p1 p2 "")
 (setq p1 (list 320.13 1514.29) p2 (list 0.00 0.00))
 (command "TEXT" "J" "MR" p1   0.75  0.00 "220.00")
 (setq p1 (list 320.13 1513.17) p2 (list 0.00 0.00))
 (command "TEXT" "J" "MR" p1   0.75  0.00 "2828.68")
 (setq p1 (list 320.50 1504.29) p2 (list 321.00 1504.29))
 (command "LINE" p1 p2 "")
 (setq p1 (list 320.13 1504.29) p2 (list 0.00 0.00))
 (command "TEXT" "J" "MR" p1   0.75  0.00 "230.00")
 (setq p1 (list 320.13 1503.17) p2 (list 0.00 0.00))
 (command "TEXT" "J" "MR" p1   0.75  0.00 "2818.68")
 (setq p1 (list 320.50 1494.20) p2 (list 321.00 1494.20))
 (command "LINE" p1 p2 "")
 (setq p1 (list 320.13 1494.20) p2 (list 0.00 0.00))
 (command "TEXT" "J" "MR" p1   0.75  0.00 "240.09")
 (setq p1 (list 320.13 1493.08) p2 (list 0.00 0.00))
 (command "TEXT" "J" "MR" p1   0.75  0.00 "2808.59")
 (command "LAYER" "S" "CGBHLHDR" "")
 (setq p1 (list 314.00 1745.79) p2 (list 314.00 1735.79) p3 (list 334.00 1735.79) p4 (list 334.00 1745.79))
 (command "LINE" p1 p2 p3 p4 "c")
 (setq p1 (list 314.50 1744.04) p2 (list 0.00 0.00))
 (command "TEXT" "J" "ML" p1   1.13  0.00 "Hole:")
 (setq p1 (list 314.50 1741.79) p2 (list 0.00 0.00))
 (command "TEXT" "J" "ML" p1   0.83  0.00 "Easting:")
 (setq p1 (list 314.50 1740.04) p2 (list 0.00 0.00))
 (command "TEXT" "J" "ML" p1   0.83  0.00 "Northing:")
 (setq p1 (list 314.50 1738.29) p2 (list 0.00 0.00))
 (command "TEXT" "J" "ML" p1   0.83  0.00 "Collar Elev:")
 (setq p1 (list 314.50 1736.54) p2 (list 0.00 0.00))
 (command "TEXT" "J" "ML" p1   0.83  0.00 "Drill Depth:")
 (setq p1 (list 333.50 1744.04) p2 (list 0.00 0.00))
 (command "TEXT" "J" "MR" p1   1.13  0.00 "XY-30")
 (setq p1 (list 333.50 1741.79) p2 (list 0.00 0.00))
 (command "TEXT" "J" "MR" p1   0.83  0.00 "4045501.38")
 (setq p1 (list 333.50 1740.04) p2 (list 0.00 0.00))
 (command "TEXT" "J" "MR" p1   0.83  0.00 "268673.78")
 (setq p1 (list 333.50 1738.29) p2 (list 0.00 0.00))
 (command "TEXT" "J" "MR" p1   0.83  0.00 "3048.68")
 (setq p1 (list 333.50 1736.54) p2 (list 0.00 0.00))
 (command "TEXT" "J" "MR" p1   0.83  0.00 "265.00")
 (setq p1 (list 324.00 1735.79) p2 (list 324.00 1734.29))
 (command "LINE" p1 p2 "")
 (command "LAYER" "S" "CGBMAIN" "")
 (setq p1 (list 428.00 1918.54) p2 (list 434.00 1918.54) p3 (list 434.00 1888.54) p4 (list 428.00 1888.54))
 (command "PLINE" p1 p2 p3 p4 "c")
 (command "LINE" p1 p3 "")
 (command "LINE" p2 p4 "")
 (command "COLOR" "BYLAYER")
 (command "LAYER" "S" "CGBLITHCD" "")
 (setq p1 (list 434.00 1903.54) p2 (list 435.35 1903.54))
 (command "LINE" p1 p2 "")
 (setq p1 (list 435.50 1903.17) p2 (list 0.00 0.00))
 (command "TEXT" "J" "ML" p1   0.75  0.00 "001")
 (command "LAYER" "S" "CGBTHK" "")
 (setq p1 (list 440.00 1903.17) p2 (list 0.00 0.00))
 (command "TEXT" "J" "ML" p1   0.75  0.00 "30.00")
 (command "LAYER" "S" "CGBHZID" "")
 (setq p1 (list 444.50 1903.17) p2 (list 0.00 0.00))
 (command "TEXT" "J" "ML" p1   0.75  0.00 "")
 (setq p1 (list 446.75 1903.17) p2 (list 0.00 0.00))
 (command "TEXT" "J" "ML" p1   0.75  0.00 "9990")
 (command "LAYER" "S" "CGBLITHTXT" "")
 (setq p1 (list 450.50 1903.17) p2 (list 0.00 0.00))
 (command "TEXT" "J" "ML" p1   0.75  0.00 "CASING")
 (command "LAYER" "S" "CGBCMNT" "")
 (setq p1 (list 470.75 1903.17) p2 (list 0.00 0.00))
 (command "TEXT" "J" "ML" p1   0.75  0.00 "M SFT")
 (command "LAYER" "S" "CGBMAIN" "")
 (setq p1 (list 428.00 1888.54) p2 (list 434.00 1888.54) p3 (list 434.00 1881.46) p4 (list 428.00 1881.46))
 (command "PLINE" p1 p2 p3 p4 "c")
 (command "HATCH" "ZIGZAG" 4.00 45.00 "L" "")
 (command "COLOR" "BYLAYER")
 (command "LAYER" "S" "CGBLITHCD" "")
 (setq p1 (list 434.00 1885.00) p2 (list 435.35 1885.00))
 (command "LINE" p1 p2 "")
 (setq p1 (list 435.50 1884.63) p2 (list 0.00 0.00))
 (command "TEXT" "J" "ML" p1   0.75  0.00 "120")
 (command "LAYER" "S" "CGBTHK" "")
 (setq p1 (list 440.00 1884.63) p2 (list 0.00 0.00))
 (command "TEXT" "J" "ML" p1   0.75  0.00 "7.08")
 (command "LAYER" "S" "CGBHZID" "")
 (setq p1 (list 444.50 1884.63) p2 (list 0.00 0.00))
 (command "TEXT" "J" "ML" p1   0.75  0.00 "")
 (setq p1 (list 446.75 1884.63) p2 (list 0.00 0.00))
 (command "TEXT" "J" "ML" p1   0.75  0.00 "9990")
 (command "LAYER" "S" "CGBLITHTXT" "")
 (setq p1 (list 450.50 1884.63) p2 (list 0.00 0.00))
 (command "TEXT" "J" "ML" p1   0.75  0.00 "DRK GRY SH (UNDIF)")
 (command "LAYER" "S" "CGBCMNT" "")
 (setq p1 (list 470.75 1884.63) p2 (list 0.00 0.00))
 (command "TEXT" "J" "ML" p1   0.75  0.00 "CASING")
 (command "LAYER" "S" "CGBMAIN" "")
 (setq p1 (list 428.00 1881.46) p2 (list 434.00 1881.46) p3 (list 434.00 1874.94) p4 (list 428.00 1874.94))
 (command "PLINE" p1 p2 p3 p4 "c")
 (command "HATCH" "ZIGZAG" 0.25 0.00 "L" "")
 (command "COLOR" "BYLAYER")
 (command "LAYER" "S" "CGBLITHCD" "")
 (setq p1 (list 434.00 1878.20) p2 (list 435.35 1878.20))
 (command "LINE" p1 p2 "")
 (setq p1 (list 435.50 1877.83) p2 (list 0.00 0.00))
 (command "TEXT" "J" "ML" p1   0.75  0.00 "744")
 (command "LAYER" "S" "CGBTHK" "")
 (setq p1 (list 440.00 1877.83) p2 (list 0.00 0.00))
 (command "TEXT" "J" "ML" p1   0.75  0.00 "6.52")
 (command "LAYER" "S" "CGBHZID" "")
 (setq p1 (list 444.50 1877.83) p2 (list 0.00 0.00))
 (command "TEXT" "J" "ML" p1   0.75  0.00 "")
 (setq p1 (list 446.75 1877.83) p2 (list 0.00 0.00))
 (command "TEXT" "J" "ML" p1   0.75  0.00 "9990")
 (command "LAYER" "S" "CGBLITHTXT" "")
 (setq p1 (list 450.50 1877.83) p2 (list 0.00 0.00))
 (command "TEXT" "J" "ML" p1   0.75  0.00 "GRY QTZ PEB CGL")
 (command "LAYER" "S" "CGBCMNT" "")
 (setq p1 (list 470.75 1877.83) p2 (list 0.00 0.00))
 (command "TEXT" "J" "ML" p1   0.75  0.00 "WTHRD")
 (command "LAYER" "S" "CGBMAIN" "")
 (setq p1 (list 428.00 1874.94) p2 (list 434.00 1874.94) p3 (list 434.00 1873.54) p4 (list 428.00 1873.54))
 (command "PLINE" p1 p2 p3 p4 "c")
 (command "HATCH" "ZIGZAG" 4.00 0.00 "L" "")
 (command "COLOR" "BYLAYER")
 (command "LAYER" "S" "CGBLITHCD" "")
 (setq p1 (list 434.00 1874.24) p2 (list 435.35 1874.24))
 (command "LINE" p1 p2 "")
 (setq p1 (list 435.50 1873.87) p2 (list 0.00 0.00))
 (command "TEXT" "J" "ML" p1   0.75  0.00 "541")
 (command "LAYER" "S" "CGBTHK" "")
 (setq p1 (list 440.00 1873.87) p2 (list 0.00 0.00))
 (command "TEXT" "J" "ML" p1   0.75  0.00 "1.40")
 (command "LAYER" "S" "CGBHZID" "")
 (setq p1 (list 444.50 1873.87) p2 (list 0.00 0.00))
 (command "TEXT" "J" "ML" p1   0.75  0.00 "")
 (setq p1 (list 446.75 1873.87) p2 (list 0.00 0.00))
 (command "TEXT" "J" "ML" p1   0.75  0.00 "9990")
 (command "LAYER" "S" "CGBLITHTXT" "")
 (setq p1 (list 450.50 1873.87) p2 (list 0.00 0.00))
 (command "TEXT" "J" "ML" p1   0.75  0.00 "GRY CROSSBED SS")
 (command "LAYER" "S" "CGBCMNT" "")
 (setq p1 (list 470.75 1873.87) p2 (list 0.00 0.00))
 (command "TEXT" "J" "ML" p1   0.75  0.00 "BADLY BRKN")
 (command "LAYER" "S" "CGBMAIN" "")
 (setq p1 (list 428.00 1873.54) p2 (list 434.00 1873.54) p3 (list 434.00 1867.94) p4 (list 428.00 1867.94))
 (command "PLINE" p1 p2 p3 p4 "c")
 (command "HATCH" "ZIGZAG" 4.00 0.00 "L" "")
 (command "COLOR" "BYLAYER")
 (command "LAYER" "S" "CGBLITHCD" "")
 (setq p1 (list 434.00 1870.74) p2 (list 435.35 1870.74))
 (command "LINE" p1 p2 "")
 (setq p1 (list 435.50 1870.37) p2 (list 0.00 0.00))
 (command "TEXT" "J" "ML" p1   0.75  0.00 "541")
 (command "LAYER" "S" "CGBTHK" "")
 (setq p1 (list 440.00 1870.37) p2 (list 0.00 0.00))
 (command "TEXT" "J" "ML" p1   0.75  0.00 "5.60")
 (command "LAYER" "S" "CGBHZID" "")
 (setq p1 (list 444.50 1870.37) p2 (list 0.00 0.00))
 (command "TEXT" "J" "ML" p1   0.75  0.00 "")
 (setq p1 (list 446.75 1870.37) p2 (list 0.00 0.00))
 (command "TEXT" "J" "ML" p1   0.75  0.00 "9990")
 (command "LAYER" "S" "CGBLITHTXT" "")
 (setq p1 (list 450.50 1870.37) p2 (list 0.00 0.00))
 (command "TEXT" "J" "ML" p1   0.75  0.00 "GRY CROSSBED SS")
 (command "LAYER" "S" "CGBCMNT" "")
 (setq p1 (list 470.75 1870.37) p2 (list 0.00 0.00))
 (command "TEXT" "J" "ML" p1   0.75  0.00 "")
 (command "LAYER" "S" "CGBMAIN" "")
 (setq p1 (list 428.00 1867.94) p2 (list 434.00 1867.94) p3 (list 434.00 1863.86) p4 (list 428.00 1863.86))
 (command "PLINE" p1 p2 p3 p4 "c")
 (command "HATCH" "ZIGZAG" 0.25 0.00 "L" "")
 (command "COLOR" "BYLAYER")
 (command "LAYER" "S" "CGBLITHCD" "")
 (setq p1 (list 434.00 1865.90) p2 (list 435.35 1865.90))
 (command "LINE" p1 p2 "")
 (setq p1 (list 435.50 1865.53) p2 (list 0.00 0.00))
 (command "TEXT" "J" "ML" p1   0.75  0.00 "744")
 (command "LAYER" "S" "CGBTHK" "")
 (setq p1 (list 440.00 1865.53) p2 (list 0.00 0.00))
 (command "TEXT" "J" "ML" p1   0.75  0.00 "4.08")
 (command "LAYER" "S" "CGBHZID" "")
 (setq p1 (list 444.50 1865.53) p2 (list 0.00 0.00))
 (command "TEXT" "J" "ML" p1   0.75  0.00 "")
 (setq p1 (list 446.75 1865.53) p2 (list 0.00 0.00))
 (command "TEXT" "J" "ML" p1   0.75  0.00 "9990")
 (command "LAYER" "S" "CGBLITHTXT" "")
 (setq p1 (list 450.50 1865.53) p2 (list 0.00 0.00))
 (command "TEXT" "J" "ML" p1   0.75  0.00 "GRY QTZ PEB CGL")
 (command "LAYER" "S" "CGBCMNT" "")
 (setq p1 (list 470.75 1865.53) p2 (list 0.00 0.00))
 (command "TEXT" "J" "ML" p1   0.75  0.00 "SLC")
 (command "LAYER" "S" "CGBMAIN" "")
 (setq p1 (list 428.00 1863.86) p2 (list 434.00 1863.86) p3 (list 434.00 1858.54) p4 (list 428.00 1858.54))
 (command "PLINE" p1 p2 p3 p4 "c")
 (command "HATCH" "ZIGZAG" 4.00 0.00 "L" "")
 (command "COLOR" "BYLAYER")
 (command "LAYER" "S" "CGBLITHCD" "")
 (setq p1 (list 434.00 1861.20) p2 (list 435.35 1861.20))
 (command "LINE" p1 p2 "")
 (setq p1 (list 435.50 1860.83) p2 (list 0.00 0.00))
 (command "TEXT" "J" "ML" p1   0.75  0.00 "124")
 (command "LAYER" "S" "CGBTHK" "")
 (setq p1 (list 440.00 1860.83) p2 (list 0.00 0.00))
 (command "TEXT" "J" "ML" p1   0.75  0.00 "5.32")
 (command "LAYER" "S" "CGBHZID" "")
 (setq p1 (list 444.50 1860.83) p2 (list 0.00 0.00))
 (command "TEXT" "J" "ML" p1   0.75  0.00 "")
 (setq p1 (list 446.75 1860.83) p2 (list 0.00 0.00))
 (command "TEXT" "J" "ML" p1   0.75  0.00 "9990")
 (command "LAYER" "S" "CGBLITHTXT" "")
 (setq p1 (list 450.50 1860.83) p2 (list 0.00 0.00))
 (command "TEXT" "J" "ML" p1   0.75  0.00 "DRK GRY SH")
 (command "LAYER" "S" "CGBCMNT" "")
 (setq p1 (list 470.75 1860.83) p2 (list 0.00 0.00))
 (command "TEXT" "J" "ML" p1   0.75  0.00 "")
 (command "LAYER" "S" "CGBMAIN" "")
 (setq p1 (list 428.00 1858.54) p2 (list 434.00 1858.54) p3 (list 434.00 1855.29) p4 (list 428.00 1855.29))
 (command "PLINE" p1 p2 p3 p4 "c")
 (command "HATCH" "ZIGZAG" 5.00 0.00 "L" "")
 (command "COLOR" "BYLAYER")
 (command "LAYER" "S" "CGBLITHCD" "")
 (setq p1 (list 434.00 1856.92) p2 (list 435.35 1856.92))
 (command "LINE" p1 p2 "")
 (setq p1 (list 435.50 1856.54) p2 (list 0.00 0.00))
 (command "TEXT" "J" "ML" p1   0.75  0.00 "174")
 (command "LAYER" "S" "CGBTHK" "")
 (setq p1 (list 440.00 1856.54) p2 (list 0.00 0.00))
 (command "TEXT" "J" "ML" p1   0.75  0.00 "3.25")
 (command "LAYER" "S" "CGBHZID" "")
 (setq p1 (list 444.50 1856.54) p2 (list 0.00 0.00))
 (command "TEXT" "J" "ML" p1   0.75  0.00 "")
 (setq p1 (list 446.75 1856.54) p2 (list 0.00 0.00))
 (command "TEXT" "J" "ML" p1   0.75  0.00 "9990")
 (command "LAYER" "S" "CGBLITHTXT" "")
 (setq p1 (list 450.50 1856.54) p2 (list 0.00 0.00))
 (command "TEXT" "J" "ML" p1   0.75  0.00 "GRY/GRN SH")
 (command "LAYER" "S" "CGBCMNT" "")
 (setq p1 (list 470.75 1856.54) p2 (list 0.00 0.00))
 (command "TEXT" "J" "ML" p1   0.75  0.00 "SIDERITE")
 (command "LAYER" "S" "CGBMAIN" "")
 (setq p1 (list 428.00 1855.29) p2 (list 434.00 1855.29) p3 (list 434.00 1849.56) p4 (list 428.00 1849.56))
 (command "PLINE" p1 p2 p3 p4 "c")
 (command "HATCH" "ZIGZAG" 10.00 0.00 "L" "")
 (command "COLOR" "BYLAYER")
 (command "LAYER" "S" "CGBLITHCD" "")
 (setq p1 (list 434.00 1852.43) p2 (list 435.35 1852.43))
 (command "LINE" p1 p2 "")
 (setq p1 (list 435.50 1852.05) p2 (list 0.00 0.00))
 (command "TEXT" "J" "ML" p1   0.75  0.00 "372")
 (command "LAYER" "S" "CGBTHK" "")
 (setq p1 (list 440.00 1852.05) p2 (list 0.00 0.00))
 (command "TEXT" "J" "ML" p1   0.75  0.00 "5.73")
 (command "LAYER" "S" "CGBHZID" "")
 (setq p1 (list 444.50 1852.05) p2 (list 0.00 0.00))
 (command "TEXT" "J" "ML" p1   0.75  0.00 "")
 (setq p1 (list 446.75 1852.05) p2 (list 0.00 0.00))
 (command "TEXT" "J" "ML" p1   0.75  0.00 "9990")
 (command "LAYER" "S" "CGBLITHTXT" "")
 (setq p1 (list 450.50 1852.05) p2 (list 0.00 0.00))
 (command "TEXT" "J" "ML" p1   0.75  0.00 "GRY/GRN SH+INTERBED SS")
 (command "LAYER" "S" "CGBCMNT" "")
 (setq p1 (list 470.75 1852.05) p2 (list 0.00 0.00))
 (command "TEXT" "J" "ML" p1   0.75  0.00 "")
 (command "LAYER" "S" "CGBMAIN" "")
 (setq p1 (list 428.00 1849.56) p2 (list 434.00 1849.56) p3 (list 434.00 1849.31) p4 (list 428.00 1849.31))
 (command "PLINE" p1 p2 p3 p4 "c")
 (command "HATCH" "ZIGZAG" 4.00 22.50 "L" "")
 (command "COLOR" "BYLAYER")
 (command "LAYER" "S" "CGBLITHCD" "")
 (setq p1 (list 434.00 1849.44) p2 (list 435.35 1849.44))
 (command "LINE" p1 p2 "")
 (setq p1 (list 435.50 1849.06) p2 (list 0.00 0.00))
 (command "TEXT" "J" "ML" p1   0.75  0.00 "114")
 (command "LAYER" "S" "CGBTHK" "")
 (setq p1 (list 440.00 1849.06) p2 (list 0.00 0.00))
 (command "TEXT" "J" "ML" p1   0.75  0.00 "0.25")
 (command "LAYER" "S" "CGBHZID" "")
 (setq p1 (list 444.50 1849.06) p2 (list 0.00 0.00))
 (command "TEXT" "J" "ML" p1   0.75  0.00 "")
 (setq p1 (list 446.75 1849.06) p2 (list 0.00 0.00))
 (command "TEXT" "J" "ML" p1   0.75  0.00 "9990")
 (command "LAYER" "S" "CGBLITHTXT" "")
 (setq p1 (list 450.50 1849.06) p2 (list 0.00 0.00))
 (command "TEXT" "J" "ML" p1   0.75  0.00 "BLK SH")
 (command "LAYER" "S" "CGBCMNT" "")
 (setq p1 (list 470.75 1849.06) p2 (list 0.00 0.00))
 (command "TEXT" "J" "ML" p1   0.75  0.00 "")
 (command "LAYER" "S" "CGBMAIN" "")
 (setq p1 (list 428.00 1849.31) p2 (list 434.00 1849.31) p3 (list 434.00 1843.79) p4 (list 428.00 1843.79))
 (command "PLINE" p1 p2 p3 p4 "c")
 (command "HATCH" "ZIGZAG" 4.00 0.00 "L" "")
 (command "COLOR" "BYLAYER")
 (command "LAYER" "S" "CGBLITHCD" "")
 (setq p1 (list 434.00 1846.55) p2 (list 435.35 1846.55))
 (command "LINE" p1 p2 "")
 (setq p1 (list 435.50 1846.18) p2 (list 0.00 0.00))
 (command "TEXT" "J" "ML" p1   0.75  0.00 "124")
 (command "LAYER" "S" "CGBTHK" "")
 (setq p1 (list 440.00 1846.18) p2 (list 0.00 0.00))
 (command "TEXT" "J" "ML" p1   0.75  0.00 "5.52")
 (command "LAYER" "S" "CGBHZID" "")
 (setq p1 (list 444.50 1846.18) p2 (list 0.00 0.00))
 (command "TEXT" "J" "ML" p1   0.75  0.00 "")
 (setq p1 (list 446.75 1846.18) p2 (list 0.00 0.00))
 (command "TEXT" "J" "ML" p1   0.75  0.00 "9990")
 (command "LAYER" "S" "CGBLITHTXT" "")
 (setq p1 (list 450.50 1846.18) p2 (list 0.00 0.00))
 (command "TEXT" "J" "ML" p1   0.75  0.00 "DRK GRY SH")
 (command "LAYER" "S" "CGBCMNT" "")
 (setq p1 (list 470.75 1846.18) p2 (list 0.00 0.00))
 (command "TEXT" "J" "ML" p1   0.75  0.00 "DRK")
 (command "LAYER" "S" "CGBMAIN" "")
 (setq p1 (list 428.00 1843.79) p2 (list 434.00 1843.79) p3 (list 434.00 1839.20) p4 (list 428.00 1839.20))
 (command "PLINE" p1 p2 p3 p4 "c")
 (command "HATCH" "ZIGZAG" 4.00 0.00 "L" "")
 (command "COLOR" "BYLAYER")
 (command "LAYER" "S" "CGBLITHCD" "")
 (setq p1 (list 434.00 1841.50) p2 (list 435.35 1841.50))
 (command "LINE" p1 p2 "")
 (setq p1 (list 435.50 1841.12) p2 (list 0.00 0.00))
 (command "TEXT" "J" "ML" p1   0.75  0.00 "124")
 (command "LAYER" "S" "CGBTHK" "")
 (setq p1 (list 440.00 1841.12) p2 (list 0.00 0.00))
 (command "TEXT" "J" "ML" p1   0.75  0.00 "4.59")
 (command "LAYER" "S" "CGBHZID" "")
 (setq p1 (list 444.50 1841.12) p2 (list 0.00 0.00))
 (command "TEXT" "J" "ML" p1   0.75  0.00 "")
 (setq p1 (list 446.75 1841.12) p2 (list 0.00 0.00))
 (command "TEXT" "J" "ML" p1   0.75  0.00 "9990")
 (command "LAYER" "S" "CGBLITHTXT" "")
 (setq p1 (list 450.50 1841.12) p2 (list 0.00 0.00))
 (command "TEXT" "J" "ML" p1   0.75  0.00 "DRK GRY SH")
 (command "LAYER" "S" "CGBCMNT" "")
 (setq p1 (list 470.75 1841.12) p2 (list 0.00 0.00))
 (command "TEXT" "J" "ML" p1   0.75  0.00 "")
 (command "LAYER" "S" "CGBMAIN" "")
 (setq p1 (list 428.00 1839.20) p2 (list 434.00 1839.20) p3 (list 434.00 1838.94) p4 (list 428.00 1838.94))
 (command "PLINE" p1 p2 p3 p4 "c")
 (command "HATCH" "ZIGZAG" 4.00 22.50 "L" "")
 (command "COLOR" "BYLAYER")
 (command "LAYER" "S" "CGBLITHCD" "")
 (setq p1 (list 434.00 1839.07) p2 (list 435.35 1839.07))
 (command "LINE" p1 p2 "")
 (setq p1 (list 435.50 1838.70) p2 (list 0.00 0.00))
 (command "TEXT" "J" "ML" p1   0.75  0.00 "114")
 (command "LAYER" "S" "CGBTHK" "")
 (setq p1 (list 440.00 1838.70) p2 (list 0.00 0.00))
 (command "TEXT" "J" "ML" p1   0.75  0.00 "0.26")
 (command "LAYER" "S" "CGBHZID" "")
 (setq p1 (list 444.50 1838.70) p2 (list 0.00 0.00))
 (command "TEXT" "J" "ML" p1   0.75  0.00 "")
 (setq p1 (list 446.75 1838.70) p2 (list 0.00 0.00))
 (command "TEXT" "J" "ML" p1   0.75  0.00 "9990")
 (command "LAYER" "S" "CGBLITHTXT" "")
 (setq p1 (list 450.50 1838.70) p2 (list 0.00 0.00))
 (command "TEXT" "J" "ML" p1   0.75  0.00 "BLK SH")
 (command "LAYER" "S" "CGBCMNT" "")
 (setq p1 (list 470.75 1838.70) p2 (list 0.00 0.00))
 (command "TEXT" "J" "ML" p1   0.75  0.00 "")
 (command "LAYER" "S" "CGBMAIN" "")
 (setq p1 (list 428.00 1838.94) p2 (list 434.00 1838.94) p3 (list 434.00 1838.08) p4 (list 428.00 1838.08))
 (command "PLINE" p1 p2 p3 p4 "c")
 (command "HATCH" "ZIGZAG" 0.40 45.00 "L" "")
 (command "COLOR" "BYLAYER")
 (command "LAYER" "S" "CGBLITHCD" "")
 (setq p1 (list 434.00 1838.51) p2 (list 435.35 1837.26))
 (command "LINE" p1 p2 "")
 (setq p1 (list 435.50 1836.89) p2 (list 0.00 0.00))
 (command "TEXT" "J" "ML" p1   0.75  0.00 "023")
 (command "LAYER" "S" "CGBTHK" "")
 (setq p1 (list 440.00 1836.89) p2 (list 0.00 0.00))
 (command "TEXT" "J" "ML" p1   0.75  0.00 "0.86")
 (command "LAYER" "S" "CGBHZID" "")
 (setq p1 (list 444.50 1836.89) p2 (list 0.00 0.00))
 (command "TEXT" "J" "ML" p1   0.75  0.00 "")
 (setq p1 (list 446.75 1836.89) p2 (list 0.00 0.00))
 (command "TEXT" "J" "ML" p1   0.75  0.00 "8500")
 (command "LAYER" "S" "CGBLITHTXT" "")
 (setq p1 (list 450.50 1836.89) p2 (list 0.00 0.00))
 (command "TEXT" "J" "ML" p1   0.75  0.00 "COAL W/BONE STKS")
 (command "LAYER" "S" "CGBCMNT" "")
 (setq p1 (list 470.75 1836.89) p2 (list 0.00 0.00))
 (command "TEXT" "J" "ML" p1   0.75  0.00 "VIT W/THIN DU")
 (command "LAYER" "S" "CGBMAIN" "")
 (setq p1 (list 428.00 1838.08) p2 (list 434.00 1838.08) p3 (list 434.00 1829.47) p4 (list 428.00 1829.47))
 (command "PLINE" p1 p2 p3 p4 "c")
 (command "HATCH" "ZIGZAG" 5.00 0.00 "L" "")
 (command "COLOR" "BYLAYER")
 (command "LAYER" "S" "CGBLITHCD" "")
 (setq p1 (list 434.00 1833.78) p2 (list 435.35 1833.78))
 (command "LINE" p1 p2 "")
 (setq p1 (list 435.50 1833.40) p2 (list 0.00 0.00))
 (command "TEXT" "J" "ML" p1   0.75  0.00 "224")
 (command "LAYER" "S" "CGBTHK" "")
 (setq p1 (list 440.00 1833.40) p2 (list 0.00 0.00))
 (command "TEXT" "J" "ML" p1   0.75  0.00 "8.61")
 (command "LAYER" "S" "CGBHZID" "")
 (setq p1 (list 444.50 1833.40) p2 (list 0.00 0.00))
 (command "TEXT" "J" "ML" p1   0.75  0.00 "")
 (setq p1 (list 446.75 1833.40) p2 (list 0.00 0.00))
 (command "TEXT" "J" "ML" p1   0.75  0.00 "8451")
 (command "LAYER" "S" "CGBLITHTXT" "")
 (setq p1 (list 450.50 1833.40) p2 (list 0.00 0.00))
 (command "TEXT" "J" "ML" p1   0.75  0.00 "DRK GRY SH W/LS NODS")
 (command "LAYER" "S" "CGBCMNT" "")
 (setq p1 (list 470.75 1833.40) p2 (list 0.00 0.00))
 (command "TEXT" "J" "ML" p1   0.75  0.00 "BRKN W/SLX")
 (command "LAYER" "S" "CGBMAIN" "")
 (setq p1 (list 428.00 1829.47) p2 (list 434.00 1829.47) p3 (list 434.00 1823.76) p4 (list 428.00 1823.76))
 (command "PLINE" p1 p2 p3 p4 "c")
 (command "HATCH" "ZIGZAG" 4.00 0.00 "L" "")
 (command "COLOR" "BYLAYER")
 (command "LAYER" "S" "CGBLITHCD" "")
 (setq p1 (list 434.00 1826.62) p2 (list 435.35 1826.62))
 (command "LINE" p1 p2 "")
 (setq p1 (list 435.50 1826.24) p2 (list 0.00 0.00))
 (command "TEXT" "J" "ML" p1   0.75  0.00 "125")
 (command "LAYER" "S" "CGBTHK" "")
 (setq p1 (list 440.00 1826.24) p2 (list 0.00 0.00))
 (command "TEXT" "J" "ML" p1   0.75  0.00 "5.71")
 (command "LAYER" "S" "CGBHZID" "")
 (setq p1 (list 444.50 1826.24) p2 (list 0.00 0.00))
 (command "TEXT" "J" "ML" p1   0.75  0.00 "")
 (setq p1 (list 446.75 1826.24) p2 (list 0.00 0.00))
 (command "TEXT" "J" "ML" p1   0.75  0.00 "8451")
 (command "LAYER" "S" "CGBLITHTXT" "")
 (setq p1 (list 450.50 1826.24) p2 (list 0.00 0.00))
 (command "TEXT" "J" "ML" p1   0.75  0.00 "DRK GRY CHRND SH")
 (command "LAYER" "S" "CGBCMNT" "")
 (setq p1 (list 470.75 1826.24) p2 (list 0.00 0.00))
 (command "TEXT" "J" "ML" p1   0.75  0.00 "")
 (command "LAYER" "S" "CGBMAIN" "")
 (setq p1 (list 428.00 1823.76) p2 (list 434.00 1823.76) p3 (list 434.00 1819.32) p4 (list 428.00 1819.32))
 (command "PLINE" p1 p2 p3 p4 "c")
 (command "HATCH" "ZIGZAG" 4.00 0.00 "L" "")
 (command "COLOR" "BYLAYER")
 (command "LAYER" "S" "CGBLITHCD" "")
 (setq p1 (list 434.00 1821.54) p2 (list 435.35 1821.54))
 (command "LINE" p1 p2 "")
 (setq p1 (list 435.50 1821.17) p2 (list 0.00 0.00))
 (command "TEXT" "J" "ML" p1   0.75  0.00 "424")
 (command "LAYER" "S" "CGBTHK" "")
 (setq p1 (list 440.00 1821.17) p2 (list 0.00 0.00))
 (command "TEXT" "J" "ML" p1   0.75  0.00 "4.44")
 (command "LAYER" "S" "CGBHZID" "")
 (setq p1 (list 444.50 1821.17) p2 (list 0.00 0.00))
 (command "TEXT" "J" "ML" p1   0.75  0.00 "")
 (setq p1 (list 446.75 1821.17) p2 (list 0.00 0.00))
 (command "TEXT" "J" "ML" p1   0.75  0.00 "8451")
 (command "LAYER" "S" "CGBLITHTXT" "")
 (setq p1 (list 450.50 1821.17) p2 (list 0.00 0.00))
 (command "TEXT" "J" "ML" p1   0.75  0.00 "DRK GRY SDY SH W/LS NODS")
 (command "LAYER" "S" "CGBCMNT" "")
 (setq p1 (list 470.75 1821.17) p2 (list 0.00 0.00))
 (command "TEXT" "J" "ML" p1   0.75  0.00 "")
 (command "LAYER" "S" "CGBMAIN" "")
 (setq p1 (list 428.00 1819.32) p2 (list 434.00 1819.32) p3 (list 434.00 1815.57) p4 (list 428.00 1815.57))
 (command "PLINE" p1 p2 p3 p4 "c")
 (command "HATCH" "ZIGZAG" 10.00 0.00 "L" "")
 (command "COLOR" "BYLAYER")
 (command "LAYER" "S" "CGBLITHCD" "")
 (setq p1 (list 434.00 1817.45) p2 (list 435.35 1817.45))
 (command "LINE" p1 p2 "")
 (setq p1 (list 435.50 1817.07) p2 (list 0.00 0.00))
 (command "TEXT" "J" "ML" p1   0.75  0.00 "372")
 (command "LAYER" "S" "CGBTHK" "")
 (setq p1 (list 440.00 1817.07) p2 (list 0.00 0.00))
 (command "TEXT" "J" "ML" p1   0.75  0.00 "3.75")
 (command "LAYER" "S" "CGBHZID" "")
 (setq p1 (list 444.50 1817.07) p2 (list 0.00 0.00))
 (command "TEXT" "J" "ML" p1   0.75  0.00 "")
 (setq p1 (list 446.75 1817.07) p2 (list 0.00 0.00))
 (command "TEXT" "J" "ML" p1   0.75  0.00 "8451")
 (command "LAYER" "S" "CGBLITHTXT" "")
 (setq p1 (list 450.50 1817.07) p2 (list 0.00 0.00))
 (command "TEXT" "J" "ML" p1   0.75  0.00 "GRY/GRN SH+INTERBED SS")
 (command "LAYER" "S" "CGBCMNT" "")
 (setq p1 (list 470.75 1817.07) p2 (list 0.00 0.00))
 (command "TEXT" "J" "ML" p1   0.75  0.00 "")
 (command "LAYER" "S" "CGBMAIN" "")
 (setq p1 (list 428.00 1815.57) p2 (list 434.00 1815.57) p3 (list 434.00 1814.82) p4 (list 428.00 1814.82))
 (command "PLINE" p1 p2 p3 p4 "c")
 (command "HATCH" "ZIGZAG" 4.00 0.00 "L" "")
 (command "COLOR" "BYLAYER")
 (command "LAYER" "S" "CGBLITHCD" "")
 (setq p1 (list 434.00 1815.20) p2 (list 435.35 1815.20))
 (command "LINE" p1 p2 "")
 (setq p1 (list 435.50 1814.82) p2 (list 0.00 0.00))
 (command "TEXT" "J" "ML" p1   0.75  0.00 "541")
 (command "LAYER" "S" "CGBTHK" "")
 (setq p1 (list 440.00 1814.82) p2 (list 0.00 0.00))
 (command "TEXT" "J" "ML" p1   0.75  0.00 "0.75")
 (command "LAYER" "S" "CGBHZID" "")
 (setq p1 (list 444.50 1814.82) p2 (list 0.00 0.00))
 (command "TEXT" "J" "ML" p1   0.75  0.00 "")
 (setq p1 (list 446.75 1814.82) p2 (list 0.00 0.00))
 (command "TEXT" "J" "ML" p1   0.75  0.00 "8451")
 (command "LAYER" "S" "CGBLITHTXT" "")
 (setq p1 (list 450.50 1814.82) p2 (list 0.00 0.00))
 (command "TEXT" "J" "ML" p1   0.75  0.00 "GRY CROSSBED SS")
 (command "LAYER" "S" "CGBCMNT" "")
 (setq p1 (list 470.75 1814.82) p2 (list 0.00 0.00))
 (command "TEXT" "J" "ML" p1   0.75  0.00 "")
 (command "LAYER" "S" "CGBMAIN" "")
 (setq p1 (list 428.00 1814.82) p2 (list 434.00 1814.82) p3 (list 434.00 1814.47) p4 (list 428.00 1814.47))
 (command "PLINE" p1 p2 p3 p4 "c")
 (command "HATCH" "ZIGZAG" 5.00 0.00 "L" "")
 (command "COLOR" "BYLAYER")
 (command "LAYER" "S" "CGBLITHCD" "")
 (setq p1 (list 434.00 1814.65) p2 (list 435.35 1813.40))
 (command "LINE" p1 p2 "")
 (setq p1 (list 435.50 1813.02) p2 (list 0.00 0.00))
 (command "TEXT" "J" "ML" p1   0.75  0.00 "137")
 (command "LAYER" "S" "CGBTHK" "")
 (setq p1 (list 440.00 1813.02) p2 (list 0.00 0.00))
 (command "TEXT" "J" "ML" p1   0.75  0.00 "0.35")
 (command "LAYER" "S" "CGBHZID" "")
 (setq p1 (list 444.50 1813.02) p2 (list 0.00 0.00))
 (command "TEXT" "J" "ML" p1   0.75  0.00 "")
 (setq p1 (list 446.75 1813.02) p2 (list 0.00 0.00))
 (command "TEXT" "J" "ML" p1   0.75  0.00 "8451")
 (command "LAYER" "S" "CGBLITHTXT" "")
 (setq p1 (list 450.50 1813.02) p2 (list 0.00 0.00))
 (command "TEXT" "J" "ML" p1   0.75  0.00 "LT GRY GRN FIRECLAY")
 (command "LAYER" "S" "CGBCMNT" "")
 (setq p1 (list 470.75 1813.02) p2 (list 0.00 0.00))
 (command "TEXT" "J" "ML" p1   0.75  0.00 "SFT")
 (command "LAYER" "S" "CGBMAIN" "")
 (setq p1 (list 428.00 1814.47) p2 (list 434.00 1814.47) p3 (list 434.00 1814.10) p4 (list 428.00 1814.10))
 (command "PLINE" p1 p2 p3 p4 "c")
 (command "HATCH" "ZIGZAG" 4.00 0.00 "L" "")
 (command "COLOR" "BYLAYER")
 (command "LAYER" "S" "CGBLITHCD" "")
 (setq p1 (list 434.00 1814.29) p2 (list 435.35 1812.15))
 (command "LINE" p1 p2 "")
 (setq p1 (list 435.50 1811.77) p2 (list 0.00 0.00))
 (command "TEXT" "J" "ML" p1   0.75  0.00 "541")
 (command "LAYER" "S" "CGBTHK" "")
 (setq p1 (list 440.00 1811.77) p2 (list 0.00 0.00))
 (command "TEXT" "J" "ML" p1   0.75  0.00 "0.37")
 (command "LAYER" "S" "CGBHZID" "")
 (setq p1 (list 444.50 1811.77) p2 (list 0.00 0.00))
 (command "TEXT" "J" "ML" p1   0.75  0.00 "")
 (setq p1 (list 446.75 1811.77) p2 (list 0.00 0.00))
 (command "TEXT" "J" "ML" p1   0.75  0.00 "8451")
 (command "LAYER" "S" "CGBLITHTXT" "")
 (setq p1 (list 450.50 1811.77) p2 (list 0.00 0.00))
 (command "TEXT" "J" "ML" p1   0.75  0.00 "GRY CROSSBED SS")
 (command "LAYER" "S" "CGBCMNT" "")
 (setq p1 (list 470.75 1811.77) p2 (list 0.00 0.00))
 (command "TEXT" "J" "ML" p1   0.75  0.00 "")
 (command "LAYER" "S" "CGBMAIN" "")
 (setq p1 (list 428.00 1814.10) p2 (list 434.00 1814.10) p3 (list 434.00 1809.44) p4 (list 428.00 1809.44))
 (command "PLINE" p1 p2 p3 p4 "c")
 (command "HATCH" "ZIGZAG" 5.00 0.00 "L" "")
 (command "COLOR" "BYLAYER")
 (command "LAYER" "S" "CGBLITHCD" "")
 (setq p1 (list 434.00 1811.77) p2 (list 435.35 1810.90))
 (command "LINE" p1 p2 "")
 (setq p1 (list 435.50 1810.52) p2 (list 0.00 0.00))
 (command "TEXT" "J" "ML" p1   0.75  0.00 "244")
 (command "LAYER" "S" "CGBTHK" "")
 (setq p1 (list 440.00 1810.52) p2 (list 0.00 0.00))
 (command "TEXT" "J" "ML" p1   0.75  0.00 "4.66")
 (command "LAYER" "S" "CGBHZID" "")
 (setq p1 (list 444.50 1810.52) p2 (list 0.00 0.00))
 (command "TEXT" "J" "ML" p1   0.75  0.00 "")
 (setq p1 (list 446.75 1810.52) p2 (list 0.00 0.00))
 (command "TEXT" "J" "ML" p1   0.75  0.00 "8451")
 (command "LAYER" "S" "CGBLITHTXT" "")
 (setq p1 (list 450.50 1810.52) p2 (list 0.00 0.00))
 (command "TEXT" "J" "ML" p1   0.75  0.00 "GRN SH W/LS NODS")
 (command "LAYER" "S" "CGBCMNT" "")
 (setq p1 (list 470.75 1810.52) p2 (list 0.00 0.00))
 (command "TEXT" "J" "ML" p1   0.75  0.00 "")
 (command "LAYER" "S" "CGBMAIN" "")
 (setq p1 (list 428.00 1809.44) p2 (list 434.00 1809.44) p3 (list 434.00 1808.69) p4 (list 428.00 1808.69))
 (command "PLINE" p1 p2 p3 p4 "c")
 (command "HATCH" "ZIGZAG" 0.50 0.00 "L" "")
 (command "COLOR" "BYLAYER")
 (command "LAYER" "S" "CGBLITHCD" "")
 (setq p1 (list 434.00 1809.07) p2 (list 435.35 1809.07))
 (command "LINE" p1 p2 "")
 (setq p1 (list 435.50 1808.69) p2 (list 0.00 0.00))
 (command "TEXT" "J" "ML" p1   0.75  0.00 "806")
 (command "LAYER" "S" "CGBTHK" "")
 (setq p1 (list 440.00 1808.69) p2 (list 0.00 0.00))
 (command "TEXT" "J" "ML" p1   0.75  0.00 "0.75")
 (command "LAYER" "S" "CGBHZID" "")
 (setq p1 (list 444.50 1808.69) p2 (list 0.00 0.00))
 (command "TEXT" "J" "ML" p1   0.75  0.00 "")
 (setq p1 (list 446.75 1808.69) p2 (list 0.00 0.00))
 (command "TEXT" "J" "ML" p1   0.75  0.00 "8451")
 (command "LAYER" "S" "CGBLITHTXT" "")
 (setq p1 (list 450.50 1808.69) p2 (list 0.00 0.00))
 (command "TEXT" "J" "ML" p1   0.75  0.00 "FN GRND SHLY LS W/LS NODS")
 (command "LAYER" "S" "CGBCMNT" "")
 (setq p1 (list 470.75 1808.69) p2 (list 0.00 0.00))
 (command "TEXT" "J" "ML" p1   0.75  0.00 "")
 (command "LAYER" "S" "CGBMAIN" "")
 (setq p1 (list 428.00 1808.69) p2 (list 434.00 1808.69) p3 (list 434.00 1805.35) p4 (list 428.00 1805.35))
 (command "PLINE" p1 p2 p3 p4 "c")
 (command "HATCH" "ZIGZAG" 4.00 0.00 "L" "")
 (command "COLOR" "BYLAYER")
 (command "LAYER" "S" "CGBLITHCD" "")
 (setq p1 (list 434.00 1807.02) p2 (list 435.35 1807.02))
 (command "LINE" p1 p2 "")
 (setq p1 (list 435.50 1806.65) p2 (list 0.00 0.00))
 (command "TEXT" "J" "ML" p1   0.75  0.00 "344")
 (command "LAYER" "S" "CGBTHK" "")
 (setq p1 (list 440.00 1806.65) p2 (list 0.00 0.00))
 (command "TEXT" "J" "ML" p1   0.75  0.00 "3.34")
 (command "LAYER" "S" "CGBHZID" "")
 (setq p1 (list 444.50 1806.65) p2 (list 0.00 0.00))
 (command "TEXT" "J" "ML" p1   0.75  0.00 "")
 (setq p1 (list 446.75 1806.65) p2 (list 0.00 0.00))
 (command "TEXT" "J" "ML" p1   0.75  0.00 "8451")
 (command "LAYER" "S" "CGBLITHTXT" "")
 (setq p1 (list 450.50 1806.65) p2 (list 0.00 0.00))
 (command "TEXT" "J" "ML" p1   0.75  0.00 "GRN MASS SDY SH")
 (command "LAYER" "S" "CGBCMNT" "")
 (setq p1 (list 470.75 1806.65) p2 (list 0.00 0.00))
 (command "TEXT" "J" "ML" p1   0.75  0.00 "FRACS")
 (command "LAYER" "S" "CGBMAIN" "")
 (setq p1 (list 428.00 1805.35) p2 (list 434.00 1805.35) p3 (list 434.00 1799.47) p4 (list 428.00 1799.47))
 (command "PLINE" p1 p2 p3 p4 "c")
 (command "HATCH" "ZIGZAG" 2.50 90.00 "L" "")
 (command "COLOR" "BYLAYER")
 (command "LAYER" "S" "CGBLITHCD" "")
 (setq p1 (list 434.00 1802.41) p2 (list 435.35 1802.41))
 (command "LINE" p1 p2 "")
 (setq p1 (list 435.50 1802.04) p2 (list 0.00 0.00))
 (command "TEXT" "J" "ML" p1   0.75  0.00 "324")
 (command "LAYER" "S" "CGBTHK" "")
 (setq p1 (list 440.00 1802.04) p2 (list 0.00 0.00))
 (command "TEXT" "J" "ML" p1   0.75  0.00 "5.88")
 (command "LAYER" "S" "CGBHZID" "")
 (setq p1 (list 444.50 1802.04) p2 (list 0.00 0.00))
 (command "TEXT" "J" "ML" p1   0.75  0.00 "")
 (setq p1 (list 446.75 1802.04) p2 (list 0.00 0.00))
 (command "TEXT" "J" "ML" p1   0.75  0.00 "8451")
 (command "LAYER" "S" "CGBLITHTXT" "")
 (setq p1 (list 450.50 1802.04) p2 (list 0.00 0.00))
 (command "TEXT" "J" "ML" p1   0.75  0.00 "DRK GRY MASS SDY SH")
 (command "LAYER" "S" "CGBCMNT" "")
 (setq p1 (list 470.75 1802.04) p2 (list 0.00 0.00))
 (command "TEXT" "J" "ML" p1   0.75  0.00 "CRSN DWN")
 (command "LAYER" "S" "CGBMAIN" "")
 (setq p1 (list 428.00 1799.47) p2 (list 434.00 1799.47) p3 (list 434.00 1784.47) p4 (list 428.00 1784.47))
 (command "PLINE" p1 p2 p3 p4 "c")
 (command "HATCH" "ZIGZAG" 4.00 0.00 "L" "")
 (command "COLOR" "BYLAYER")
 (command "LAYER" "S" "CGBLITHCD" "")
 (setq p1 (list 434.00 1791.97) p2 (list 435.35 1791.97))
 (command "LINE" p1 p2 "")
 (setq p1 (list 435.50 1791.60) p2 (list 0.00 0.00))
 (command "TEXT" "J" "ML" p1   0.75  0.00 "541")
 (command "LAYER" "S" "CGBTHK" "")
 (setq p1 (list 440.00 1791.60) p2 (list 0.00 0.00))
 (command "TEXT" "J" "ML" p1   0.75  0.00 "15.00")
 (command "LAYER" "S" "CGBHZID" "")
 (setq p1 (list 444.50 1791.60) p2 (list 0.00 0.00))
 (command "TEXT" "J" "ML" p1   0.75  0.00 "")
 (setq p1 (list 446.75 1791.60) p2 (list 0.00 0.00))
 (command "TEXT" "J" "ML" p1   0.75  0.00 "8451")
 (command "LAYER" "S" "CGBLITHTXT" "")
 (setq p1 (list 450.50 1791.60) p2 (list 0.00 0.00))
 (command "TEXT" "J" "ML" p1   0.75  0.00 "GRY CROSSBED SS")
 (command "LAYER" "S" "CGBCMNT" "")
 (setq p1 (list 470.75 1791.60) p2 (list 0.00 0.00))
 (command "TEXT" "J" "ML" p1   0.75  0.00 "")
 (command "LAYER" "S" "CGBMAIN" "")
 (setq p1 (list 428.00 1784.47) p2 (list 434.00 1784.47) p3 (list 434.00 1781.80) p4 (list 428.00 1781.80))
 (command "PLINE" p1 p2 p3 p4 "c")
 (command "HATCH" "ZIGZAG" 4.00 0.00 "L" "")
 (command "COLOR" "BYLAYER")
 (command "LAYER" "S" "CGBLITHCD" "")
 (setq p1 (list 434.00 1783.14) p2 (list 435.35 1783.14))
 (command "LINE" p1 p2 "")
 (setq p1 (list 435.50 1782.76) p2 (list 0.00 0.00))
 (command "TEXT" "J" "ML" p1   0.75  0.00 "541")
 (command "LAYER" "S" "CGBTHK" "")
 (setq p1 (list 440.00 1782.76) p2 (list 0.00 0.00))
 (command "TEXT" "J" "ML" p1   0.75  0.00 "2.67")
 (command "LAYER" "S" "CGBHZID" "")
 (setq p1 (list 444.50 1782.76) p2 (list 0.00 0.00))
 (command "TEXT" "J" "ML" p1   0.75  0.00 "")
 (setq p1 (list 446.75 1782.76) p2 (list 0.00 0.00))
 (command "TEXT" "J" "ML" p1   0.75  0.00 "8451")
 (command "LAYER" "S" "CGBLITHTXT" "")
 (setq p1 (list 450.50 1782.76) p2 (list 0.00 0.00))
 (command "TEXT" "J" "ML" p1   0.75  0.00 "GRY CROSSBED SS")
 (command "LAYER" "S" "CGBCMNT" "")
 (setq p1 (list 470.75 1782.76) p2 (list 0.00 0.00))
 (command "TEXT" "J" "ML" p1   0.75  0.00 "")
 (command "LAYER" "S" "CGBMAIN" "")
 (setq p1 (list 428.00 1781.80) p2 (list 434.00 1781.80) p3 (list 434.00 1770.17) p4 (list 428.00 1770.17))
 (command "PLINE" p1 p2 p3 p4 "c")
 (command "HATCH" "ZIGZAG" 4.00 0.00 "L" "")
 (command "COLOR" "BYLAYER")
 (command "LAYER" "S" "CGBLITHCD" "")
 (setq p1 (list 434.00 1775.99) p2 (list 435.35 1775.99))
 (command "LINE" p1 p2 "")
 (setq p1 (list 435.50 1775.61) p2 (list 0.00 0.00))
 (command "TEXT" "J" "ML" p1   0.75  0.00 "563")
 (command "LAYER" "S" "CGBTHK" "")
 (setq p1 (list 440.00 1775.61) p2 (list 0.00 0.00))
 (command "TEXT" "J" "ML" p1   0.75  0.00 "11.63")
 (command "LAYER" "S" "CGBHZID" "")
 (setq p1 (list 444.50 1775.61) p2 (list 0.00 0.00))
 (command "TEXT" "J" "ML" p1   0.75  0.00 "")
 (setq p1 (list 446.75 1775.61) p2 (list 0.00 0.00))
 (command "TEXT" "J" "ML" p1   0.75  0.00 "8451")
 (command "LAYER" "S" "CGBLITHTXT" "")
 (setq p1 (list 450.50 1775.61) p2 (list 0.00 0.00))
 (command "TEXT" "J" "ML" p1   0.75  0.00 "HARD SS W/SH STKS")
 (command "LAYER" "S" "CGBCMNT" "")
 (setq p1 (list 470.75 1775.61) p2 (list 0.00 0.00))
 (command "TEXT" "J" "ML" p1   0.75  0.00 "SLC")
 (command "LAYER" "S" "CGBMAIN" "")
 (setq p1 (list 428.00 1770.17) p2 (list 434.00 1770.17) p3 (list 434.00 1770.03) p4 (list 428.00 1770.03))
 (command "PLINE" p1 p2 p3 p4 "c")
 (command "HATCH" "ZIGZAG" 2.50 90.00 "L" "")
 (command "COLOR" "BYLAYER")
 (command "LAYER" "S" "CGBLITHCD" "")
 (setq p1 (list 434.00 1770.10) p2 (list 435.35 1770.10))
 (command "LINE" p1 p2 "")
 (setq p1 (list 435.50 1769.73) p2 (list 0.00 0.00))
 (command "TEXT" "J" "ML" p1   0.75  0.00 "324")
 (command "LAYER" "S" "CGBTHK" "")
 (setq p1 (list 440.00 1769.73) p2 (list 0.00 0.00))
 (command "TEXT" "J" "ML" p1   0.75  0.00 "0.14")
 (command "LAYER" "S" "CGBHZID" "")
 (setq p1 (list 444.50 1769.73) p2 (list 0.00 0.00))
 (command "TEXT" "J" "ML" p1   0.75  0.00 "")
 (setq p1 (list 446.75 1769.73) p2 (list 0.00 0.00))
 (command "TEXT" "J" "ML" p1   0.75  0.00 "8451")
 (command "LAYER" "S" "CGBLITHTXT" "")
 (setq p1 (list 450.50 1769.73) p2 (list 0.00 0.00))
 (command "TEXT" "J" "ML" p1   0.75  0.00 "DRK GRY MASS SDY SH")
 (command "LAYER" "S" "CGBCMNT" "")
 (setq p1 (list 470.75 1769.73) p2 (list 0.00 0.00))
 (command "TEXT" "J" "ML" p1   0.75  0.00 "")
 (command "LAYER" "S" "CGBMAIN" "")
 (setq p1 (list 428.00 1770.03) p2 (list 434.00 1770.03) p3 (list 434.00 1769.32) p4 (list 428.00 1769.32))
 (command "PLINE" p1 p2 p3 p4 "c")
 (command "HATCH" "ZIGZAG" 4.00 0.00 "L" "")
 (command "COLOR" "BYLAYER")
 (command "LAYER" "S" "CGBLITHCD" "")
 (setq p1 (list 434.00 1769.68) p2 (list 435.35 1768.43))
 (command "LINE" p1 p2 "")
 (setq p1 (list 435.50 1768.05) p2 (list 0.00 0.00))
 (command "TEXT" "J" "ML" p1   0.75  0.00 "541")
 (command "LAYER" "S" "CGBTHK" "")
 (setq p1 (list 440.00 1768.05) p2 (list 0.00 0.00))
 (command "TEXT" "J" "ML" p1   0.75  0.00 "0.71")
 (command "LAYER" "S" "CGBHZID" "")
 (setq p1 (list 444.50 1768.05) p2 (list 0.00 0.00))
 (command "TEXT" "J" "ML" p1   0.75  0.00 "")
 (setq p1 (list 446.75 1768.05) p2 (list 0.00 0.00))
 (command "TEXT" "J" "ML" p1   0.75  0.00 "8451")
 (command "LAYER" "S" "CGBLITHTXT" "")
 (setq p1 (list 450.50 1768.05) p2 (list 0.00 0.00))
 (command "TEXT" "J" "ML" p1   0.75  0.00 "GRY CROSSBED SS")
 (command "LAYER" "S" "CGBCMNT" "")
 (setq p1 (list 470.75 1768.05) p2 (list 0.00 0.00))
 (command "TEXT" "J" "ML" p1   0.75  0.00 "")
 (command "LAYER" "S" "CGBMAIN" "")
 (setq p1 (list 428.00 1769.32) p2 (list 434.00 1769.32) p3 (list 434.00 1767.36) p4 (list 428.00 1767.36))
 (command "PLINE" p1 p2 p3 p4 "c")
 (command "HATCH" "ZIGZAG" 0.25 0.00 "L" "")
 (command "COLOR" "BYLAYER")
 (command "LAYER" "S" "CGBLITHCD" "")
 (setq p1 (list 434.00 1768.34) p2 (list 435.35 1767.18))
 (command "LINE" p1 p2 "")
 (setq p1 (list 435.50 1766.80) p2 (list 0.00 0.00))
 (command "TEXT" "J" "ML" p1   0.75  0.00 "742")
 (command "LAYER" "S" "CGBTHK" "")
 (setq p1 (list 440.00 1766.80) p2 (list 0.00 0.00))
 (command "TEXT" "J" "ML" p1   0.75  0.00 "1.96")
 (command "LAYER" "S" "CGBHZID" "")
 (setq p1 (list 444.50 1766.80) p2 (list 0.00 0.00))
 (command "TEXT" "J" "ML" p1   0.75  0.00 "")
 (setq p1 (list 446.75 1766.80) p2 (list 0.00 0.00))
 (command "TEXT" "J" "ML" p1   0.75  0.00 "8451")
 (command "LAYER" "S" "CGBLITHTXT" "")
 (setq p1 (list 450.50 1766.80) p2 (list 0.00 0.00))
 (command "TEXT" "J" "ML" p1   0.75  0.00 "GRY SH PEB CGL")
 (command "LAYER" "S" "CGBCMNT" "")
 (setq p1 (list 470.75 1766.80) p2 (list 0.00 0.00))
 (command "TEXT" "J" "ML" p1   0.75  0.00 "")
 (command "LAYER" "S" "CGBMAIN" "")
 (setq p1 (list 428.00 1767.36) p2 (list 434.00 1767.36) p3 (list 434.00 1764.43) p4 (list 428.00 1764.43))
 (command "PLINE" p1 p2 p3 p4 "c")
 (command "HATCH" "ZIGZAG" 4.00 0.00 "L" "")
 (command "COLOR" "BYLAYER")
 (command "LAYER" "S" "CGBLITHCD" "")
 (setq p1 (list 434.00 1765.90) p2 (list 435.35 1765.90))
 (command "LINE" p1 p2 "")
 (setq p1 (list 435.50 1765.52) p2 (list 0.00 0.00))
 (command "TEXT" "J" "ML" p1   0.75  0.00 "543")
 (command "LAYER" "S" "CGBTHK" "")
 (setq p1 (list 440.00 1765.52) p2 (list 0.00 0.00))
 (command "TEXT" "J" "ML" p1   0.75  0.00 "2.93")
 (command "LAYER" "S" "CGBHZID" "")
 (setq p1 (list 444.50 1765.52) p2 (list 0.00 0.00))
 (command "TEXT" "J" "ML" p1   0.75  0.00 "")
 (setq p1 (list 446.75 1765.52) p2 (list 0.00 0.00))
 (command "TEXT" "J" "ML" p1   0.75  0.00 "8451")
 (command "LAYER" "S" "CGBLITHTXT" "")
 (setq p1 (list 450.50 1765.52) p2 (list 0.00 0.00))
 (command "TEXT" "J" "ML" p1   0.75  0.00 "GRY SS W/SH STKS")
 (command "LAYER" "S" "CGBCMNT" "")
 (setq p1 (list 470.75 1765.52) p2 (list 0.00 0.00))
 (command "TEXT" "J" "ML" p1   0.75  0.00 "")
 (command "LAYER" "S" "CGBMAIN" "")
 (setq p1 (list 428.00 1764.43) p2 (list 434.00 1764.43) p3 (list 434.00 1759.36) p4 (list 428.00 1759.36))
 (command "PLINE" p1 p2 p3 p4 "c")
 (command "HATCH" "ZIGZAG" 4.00 0.00 "L" "")
 (command "COLOR" "BYLAYER")
 (command "LAYER" "S" "CGBLITHCD" "")
 (setq p1 (list 434.00 1761.90) p2 (list 435.35 1761.90))
 (command "LINE" p1 p2 "")
 (setq p1 (list 435.50 1761.52) p2 (list 0.00 0.00))
 (command "TEXT" "J" "ML" p1   0.75  0.00 "563")
 (command "LAYER" "S" "CGBTHK" "")
 (setq p1 (list 440.00 1761.52) p2 (list 0.00 0.00))
 (command "TEXT" "J" "ML" p1   0.75  0.00 "5.07")
 (command "LAYER" "S" "CGBHZID" "")
 (setq p1 (list 444.50 1761.52) p2 (list 0.00 0.00))
 (command "TEXT" "J" "ML" p1   0.75  0.00 "")
 (setq p1 (list 446.75 1761.52) p2 (list 0.00 0.00))
 (command "TEXT" "J" "ML" p1   0.75  0.00 "8451")
 (command "LAYER" "S" "CGBLITHTXT" "")
 (setq p1 (list 450.50 1761.52) p2 (list 0.00 0.00))
 (command "TEXT" "J" "ML" p1   0.75  0.00 "HARD SS W/SH STKS")
 (command "LAYER" "S" "CGBCMNT" "")
 (setq p1 (list 470.75 1761.52) p2 (list 0.00 0.00))
 (command "TEXT" "J" "ML" p1   0.75  0.00 "SLC")
 (command "LAYER" "S" "CGBMAIN" "")
 (setq p1 (list 428.00 1759.36) p2 (list 434.00 1759.36) p3 (list 434.00 1756.20) p4 (list 428.00 1756.20))
 (command "PLINE" p1 p2 p3 p4 "c")
 (command "HATCH" "ZIGZAG" 2.50 90.00 "L" "")
 (command "COLOR" "BYLAYER")
 (command "LAYER" "S" "CGBLITHCD" "")
 (setq p1 (list 434.00 1757.78) p2 (list 435.35 1757.78))
 (command "LINE" p1 p2 "")
 (setq p1 (list 435.50 1757.41) p2 (list 0.00 0.00))
 (command "TEXT" "J" "ML" p1   0.75  0.00 "324")
 (command "LAYER" "S" "CGBTHK" "")
 (setq p1 (list 440.00 1757.41) p2 (list 0.00 0.00))
 (command "TEXT" "J" "ML" p1   0.75  0.00 "3.16")
 (command "LAYER" "S" "CGBHZID" "")
 (setq p1 (list 444.50 1757.41) p2 (list 0.00 0.00))
 (command "TEXT" "J" "ML" p1   0.75  0.00 "")
 (setq p1 (list 446.75 1757.41) p2 (list 0.00 0.00))
 (command "TEXT" "J" "ML" p1   0.75  0.00 "8451")
 (command "LAYER" "S" "CGBLITHTXT" "")
 (setq p1 (list 450.50 1757.41) p2 (list 0.00 0.00))
 (command "TEXT" "J" "ML" p1   0.75  0.00 "DRK GRY MASS SDY SH")
 (command "LAYER" "S" "CGBCMNT" "")
 (setq p1 (list 470.75 1757.41) p2 (list 0.00 0.00))
 (command "TEXT" "J" "ML" p1   0.75  0.00 "")
 (command "LAYER" "S" "CGBMAIN" "")
 (setq p1 (list 428.00 1756.20) p2 (list 434.00 1756.20) p3 (list 434.00 1754.77) p4 (list 428.00 1754.77))
 (command "PLINE" p1 p2 p3 p4 "c")
 (command "HATCH" "ZIGZAG" 4.00 0.00 "L" "")
 (command "COLOR" "BYLAYER")
 (command "LAYER" "S" "CGBLITHCD" "")
 (setq p1 (list 434.00 1755.49) p2 (list 435.35 1755.49))
 (command "LINE" p1 p2 "")
 (setq p1 (list 435.50 1755.11) p2 (list 0.00 0.00))
 (command "TEXT" "J" "ML" p1   0.75  0.00 "124")
 (command "LAYER" "S" "CGBTHK" "")
 (setq p1 (list 440.00 1755.11) p2 (list 0.00 0.00))
 (command "TEXT" "J" "ML" p1   0.75  0.00 "1.43")
 (command "LAYER" "S" "CGBHZID" "")
 (setq p1 (list 444.50 1755.11) p2 (list 0.00 0.00))
 (command "TEXT" "J" "ML" p1   0.75  0.00 "")
 (setq p1 (list 446.75 1755.11) p2 (list 0.00 0.00))
 (command "TEXT" "J" "ML" p1   0.75  0.00 "8451")
 (command "LAYER" "S" "CGBLITHTXT" "")
 (setq p1 (list 450.50 1755.11) p2 (list 0.00 0.00))
 (command "TEXT" "J" "ML" p1   0.75  0.00 "DRK GRY SH")
 (command "LAYER" "S" "CGBCMNT" "")
 (setq p1 (list 470.75 1755.11) p2 (list 0.00 0.00))
 (command "TEXT" "J" "ML" p1   0.75  0.00 "")
 (command "LAYER" "S" "CGBMAIN" "")
 (setq p1 (list 428.00 1754.77) p2 (list 434.00 1754.77) p3 (list 434.00 1754.19) p4 (list 428.00 1754.19))
 (command "PLINE" p1 p2 p3 p4 "c")
 (command "HATCH" "ZIGZAG" 4.00 22.50 "L" "")
 (command "COLOR" "BYLAYER")
 (command "LAYER" "S" "CGBLITHCD" "")
 (setq p1 (list 434.00 1754.48) p2 (list 435.35 1753.23))
 (command "LINE" p1 p2 "")
 (setq p1 (list 435.50 1752.86) p2 (list 0.00 0.00))
 (command "TEXT" "J" "ML" p1   0.75  0.00 "114")
 (command "LAYER" "S" "CGBTHK" "")
 (setq p1 (list 440.00 1752.86) p2 (list 0.00 0.00))
 (command "TEXT" "J" "ML" p1   0.75  0.00 "0.58")
 (command "LAYER" "S" "CGBHZID" "")
 (setq p1 (list 444.50 1752.86) p2 (list 0.00 0.00))
 (command "TEXT" "J" "ML" p1   0.75  0.00 "")
 (setq p1 (list 446.75 1752.86) p2 (list 0.00 0.00))
 (command "TEXT" "J" "ML" p1   0.75  0.00 "8451")
 (command "LAYER" "S" "CGBLITHTXT" "")
 (setq p1 (list 450.50 1752.86) p2 (list 0.00 0.00))
 (command "TEXT" "J" "ML" p1   0.75  0.00 "BLK SH")
 (command "LAYER" "S" "CGBCMNT" "")
 (setq p1 (list 470.75 1752.86) p2 (list 0.00 0.00))
 (command "TEXT" "J" "ML" p1   0.75  0.00 "")
 (command "LAYER" "S" "CGBMAIN" "")
 (setq p1 (list 428.00 1754.19) p2 (list 434.00 1754.19) p3 (list 434.00 1753.95) p4 (list 428.00 1753.95))
 (command "PLINE" p1 p2 p3 p4 "c")
 (command "HATCH" "ZIGZAG" 4.00 22.50 "L" "")
 (command "COLOR" "BYLAYER")
 (command "LAYER" "S" "CGBLITHCD" "")
 (setq p1 (list 434.00 1754.07) p2 (list 435.35 1751.98))
 (command "LINE" p1 p2 "")
 (setq p1 (list 435.50 1751.61) p2 (list 0.00 0.00))
 (command "TEXT" "J" "ML" p1   0.75  0.00 "114")
 (command "LAYER" "S" "CGBTHK" "")
 (setq p1 (list 440.00 1751.61) p2 (list 0.00 0.00))
 (command "TEXT" "J" "ML" p1   0.75  0.00 "0.24")
 (command "LAYER" "S" "CGBHZID" "")
 (setq p1 (list 444.50 1751.61) p2 (list 0.00 0.00))
 (command "TEXT" "J" "ML" p1   0.75  0.00 "")
 (setq p1 (list 446.75 1751.61) p2 (list 0.00 0.00))
 (command "TEXT" "J" "ML" p1   0.75  0.00 "8451")
 (command "LAYER" "S" "CGBLITHTXT" "")
 (setq p1 (list 450.50 1751.61) p2 (list 0.00 0.00))
 (command "TEXT" "J" "ML" p1   0.75  0.00 "BLK SH")
 (command "LAYER" "S" "CGBCMNT" "")
 (setq p1 (list 470.75 1751.61) p2 (list 0.00 0.00))
 (command "TEXT" "J" "ML" p1   0.75  0.00 "")
 (command "LAYER" "S" "CGBMAIN" "")
 (setq p1 (list 428.00 1753.95) p2 (list 434.00 1753.95) p3 (list 434.00 1749.30) p4 (list 428.00 1749.30))
 (command "PLINE" p1 p2 p3 p4 "c")
 (command "HATCH" "ZIGZAG" 5.00 0.00 "L" "")
 (command "COLOR" "BYLAYER")
 (command "LAYER" "S" "CGBLITHCD" "")
 (setq p1 (list 434.00 1751.63) p2 (list 435.35 1750.73))
 (command "LINE" p1 p2 "")
 (setq p1 (list 435.50 1750.36) p2 (list 0.00 0.00))
 (command "TEXT" "J" "ML" p1   0.75  0.00 "224")
 (command "LAYER" "S" "CGBTHK" "")
 (setq p1 (list 440.00 1750.36) p2 (list 0.00 0.00))
 (command "TEXT" "J" "ML" p1   0.75  0.00 "4.65")
 (command "LAYER" "S" "CGBHZID" "")
 (setq p1 (list 444.50 1750.36) p2 (list 0.00 0.00))
 (command "TEXT" "J" "ML" p1   0.75  0.00 "")
 (setq p1 (list 446.75 1750.36) p2 (list 0.00 0.00))
 (command "TEXT" "J" "ML" p1   0.75  0.00 "8451")
 (command "LAYER" "S" "CGBLITHTXT" "")
 (setq p1 (list 450.50 1750.36) p2 (list 0.00 0.00))
 (command "TEXT" "J" "ML" p1   0.75  0.00 "DRK GRY SH W/LS NODS")
 (command "LAYER" "S" "CGBCMNT" "")
 (setq p1 (list 470.75 1750.36) p2 (list 0.00 0.00))
 (command "TEXT" "J" "ML" p1   0.75  0.00 "")
 (command "LAYER" "S" "CGBMAIN" "")
 (setq p1 (list 428.00 1749.30) p2 (list 434.00 1749.30) p3 (list 434.00 1746.31) p4 (list 428.00 1746.31))
 (command "PLINE" p1 p2 p3 p4 "c")
 (command "HATCH" "ZIGZAG" 4.00 0.00 "L" "")
 (command "COLOR" "BYLAYER")
 (command "LAYER" "S" "CGBLITHCD" "")
 (setq p1 (list 434.00 1747.81) p2 (list 435.35 1747.81))
 (command "LINE" p1 p2 "")
 (setq p1 (list 435.50 1747.43) p2 (list 0.00 0.00))
 (command "TEXT" "J" "ML" p1   0.75  0.00 "374")
 (command "LAYER" "S" "CGBTHK" "")
 (setq p1 (list 440.00 1747.43) p2 (list 0.00 0.00))
 (command "TEXT" "J" "ML" p1   0.75  0.00 "2.99")
 (command "LAYER" "S" "CGBHZID" "")
 (setq p1 (list 444.50 1747.43) p2 (list 0.00 0.00))
 (command "TEXT" "J" "ML" p1   0.75  0.00 "")
 (setq p1 (list 446.75 1747.43) p2 (list 0.00 0.00))
 (command "TEXT" "J" "ML" p1   0.75  0.00 "8451")
 (command "LAYER" "S" "CGBLITHTXT" "")
 (setq p1 (list 450.50 1747.43) p2 (list 0.00 0.00))
 (command "TEXT" "J" "ML" p1   0.75  0.00 "GRY/GRN SDY SH")
 (command "LAYER" "S" "CGBCMNT" "")
 (setq p1 (list 470.75 1747.43) p2 (list 0.00 0.00))
 (command "TEXT" "J" "ML" p1   0.75  0.00 "")
 (command "LAYER" "S" "CGBMAIN" "")
 (setq p1 (list 428.00 1746.31) p2 (list 434.00 1746.31) p3 (list 434.00 1745.31) p4 (list 428.00 1745.31))
 (command "PLINE" p1 p2 p3 p4 "c")
 (command "HATCH" "ZIGZAG" 4.00 0.00 "L" "")
 (command "COLOR" "BYLAYER")
 (command "LAYER" "S" "CGBLITHCD" "")
 (setq p1 (list 434.00 1745.81) p2 (list 435.35 1745.81))
 (command "LINE" p1 p2 "")
 (setq p1 (list 435.50 1745.44) p2 (list 0.00 0.00))
 (command "TEXT" "J" "ML" p1   0.75  0.00 "444")
 (command "LAYER" "S" "CGBTHK" "")
 (setq p1 (list 440.00 1745.44) p2 (list 0.00 0.00))
 (command "TEXT" "J" "ML" p1   0.75  0.00 "1.00")
 (command "LAYER" "S" "CGBHZID" "")
 (setq p1 (list 444.50 1745.44) p2 (list 0.00 0.00))
 (command "TEXT" "J" "ML" p1   0.75  0.00 "")
 (setq p1 (list 446.75 1745.44) p2 (list 0.00 0.00))
 (command "TEXT" "J" "ML" p1   0.75  0.00 "8451")
 (command "LAYER" "S" "CGBLITHTXT" "")
 (setq p1 (list 450.50 1745.44) p2 (list 0.00 0.00))
 (command "TEXT" "J" "ML" p1   0.75  0.00 "GRN SDY SH W/LS NODS")
 (command "LAYER" "S" "CGBCMNT" "")
 (setq p1 (list 470.75 1745.44) p2 (list 0.00 0.00))
 (command "TEXT" "J" "ML" p1   0.75  0.00 "")
 (command "LAYER" "S" "CGBMAIN" "")
 (setq p1 (list 428.00 1745.31) p2 (list 434.00 1745.31) p3 (list 434.00 1744.01) p4 (list 428.00 1744.01))
 (command "PLINE" p1 p2 p3 p4 "c")
 (command "HATCH" "ZIGZAG" 4.00 0.00 "L" "")
 (command "COLOR" "BYLAYER")
 (command "LAYER" "S" "CGBLITHCD" "")
 (setq p1 (list 434.00 1744.66) p2 (list 435.35 1743.41))
 (command "LINE" p1 p2 "")
 (setq p1 (list 435.50 1743.04) p2 (list 0.00 0.00))
 (command "TEXT" "J" "ML" p1   0.75  0.00 "125")
 (command "LAYER" "S" "CGBTHK" "")
 (setq p1 (list 440.00 1743.04) p2 (list 0.00 0.00))
 (command "TEXT" "J" "ML" p1   0.75  0.00 "1.30")
 (command "LAYER" "S" "CGBHZID" "")
 (setq p1 (list 444.50 1743.04) p2 (list 0.00 0.00))
 (command "TEXT" "J" "ML" p1   0.75  0.00 "")
 (setq p1 (list 446.75 1743.04) p2 (list 0.00 0.00))
 (command "TEXT" "J" "ML" p1   0.75  0.00 "8451")
 (command "LAYER" "S" "CGBLITHTXT" "")
 (setq p1 (list 450.50 1743.04) p2 (list 0.00 0.00))
 (command "TEXT" "J" "ML" p1   0.75  0.00 "DRK GRY CHRND SH")
 (command "LAYER" "S" "CGBCMNT" "")
 (setq p1 (list 470.75 1743.04) p2 (list 0.00 0.00))
 (command "TEXT" "J" "ML" p1   0.75  0.00 "CARBONACEOUS")
 (command "LAYER" "S" "CGBMAIN" "")
 (setq p1 (list 428.00 1744.01) p2 (list 434.00 1744.01) p3 (list 434.00 1743.36) p4 (list 428.00 1743.36))
 (command "PLINE" p1 p2 p3 p4 "c")
 (command "HATCH" "ZIGZAG" 0.50 0.00 "L" "")
 (command "COLOR" "BYLAYER")
 (command "LAYER" "S" "CGBLITHCD" "")
 (setq p1 (list 434.00 1743.69) p2 (list 435.35 1742.16))
 (command "LINE" p1 p2 "")
 (setq p1 (list 435.50 1741.79) p2 (list 0.00 0.00))
 (command "TEXT" "J" "ML" p1   0.75  0.00 "806")
 (command "LAYER" "S" "CGBTHK" "")
 (setq p1 (list 440.00 1741.79) p2 (list 0.00 0.00))
 (command "TEXT" "J" "ML" p1   0.75  0.00 "0.65")
 (command "LAYER" "S" "CGBHZID" "")
 (setq p1 (list 444.50 1741.79) p2 (list 0.00 0.00))
 (command "TEXT" "J" "ML" p1   0.75  0.00 "")
 (setq p1 (list 446.75 1741.79) p2 (list 0.00 0.00))
 (command "TEXT" "J" "ML" p1   0.75  0.00 "8451")
 (command "LAYER" "S" "CGBLITHTXT" "")
 (setq p1 (list 450.50 1741.79) p2 (list 0.00 0.00))
 (command "TEXT" "J" "ML" p1   0.75  0.00 "FN GRND SHLY LS W/LS NODS")
 (command "LAYER" "S" "CGBCMNT" "")
 (setq p1 (list 470.75 1741.79) p2 (list 0.00 0.00))
 (command "TEXT" "J" "ML" p1   0.75  0.00 "")
 (command "LAYER" "S" "CGBMAIN" "")
 (setq p1 (list 428.00 1743.36) p2 (list 434.00 1743.36) p3 (list 434.00 1742.78) p4 (list 428.00 1742.78))
 (command "PLINE" p1 p2 p3 p4 "c")
 (command "HATCH" "ZIGZAG" 0.25 0.00 "L" "")
 (command "COLOR" "BYLAYER")
 (command "LAYER" "S" "CGBLITHCD" "")
 (setq p1 (list 434.00 1743.07) p2 (list 435.35 1740.91))
 (command "LINE" p1 p2 "")
 (setq p1 (list 435.50 1740.54) p2 (list 0.00 0.00))
 (command "TEXT" "J" "ML" p1   0.75  0.00 "127")
 (command "LAYER" "S" "CGBTHK" "")
 (setq p1 (list 440.00 1740.54) p2 (list 0.00 0.00))
 (command "TEXT" "J" "ML" p1   0.75  0.00 "0.58")
 (command "LAYER" "S" "CGBHZID" "")
 (setq p1 (list 444.50 1740.54) p2 (list 0.00 0.00))
 (command "TEXT" "J" "ML" p1   0.75  0.00 "")
 (setq p1 (list 446.75 1740.54) p2 (list 0.00 0.00))
 (command "TEXT" "J" "ML" p1   0.75  0.00 "8451")
 (command "LAYER" "S" "CGBLITHTXT" "")
 (setq p1 (list 450.50 1740.54) p2 (list 0.00 0.00))
 (command "TEXT" "J" "ML" p1   0.75  0.00 "DRK GRY FIRECLAY")
 (command "LAYER" "S" "CGBCMNT" "")
 (setq p1 (list 470.75 1740.54) p2 (list 0.00 0.00))
 (command "TEXT" "J" "ML" p1   0.75  0.00 "")
 (command "LAYER" "S" "CGBMAIN" "")
 (setq p1 (list 428.00 1742.78) p2 (list 434.00 1742.78) p3 (list 434.00 1739.01) p4 (list 428.00 1739.01))
 (command "PLINE" p1 p2 p3 p4 "c")
 (command "HATCH" "ZIGZAG" 5.00 0.00 "L" "")
 (command "COLOR" "BYLAYER")
 (command "LAYER" "S" "CGBLITHCD" "")
 (setq p1 (list 434.00 1740.90) p2 (list 435.35 1739.66))
 (command "LINE" p1 p2 "")
 (setq p1 (list 435.50 1739.29) p2 (list 0.00 0.00))
 (command "TEXT" "J" "ML" p1   0.75  0.00 "274")
 (command "LAYER" "S" "CGBTHK" "")
 (setq p1 (list 440.00 1739.29) p2 (list 0.00 0.00))
 (command "TEXT" "J" "ML" p1   0.75  0.00 "3.77")
 (command "LAYER" "S" "CGBHZID" "")
 (setq p1 (list 444.50 1739.29) p2 (list 0.00 0.00))
 (command "TEXT" "J" "ML" p1   0.75  0.00 "")
 (setq p1 (list 446.75 1739.29) p2 (list 0.00 0.00))
 (command "TEXT" "J" "ML" p1   0.75  0.00 "8451")
 (command "LAYER" "S" "CGBLITHTXT" "")
 (setq p1 (list 450.50 1739.29) p2 (list 0.00 0.00))
 (command "TEXT" "J" "ML" p1   0.75  0.00 "GRY/GRN SH W/LS NODS")
 (command "LAYER" "S" "CGBCMNT" "")
 (setq p1 (list 470.75 1739.29) p2 (list 0.00 0.00))
 (command "TEXT" "J" "ML" p1   0.75  0.00 "SLX")
 (command "LAYER" "S" "CGBMAIN" "")
 (setq p1 (list 428.00 1739.01) p2 (list 434.00 1739.01) p3 (list 434.00 1736.67) p4 (list 428.00 1736.67))
 (command "PLINE" p1 p2 p3 p4 "c")
 (command "HATCH" "ZIGZAG" 10.00 0.00 "L" "")
 (command "COLOR" "BYLAYER")
 (command "LAYER" "S" "CGBLITHCD" "")
 (setq p1 (list 434.00 1737.84) p2 (list 435.35 1737.84))
 (command "LINE" p1 p2 "")
 (setq p1 (list 435.50 1737.47) p2 (list 0.00 0.00))
 (command "TEXT" "J" "ML" p1   0.75  0.00 "372")
 (command "LAYER" "S" "CGBTHK" "")
 (setq p1 (list 440.00 1737.47) p2 (list 0.00 0.00))
 (command "TEXT" "J" "ML" p1   0.75  0.00 "2.34")
 (command "LAYER" "S" "CGBHZID" "")
 (setq p1 (list 444.50 1737.47) p2 (list 0.00 0.00))
 (command "TEXT" "J" "ML" p1   0.75  0.00 "")
 (setq p1 (list 446.75 1737.47) p2 (list 0.00 0.00))
 (command "TEXT" "J" "ML" p1   0.75  0.00 "8451")
 (command "LAYER" "S" "CGBLITHTXT" "")
 (setq p1 (list 450.50 1737.47) p2 (list 0.00 0.00))
 (command "TEXT" "J" "ML" p1   0.75  0.00 "GRY/GRN SH+INTERBED SS")
 (command "LAYER" "S" "CGBCMNT" "")
 (setq p1 (list 470.75 1737.47) p2 (list 0.00 0.00))
 (command "TEXT" "J" "ML" p1   0.75  0.00 "CRSN DWN")
 (command "LAYER" "S" "CGBMAIN" "")
 (setq p1 (list 428.00 1736.67) p2 (list 434.00 1736.67) p3 (list 434.00 1735.86) p4 (list 428.00 1735.86))
 (command "PLINE" p1 p2 p3 p4 "c")
 (command "HATCH" "ZIGZAG" 5.00 0.00 "L" "")
 (command "COLOR" "BYLAYER")
 (command "LAYER" "S" "CGBLITHCD" "")
 (setq p1 (list 434.00 1736.27) p2 (list 435.35 1736.27))
 (command "LINE" p1 p2 "")
 (setq p1 (list 435.50 1735.89) p2 (list 0.00 0.00))
 (command "TEXT" "J" "ML" p1   0.75  0.00 "244")
 (command "LAYER" "S" "CGBTHK" "")
 (setq p1 (list 440.00 1735.89) p2 (list 0.00 0.00))
 (command "TEXT" "J" "ML" p1   0.75  0.00 "0.81")
 (command "LAYER" "S" "CGBHZID" "")
 (setq p1 (list 444.50 1735.89) p2 (list 0.00 0.00))
 (command "TEXT" "J" "ML" p1   0.75  0.00 "")
 (setq p1 (list 446.75 1735.89) p2 (list 0.00 0.00))
 (command "TEXT" "J" "ML" p1   0.75  0.00 "8451")
 (command "LAYER" "S" "CGBLITHTXT" "")
 (setq p1 (list 450.50 1735.89) p2 (list 0.00 0.00))
 (command "TEXT" "J" "ML" p1   0.75  0.00 "GRN SH W/LS NODS")
 (command "LAYER" "S" "CGBCMNT" "")
 (setq p1 (list 470.75 1735.89) p2 (list 0.00 0.00))
 (command "TEXT" "J" "ML" p1   0.75  0.00 "")
 (command "LAYER" "S" "CGBMAIN" "")
 (setq p1 (list 428.00 1735.86) p2 (list 434.00 1735.86) p3 (list 434.00 1735.49) p4 (list 428.00 1735.49))
 (command "PLINE" p1 p2 p3 p4 "c")
 (command "HATCH" "ZIGZAG" 4.00 22.50 "L" "")
 (command "COLOR" "BYLAYER")
 (command "LAYER" "S" "CGBLITHCD" "")
 (setq p1 (list 434.00 1735.68) p2 (list 435.35 1734.43))
 (command "LINE" p1 p2 "")
 (setq p1 (list 435.50 1734.05) p2 (list 0.00 0.00))
 (command "TEXT" "J" "ML" p1   0.75  0.00 "114")
 (command "LAYER" "S" "CGBTHK" "")
 (setq p1 (list 440.00 1734.05) p2 (list 0.00 0.00))
 (command "TEXT" "J" "ML" p1   0.75  0.00 "0.37")
 (command "LAYER" "S" "CGBHZID" "")
 (setq p1 (list 444.50 1734.05) p2 (list 0.00 0.00))
 (command "TEXT" "J" "ML" p1   0.75  0.00 "")
 (setq p1 (list 446.75 1734.05) p2 (list 0.00 0.00))
 (command "TEXT" "J" "ML" p1   0.75  0.00 "8451")
 (command "LAYER" "S" "CGBLITHTXT" "")
 (setq p1 (list 450.50 1734.05) p2 (list 0.00 0.00))
 (command "TEXT" "J" "ML" p1   0.75  0.00 "BLK SH")
 (command "LAYER" "S" "CGBCMNT" "")
 (setq p1 (list 470.75 1734.05) p2 (list 0.00 0.00))
 (command "TEXT" "J" "ML" p1   0.75  0.00 "")
 (command "LAYER" "S" "CGBMAIN" "")
 (setq p1 (list 428.00 1735.49) p2 (list 434.00 1735.49) p3 (list 434.00 1731.99) p4 (list 428.00 1731.99))
 (command "PLINE" p1 p2 p3 p4 "c")
 (command "HATCH" "ZIGZAG" 4.00 0.00 "L" "")
 (command "COLOR" "BYLAYER")
 (command "LAYER" "S" "CGBLITHCD" "")
 (setq p1 (list 434.00 1733.74) p2 (list 435.35 1733.18))
 (command "LINE" p1 p2 "")
 (setq p1 (list 435.50 1732.80) p2 (list 0.00 0.00))
 (command "TEXT" "J" "ML" p1   0.75  0.00 "444")
 (command "LAYER" "S" "CGBTHK" "")
 (setq p1 (list 440.00 1732.80) p2 (list 0.00 0.00))
 (command "TEXT" "J" "ML" p1   0.75  0.00 "3.50")
 (command "LAYER" "S" "CGBHZID" "")
 (setq p1 (list 444.50 1732.80) p2 (list 0.00 0.00))
 (command "TEXT" "J" "ML" p1   0.75  0.00 "")
 (setq p1 (list 446.75 1732.80) p2 (list 0.00 0.00))
 (command "TEXT" "J" "ML" p1   0.75  0.00 "8451")
 (command "LAYER" "S" "CGBLITHTXT" "")
 (setq p1 (list 450.50 1732.80) p2 (list 0.00 0.00))
 (command "TEXT" "J" "ML" p1   0.75  0.00 "GRN SDY SH W/LS NODS")
 (command "LAYER" "S" "CGBCMNT" "")
 (setq p1 (list 470.75 1732.80) p2 (list 0.00 0.00))
 (command "TEXT" "J" "ML" p1   0.75  0.00 "")
 (command "LAYER" "S" "CGBMAIN" "")
 (setq p1 (list 428.00 1731.99) p2 (list 434.00 1731.99) p3 (list 434.00 1730.11) p4 (list 428.00 1730.11))
 (command "PLINE" p1 p2 p3 p4 "c")
 (command "HATCH" "ZIGZAG" 5.00 0.00 "L" "")
 (command "COLOR" "BYLAYER")
 (command "LAYER" "S" "CGBLITHCD" "")
 (setq p1 (list 434.00 1731.05) p2 (list 435.35 1731.05))
 (command "LINE" p1 p2 "")
 (setq p1 (list 435.50 1730.68) p2 (list 0.00 0.00))
 (command "TEXT" "J" "ML" p1   0.75  0.00 "144")
 (command "LAYER" "S" "CGBTHK" "")
 (setq p1 (list 440.00 1730.68) p2 (list 0.00 0.00))
 (command "TEXT" "J" "ML" p1   0.75  0.00 "1.88")
 (command "LAYER" "S" "CGBHZID" "")
 (setq p1 (list 444.50 1730.68) p2 (list 0.00 0.00))
 (command "TEXT" "J" "ML" p1   0.75  0.00 "")
 (setq p1 (list 446.75 1730.68) p2 (list 0.00 0.00))
 (command "TEXT" "J" "ML" p1   0.75  0.00 "8451")
 (command "LAYER" "S" "CGBLITHTXT" "")
 (setq p1 (list 450.50 1730.68) p2 (list 0.00 0.00))
 (command "TEXT" "J" "ML" p1   0.75  0.00 "GRN SH")
 (command "LAYER" "S" "CGBCMNT" "")
 (setq p1 (list 470.75 1730.68) p2 (list 0.00 0.00))
 (command "TEXT" "J" "ML" p1   0.75  0.00 "")
 (command "LAYER" "S" "CGBMAIN" "")
 (setq p1 (list 428.00 1730.11) p2 (list 434.00 1730.11) p3 (list 434.00 1727.69) p4 (list 428.00 1727.69))
 (command "PLINE" p1 p2 p3 p4 "c")
 (command "HATCH" "ZIGZAG" 5.00 0.00 "L" "")
 (command "COLOR" "BYLAYER")
 (command "LAYER" "S" "CGBLITHCD" "")
 (setq p1 (list 434.00 1728.90) p2 (list 435.35 1728.90))
 (command "LINE" p1 p2 "")
 (setq p1 (list 435.50 1728.53) p2 (list 0.00 0.00))
 (command "TEXT" "J" "ML" p1   0.75  0.00 "144")
 (command "LAYER" "S" "CGBTHK" "")
 (setq p1 (list 440.00 1728.53) p2 (list 0.00 0.00))
 (command "TEXT" "J" "ML" p1   0.75  0.00 "2.42")
 (command "LAYER" "S" "CGBHZID" "")
 (setq p1 (list 444.50 1728.53) p2 (list 0.00 0.00))
 (command "TEXT" "J" "ML" p1   0.75  0.00 "")
 (setq p1 (list 446.75 1728.53) p2 (list 0.00 0.00))
 (command "TEXT" "J" "ML" p1   0.75  0.00 "8451")
 (command "LAYER" "S" "CGBLITHTXT" "")
 (setq p1 (list 450.50 1728.53) p2 (list 0.00 0.00))
 (command "TEXT" "J" "ML" p1   0.75  0.00 "GRN SH")
 (command "LAYER" "S" "CGBCMNT" "")
 (setq p1 (list 470.75 1728.53) p2 (list 0.00 0.00))
 (command "TEXT" "J" "ML" p1   0.75  0.00 "")
 (command "LAYER" "S" "CGBMAIN" "")
 (setq p1 (list 428.00 1727.69) p2 (list 434.00 1727.69) p3 (list 434.00 1721.52) p4 (list 428.00 1721.52))
 (command "PLINE" p1 p2 p3 p4 "c")
 (command "HATCH" "ZIGZAG" 2.50 90.00 "L" "")
 (command "COLOR" "BYLAYER")
 (command "LAYER" "S" "CGBLITHCD" "")
 (setq p1 (list 434.00 1724.61) p2 (list 435.35 1724.61))
 (command "LINE" p1 p2 "")
 (setq p1 (list 435.50 1724.23) p2 (list 0.00 0.00))
 (command "TEXT" "J" "ML" p1   0.75  0.00 "324")
 (command "LAYER" "S" "CGBTHK" "")
 (setq p1 (list 440.00 1724.23) p2 (list 0.00 0.00))
 (command "TEXT" "J" "ML" p1   0.75  0.00 "6.17")
 (command "LAYER" "S" "CGBHZID" "")
 (setq p1 (list 444.50 1724.23) p2 (list 0.00 0.00))
 (command "TEXT" "J" "ML" p1   0.75  0.00 "")
 (setq p1 (list 446.75 1724.23) p2 (list 0.00 0.00))
 (command "TEXT" "J" "ML" p1   0.75  0.00 "8451")
 (command "LAYER" "S" "CGBLITHTXT" "")
 (setq p1 (list 450.50 1724.23) p2 (list 0.00 0.00))
 (command "TEXT" "J" "ML" p1   0.75  0.00 "DRK GRY MASS SDY SH")
 (command "LAYER" "S" "CGBCMNT" "")
 (setq p1 (list 470.75 1724.23) p2 (list 0.00 0.00))
 (command "TEXT" "J" "ML" p1   0.75  0.00 "FNS DWN")
 (command "LAYER" "S" "CGBMAIN" "")
 (setq p1 (list 428.00 1721.52) p2 (list 434.00 1721.52) p3 (list 434.00 1719.29) p4 (list 428.00 1719.29))
 (command "PLINE" p1 p2 p3 p4 "c")
 (command "HATCH" "ZIGZAG" 4.00 0.00 "L" "")
 (command "COLOR" "BYLAYER")
 (command "LAYER" "S" "CGBLITHCD" "")
 (setq p1 (list 434.00 1720.41) p2 (list 435.35 1720.41))
 (command "LINE" p1 p2 "")
 (setq p1 (list 435.50 1720.03) p2 (list 0.00 0.00))
 (command "TEXT" "J" "ML" p1   0.75  0.00 "543")
 (command "LAYER" "S" "CGBTHK" "")
 (setq p1 (list 440.00 1720.03) p2 (list 0.00 0.00))
 (command "TEXT" "J" "ML" p1   0.75  0.00 "2.23")
 (command "LAYER" "S" "CGBHZID" "")
 (setq p1 (list 444.50 1720.03) p2 (list 0.00 0.00))
 (command "TEXT" "J" "ML" p1   0.75  0.00 "")
 (setq p1 (list 446.75 1720.03) p2 (list 0.00 0.00))
 (command "TEXT" "J" "ML" p1   0.75  0.00 "8451")
 (command "LAYER" "S" "CGBLITHTXT" "")
 (setq p1 (list 450.50 1720.03) p2 (list 0.00 0.00))
 (command "TEXT" "J" "ML" p1   0.75  0.00 "GRY SS W/SH STKS")
 (command "LAYER" "S" "CGBCMNT" "")
 (setq p1 (list 470.75 1720.03) p2 (list 0.00 0.00))
 (command "TEXT" "J" "ML" p1   0.75  0.00 "")
 (command "LAYER" "S" "CGBMAIN" "")
 (setq p1 (list 428.00 1719.29) p2 (list 434.00 1719.29) p3 (list 434.00 1716.06) p4 (list 428.00 1716.06))
 (command "PLINE" p1 p2 p3 p4 "c")
 (command "HATCH" "ZIGZAG" 2.50 90.00 "L" "")
 (command "COLOR" "BYLAYER")
 (command "LAYER" "S" "CGBLITHCD" "")
 (setq p1 (list 434.00 1717.68) p2 (list 435.35 1717.68))
 (command "LINE" p1 p2 "")
 (setq p1 (list 435.50 1717.30) p2 (list 0.00 0.00))
 (command "TEXT" "J" "ML" p1   0.75  0.00 "324")
 (command "LAYER" "S" "CGBTHK" "")
 (setq p1 (list 440.00 1717.30) p2 (list 0.00 0.00))
 (command "TEXT" "J" "ML" p1   0.75  0.00 "3.23")
 (command "LAYER" "S" "CGBHZID" "")
 (setq p1 (list 444.50 1717.30) p2 (list 0.00 0.00))
 (command "TEXT" "J" "ML" p1   0.75  0.00 "")
 (setq p1 (list 446.75 1717.30) p2 (list 0.00 0.00))
 (command "TEXT" "J" "ML" p1   0.75  0.00 "8451")
 (command "LAYER" "S" "CGBLITHTXT" "")
 (setq p1 (list 450.50 1717.30) p2 (list 0.00 0.00))
 (command "TEXT" "J" "ML" p1   0.75  0.00 "DRK GRY MASS SDY SH")
 (command "LAYER" "S" "CGBCMNT" "")
 (setq p1 (list 470.75 1717.30) p2 (list 0.00 0.00))
 (command "TEXT" "J" "ML" p1   0.75  0.00 "CRSN DWN")
 (command "LAYER" "S" "CGBMAIN" "")
 (setq p1 (list 428.00 1716.06) p2 (list 434.00 1716.06) p3 (list 434.00 1715.55) p4 (list 428.00 1715.55))
 (command "PLINE" p1 p2 p3 p4 "c")
 (command "HATCH" "ZIGZAG" 4.00 0.00 "L" "")
 (command "COLOR" "BYLAYER")
 (command "LAYER" "S" "CGBLITHCD" "")
 (setq p1 (list 434.00 1715.81) p2 (list 435.35 1715.81))
 (command "LINE" p1 p2 "")
 (setq p1 (list 435.50 1715.43) p2 (list 0.00 0.00))
 (command "TEXT" "J" "ML" p1   0.75  0.00 "124")
 (command "LAYER" "S" "CGBTHK" "")
 (setq p1 (list 440.00 1715.43) p2 (list 0.00 0.00))
 (command "TEXT" "J" "ML" p1   0.75  0.00 "0.51")
 (command "LAYER" "S" "CGBHZID" "")
 (setq p1 (list 444.50 1715.43) p2 (list 0.00 0.00))
 (command "TEXT" "J" "ML" p1   0.75  0.00 "")
 (setq p1 (list 446.75 1715.43) p2 (list 0.00 0.00))
 (command "TEXT" "J" "ML" p1   0.75  0.00 "8451")
 (command "LAYER" "S" "CGBLITHTXT" "")
 (setq p1 (list 450.50 1715.43) p2 (list 0.00 0.00))
 (command "TEXT" "J" "ML" p1   0.75  0.00 "DRK GRY SH")
 (command "LAYER" "S" "CGBCMNT" "")
 (setq p1 (list 470.75 1715.43) p2 (list 0.00 0.00))
 (command "TEXT" "J" "ML" p1   0.75  0.00 "")
 (command "LAYER" "S" "CGBMAIN" "")
 (setq p1 (list 428.00 1715.55) p2 (list 434.00 1715.55) p3 (list 434.00 1714.81) p4 (list 428.00 1714.81))
 (command "PLINE" p1 p2 p3 p4 "c")
 (command "HATCH" "ZIGZAG" 4.00 0.00 "L" "")
 (command "COLOR" "BYLAYER")
 (command "LAYER" "S" "CGBLITHCD" "")
 (setq p1 (list 434.00 1715.18) p2 (list 435.35 1713.93))
 (command "LINE" p1 p2 "")
 (setq p1 (list 435.50 1713.56) p2 (list 0.00 0.00))
 (command "TEXT" "J" "ML" p1   0.75  0.00 "544")
 (command "LAYER" "S" "CGBTHK" "")
 (setq p1 (list 440.00 1713.56) p2 (list 0.00 0.00))
 (command "TEXT" "J" "ML" p1   0.75  0.00 "0.74")
 (command "LAYER" "S" "CGBHZID" "")
 (setq p1 (list 444.50 1713.56) p2 (list 0.00 0.00))
 (command "TEXT" "J" "ML" p1   0.75  0.00 "")
 (setq p1 (list 446.75 1713.56) p2 (list 0.00 0.00))
 (command "TEXT" "J" "ML" p1   0.75  0.00 "8451")
 (command "LAYER" "S" "CGBLITHTXT" "")
 (setq p1 (list 450.50 1713.56) p2 (list 0.00 0.00))
 (command "TEXT" "J" "ML" p1   0.75  0.00 "GRY MASS SS")
 (command "LAYER" "S" "CGBCMNT" "")
 (setq p1 (list 470.75 1713.56) p2 (list 0.00 0.00))
 (command "TEXT" "J" "ML" p1   0.75  0.00 "")
 (command "LAYER" "S" "CGBMAIN" "")
 (setq p1 (list 428.00 1714.81) p2 (list 434.00 1714.81) p3 (list 434.00 1714.30) p4 (list 428.00 1714.30))
 (command "PLINE" p1 p2 p3 p4 "c")
 (command "HATCH" "ZIGZAG" 4.00 0.00 "L" "")
 (command "COLOR" "BYLAYER")
 (command "LAYER" "S" "CGBLITHCD" "")
 (setq p1 (list 434.00 1714.56) p2 (list 435.35 1712.68))
 (command "LINE" p1 p2 "")
 (setq p1 (list 435.50 1712.31) p2 (list 0.00 0.00))
 (command "TEXT" "J" "ML" p1   0.75  0.00 "544")
 (command "LAYER" "S" "CGBTHK" "")
 (setq p1 (list 440.00 1712.31) p2 (list 0.00 0.00))
 (command "TEXT" "J" "ML" p1   0.75  0.00 "0.51")
 (command "LAYER" "S" "CGBHZID" "")
 (setq p1 (list 444.50 1712.31) p2 (list 0.00 0.00))
 (command "TEXT" "J" "ML" p1   0.75  0.00 "")
 (setq p1 (list 446.75 1712.31) p2 (list 0.00 0.00))
 (command "TEXT" "J" "ML" p1   0.75  0.00 "8451")
 (command "LAYER" "S" "CGBLITHTXT" "")
 (setq p1 (list 450.50 1712.31) p2 (list 0.00 0.00))
 (command "TEXT" "J" "ML" p1   0.75  0.00 "GRY MASS SS")
 (command "LAYER" "S" "CGBCMNT" "")
 (setq p1 (list 470.75 1712.31) p2 (list 0.00 0.00))
 (command "TEXT" "J" "ML" p1   0.75  0.00 "SLC")
 (command "LAYER" "S" "CGBMAIN" "")
 (setq p1 (list 428.00 1714.30) p2 (list 434.00 1714.30) p3 (list 434.00 1713.84) p4 (list 428.00 1713.84))
 (command "PLINE" p1 p2 p3 p4 "c")
 (command "HATCH" "ZIGZAG" 4.00 22.50 "L" "")
 (command "COLOR" "BYLAYER")
 (command "LAYER" "S" "CGBLITHCD" "")
 (setq p1 (list 434.00 1714.07) p2 (list 435.35 1711.43))
 (command "LINE" p1 p2 "")
 (setq p1 (list 435.50 1711.06) p2 (list 0.00 0.00))
 (command "TEXT" "J" "ML" p1   0.75  0.00 "114")
 (command "LAYER" "S" "CGBTHK" "")
 (setq p1 (list 440.00 1711.06) p2 (list 0.00 0.00))
 (command "TEXT" "J" "ML" p1   0.75  0.00 "0.46")
 (command "LAYER" "S" "CGBHZID" "")
 (setq p1 (list 444.50 1711.06) p2 (list 0.00 0.00))
 (command "TEXT" "J" "ML" p1   0.75  0.00 "")
 (setq p1 (list 446.75 1711.06) p2 (list 0.00 0.00))
 (command "TEXT" "J" "ML" p1   0.75  0.00 "8451")
 (command "LAYER" "S" "CGBLITHTXT" "")
 (setq p1 (list 450.50 1711.06) p2 (list 0.00 0.00))
 (command "TEXT" "J" "ML" p1   0.75  0.00 "BLK SH")
 (command "LAYER" "S" "CGBCMNT" "")
 (setq p1 (list 470.75 1711.06) p2 (list 0.00 0.00))
 (command "TEXT" "J" "ML" p1   0.75  0.00 "SLC")
 (command "LAYER" "S" "CGBMAIN" "")
 (setq p1 (list 428.00 1713.84) p2 (list 434.00 1713.84) p3 (list 434.00 1712.03) p4 (list 428.00 1712.03))
 (command "PLINE" p1 p2 p3 p4 "c")
 (command "HATCH" "ZIGZAG" 4.00 0.00 "L" "")
 (command "COLOR" "BYLAYER")
 (command "LAYER" "S" "CGBLITHCD" "")
 (setq p1 (list 434.00 1712.94) p2 (list 435.35 1710.18))
 (command "LINE" p1 p2 "")
 (setq p1 (list 435.50 1709.81) p2 (list 0.00 0.00))
 (command "TEXT" "J" "ML" p1   0.75  0.00 "544")
 (command "LAYER" "S" "CGBTHK" "")
 (setq p1 (list 440.00 1709.81) p2 (list 0.00 0.00))
 (command "TEXT" "J" "ML" p1   0.75  0.00 "1.81")
 (command "LAYER" "S" "CGBHZID" "")
 (setq p1 (list 444.50 1709.81) p2 (list 0.00 0.00))
 (command "TEXT" "J" "ML" p1   0.75  0.00 "")
 (setq p1 (list 446.75 1709.81) p2 (list 0.00 0.00))
 (command "TEXT" "J" "ML" p1   0.75  0.00 "8451")
 (command "LAYER" "S" "CGBLITHTXT" "")
 (setq p1 (list 450.50 1709.81) p2 (list 0.00 0.00))
 (command "TEXT" "J" "ML" p1   0.75  0.00 "GRY MASS SS")
 (command "LAYER" "S" "CGBCMNT" "")
 (setq p1 (list 470.75 1709.81) p2 (list 0.00 0.00))
 (command "TEXT" "J" "ML" p1   0.75  0.00 "SLC")
 (command "LAYER" "S" "CGBMAIN" "")
 (setq p1 (list 428.00 1712.03) p2 (list 434.00 1712.03) p3 (list 434.00 1710.90) p4 (list 428.00 1710.90))
 (command "PLINE" p1 p2 p3 p4 "c")
 (command "HATCH" "ZIGZAG" 4.00 22.50 "L" "")
 (command "COLOR" "BYLAYER")
 (command "LAYER" "S" "CGBLITHCD" "")
 (setq p1 (list 434.00 1711.47) p2 (list 435.35 1708.93))
 (command "LINE" p1 p2 "")
 (setq p1 (list 435.50 1708.56) p2 (list 0.00 0.00))
 (command "TEXT" "J" "ML" p1   0.75  0.00 "114")
 (command "LAYER" "S" "CGBTHK" "")
 (setq p1 (list 440.00 1708.56) p2 (list 0.00 0.00))
 (command "TEXT" "J" "ML" p1   0.75  0.00 "1.13")
 (command "LAYER" "S" "CGBHZID" "")
 (setq p1 (list 444.50 1708.56) p2 (list 0.00 0.00))
 (command "TEXT" "J" "ML" p1   0.75  0.00 "")
 (setq p1 (list 446.75 1708.56) p2 (list 0.00 0.00))
 (command "TEXT" "J" "ML" p1   0.75  0.00 "8451")
 (command "LAYER" "S" "CGBLITHTXT" "")
 (setq p1 (list 450.50 1708.56) p2 (list 0.00 0.00))
 (command "TEXT" "J" "ML" p1   0.75  0.00 "BLK SH")
 (command "LAYER" "S" "CGBCMNT" "")
 (setq p1 (list 470.75 1708.56) p2 (list 0.00 0.00))
 (command "TEXT" "J" "ML" p1   0.75  0.00 "BRKN, BLCKY")
 (command "LAYER" "S" "CGBMAIN" "")
 (setq p1 (list 428.00 1710.90) p2 (list 434.00 1710.90) p3 (list 434.00 1710.65) p4 (list 428.00 1710.65))
 (command "PLINE" p1 p2 p3 p4 "c")
 (command "HATCH" "ZIGZAG" 4.00 22.50 "L" "")
 (command "COLOR" "BYLAYER")
 (command "LAYER" "S" "CGBLITHCD" "")
 (setq p1 (list 434.00 1710.78) p2 (list 435.35 1707.68))
 (command "LINE" p1 p2 "")
 (setq p1 (list 435.50 1707.31) p2 (list 0.00 0.00))
 (command "TEXT" "J" "ML" p1   0.75  0.00 "114")
 (command "LAYER" "S" "CGBTHK" "")
 (setq p1 (list 440.00 1707.31) p2 (list 0.00 0.00))
 (command "TEXT" "J" "ML" p1   0.75  0.00 "0.25")
 (command "LAYER" "S" "CGBHZID" "")
 (setq p1 (list 444.50 1707.31) p2 (list 0.00 0.00))
 (command "TEXT" "J" "ML" p1   0.75  0.00 "")
 (setq p1 (list 446.75 1707.31) p2 (list 0.00 0.00))
 (command "TEXT" "J" "ML" p1   0.75  0.00 "8451")
 (command "LAYER" "S" "CGBLITHTXT" "")
 (setq p1 (list 450.50 1707.31) p2 (list 0.00 0.00))
 (command "TEXT" "J" "ML" p1   0.75  0.00 "BLK SH")
 (command "LAYER" "S" "CGBCMNT" "")
 (setq p1 (list 470.75 1707.31) p2 (list 0.00 0.00))
 (command "TEXT" "J" "ML" p1   0.75  0.00 "PYRT @ BASE")
 (command "LAYER" "S" "CGBMAIN" "")
 (setq p1 (list 428.00 1710.65) p2 (list 434.00 1710.65) p3 (list 434.00 1710.20) p4 (list 428.00 1710.20))
 (command "PLINE" p1 p2 p3 p4 "c")
 (command "HATCH" "ZIGZAG" 5.00 0.00 "L" "")
 (command "COLOR" "BYLAYER")
 (command "LAYER" "S" "CGBLITHCD" "")
 (setq p1 (list 434.00 1710.43) p2 (list 435.35 1706.43))
 (command "LINE" p1 p2 "")
 (setq p1 (list 435.50 1706.06) p2 (list 0.00 0.00))
 (command "TEXT" "J" "ML" p1   0.75  0.00 "032")
 (command "LAYER" "S" "CGBTHK" "")
 (setq p1 (list 440.00 1706.06) p2 (list 0.00 0.00))
 (command "TEXT" "J" "ML" p1   0.75  0.00 "0.45")
 (command "LAYER" "S" "CGBHZID" "")
 (setq p1 (list 444.50 1706.06) p2 (list 0.00 0.00))
 (command "TEXT" "J" "ML" p1   0.75  0.00 "")
 (setq p1 (list 446.75 1706.06) p2 (list 0.00 0.00))
 (command "TEXT" "J" "ML" p1   0.75  0.00 "8000")
 (command "LAYER" "S" "CGBLITHTXT" "")
 (setq p1 (list 450.50 1706.06) p2 (list 0.00 0.00))
 (command "TEXT" "J" "ML" p1   0.75  0.00 "BONE W/COAL LAYERS")
 (command "LAYER" "S" "CGBCMNT" "")
 (setq p1 (list 470.75 1706.06) p2 (list 0.00 0.00))
 (command "TEXT" "J" "ML" p1   0.75  0.00 "DULL W/THIN V")
 (command "LAYER" "S" "CGBMAIN" "")
 (setq p1 (list 428.00 1710.20) p2 (list 434.00 1710.20) p3 (list 434.00 1709.92) p4 (list 428.00 1709.92))
 (command "PLINE" p1 p2 p3 p4 "c")
 (command "HATCH" "ZIGZAG" 0.40 45.00 "L" "")
 (command "COLOR" "BYLAYER")
 (command "LAYER" "S" "CGBLITHCD" "")
 (setq p1 (list 434.00 1710.06) p2 (list 435.35 1705.18))
 (command "LINE" p1 p2 "")
 (setq p1 (list 435.50 1704.81) p2 (list 0.00 0.00))
 (command "TEXT" "J" "ML" p1   0.75  0.00 "023")
 (command "LAYER" "S" "CGBTHK" "")
 (setq p1 (list 440.00 1704.81) p2 (list 0.00 0.00))
 (command "TEXT" "J" "ML" p1   0.75  0.00 "0.28")
 (command "LAYER" "S" "CGBHZID" "")
 (setq p1 (list 444.50 1704.81) p2 (list 0.00 0.00))
 (command "TEXT" "J" "ML" p1   0.75  0.00 "")
 (setq p1 (list 446.75 1704.81) p2 (list 0.00 0.00))
 (command "TEXT" "J" "ML" p1   0.75  0.00 "8000")
 (command "LAYER" "S" "CGBLITHTXT" "")
 (setq p1 (list 450.50 1704.81) p2 (list 0.00 0.00))
 (command "TEXT" "J" "ML" p1   0.75  0.00 "COAL W/BONE STKS")
 (command "LAYER" "S" "CGBCMNT" "")
 (setq p1 (list 470.75 1704.81) p2 (list 0.00 0.00))
 (command "TEXT" "J" "ML" p1   0.75  0.00 "DULL W THIN V")
 (command "LAYER" "S" "CGBMAIN" "")
 (setq p1 (list 428.00 1709.92) p2 (list 434.00 1709.92) p3 (list 434.00 1709.46) p4 (list 428.00 1709.46))
 (command "PLINE" p1 p2 p3 p4 "c")
 (command "HATCH" "ZIGZAG" 0.80 0.00 "L" "")
 (command "COLOR" "BYLAYER")
 (command "LAYER" "S" "CGBLITHCD" "")
 (setq p1 (list 434.00 1709.69) p2 (list 435.35 1703.93))
 (command "LINE" p1 p2 "")
 (setq p1 (list 435.50 1703.56) p2 (list 0.00 0.00))
 (command "TEXT" "J" "ML" p1   0.75  0.00 "029")
 (command "LAYER" "S" "CGBTHK" "")
 (setq p1 (list 440.00 1703.56) p2 (list 0.00 0.00))
 (command "TEXT" "J" "ML" p1   0.75  0.00 "0.46")
 (command "LAYER" "S" "CGBHZID" "")
 (setq p1 (list 444.50 1703.56) p2 (list 0.00 0.00))
 (command "TEXT" "J" "ML" p1   0.75  0.00 "")
 (setq p1 (list 446.75 1703.56) p2 (list 0.00 0.00))
 (command "TEXT" "J" "ML" p1   0.75  0.00 "8000")
 (command "LAYER" "S" "CGBLITHTXT" "")
 (setq p1 (list 450.50 1703.56) p2 (list 0.00 0.00))
 (command "TEXT" "J" "ML" p1   0.75  0.00 "COAL W/PYRITE STKS")
 (command "LAYER" "S" "CGBCMNT" "")
 (setq p1 (list 470.75 1703.56) p2 (list 0.00 0.00))
 (command "TEXT" "J" "ML" p1   0.75  0.00 "MOSTLY BRIGHT")
 (command "LAYER" "S" "CGBMAIN" "")
 (setq p1 (list 428.00 1709.46) p2 (list 434.00 1709.46) p3 (list 434.00 1709.26) p4 (list 428.00 1709.26))
 (command "PLINE" p1 p2 p3 p4 "c")
 (command "HATCH" "ZIGZAG" 6.00 0.00 "L" "")
 (command "COLOR" "BYLAYER")
 (command "LAYER" "S" "CGBLITHCD" "")
 (setq p1 (list 434.00 1709.36) p2 (list 435.35 1702.68))
 (command "LINE" p1 p2 "")
 (setq p1 (list 435.50 1702.31) p2 (list 0.00 0.00))
 (command "TEXT" "J" "ML" p1   0.75  0.00 "113")
 (command "LAYER" "S" "CGBTHK" "")
 (setq p1 (list 440.00 1702.31) p2 (list 0.00 0.00))
 (command "TEXT" "J" "ML" p1   0.75  0.00 "0.20")
 (command "LAYER" "S" "CGBHZID" "")
 (setq p1 (list 444.50 1702.31) p2 (list 0.00 0.00))
 (command "TEXT" "J" "ML" p1   0.75  0.00 "")
 (setq p1 (list 446.75 1702.31) p2 (list 0.00 0.00))
 (command "TEXT" "J" "ML" p1   0.75  0.00 "8000")
 (command "LAYER" "S" "CGBLITHTXT" "")
 (setq p1 (list 450.50 1702.31) p2 (list 0.00 0.00))
 (command "TEXT" "J" "ML" p1   0.75  0.00 "BLK SH W/COAL STKS")
 (command "LAYER" "S" "CGBCMNT" "")
 (setq p1 (list 470.75 1702.31) p2 (list 0.00 0.00))
 (command "TEXT" "J" "ML" p1   0.75  0.00 "DULL")
 (command "LAYER" "S" "CGBMAIN" "")
 (setq p1 (list 428.00 1709.26) p2 (list 434.00 1709.26) p3 (list 434.00 1709.16) p4 (list 428.00 1709.16))
 (command "PLINE" p1 p2 p3 p4 "c")
 (command "HATCH" "ZIGZAG" 5.00 0.00 "L" "")
 (command "COLOR" "BYLAYER")
 (command "LAYER" "S" "CGBLITHCD" "")
 (setq p1 (list 434.00 1709.21) p2 (list 435.35 1701.43))
 (command "LINE" p1 p2 "")
 (setq p1 (list 435.50 1701.06) p2 (list 0.00 0.00))
 (command "TEXT" "J" "ML" p1   0.75  0.00 "033")
 (command "LAYER" "S" "CGBTHK" "")
 (setq p1 (list 440.00 1701.06) p2 (list 0.00 0.00))
 (command "TEXT" "J" "ML" p1   0.75  0.00 "0.10")
 (command "LAYER" "S" "CGBHZID" "")
 (setq p1 (list 444.50 1701.06) p2 (list 0.00 0.00))
 (command "TEXT" "J" "ML" p1   0.75  0.00 "")
 (setq p1 (list 446.75 1701.06) p2 (list 0.00 0.00))
 (command "TEXT" "J" "ML" p1   0.75  0.00 "8000")
 (command "LAYER" "S" "CGBLITHTXT" "")
 (setq p1 (list 450.50 1701.06) p2 (list 0.00 0.00))
 (command "TEXT" "J" "ML" p1   0.75  0.00 "BONE W/COAL STKS")
 (command "LAYER" "S" "CGBCMNT" "")
 (setq p1 (list 470.75 1701.06) p2 (list 0.00 0.00))
 (command "TEXT" "J" "ML" p1   0.75  0.00 "V BONEY")
 (command "LAYER" "S" "CGBMAIN" "")
 (setq p1 (list 428.00 1709.16) p2 (list 434.00 1709.16) p3 (list 434.00 1709.03) p4 (list 428.00 1709.03))
 (command "PLINE" p1 p2 p3 p4 "c")
 (command "HATCH" "ZIGZAG" 6.00 0.00 "L" "")
 (command "COLOR" "BYLAYER")
 (command "LAYER" "S" "CGBLITHCD" "")
 (setq p1 (list 434.00 1709.10) p2 (list 435.35 1700.18))
 (command "LINE" p1 p2 "")
 (setq p1 (list 435.50 1699.81) p2 (list 0.00 0.00))
 (command "TEXT" "J" "ML" p1   0.75  0.00 "113")
 (command "LAYER" "S" "CGBTHK" "")
 (setq p1 (list 440.00 1699.81) p2 (list 0.00 0.00))
 (command "TEXT" "J" "ML" p1   0.75  0.00 "0.13")
 (command "LAYER" "S" "CGBHZID" "")
 (setq p1 (list 444.50 1699.81) p2 (list 0.00 0.00))
 (command "TEXT" "J" "ML" p1   0.75  0.00 "")
 (setq p1 (list 446.75 1699.81) p2 (list 0.00 0.00))
 (command "TEXT" "J" "ML" p1   0.75  0.00 "8000")
 (command "LAYER" "S" "CGBLITHTXT" "")
 (setq p1 (list 450.50 1699.81) p2 (list 0.00 0.00))
 (command "TEXT" "J" "ML" p1   0.75  0.00 "BLK SH W/COAL STKS")
 (command "LAYER" "S" "CGBCMNT" "")
 (setq p1 (list 470.75 1699.81) p2 (list 0.00 0.00))
 (command "TEXT" "J" "ML" p1   0.75  0.00 "DULL")
 (command "LAYER" "S" "CGBMAIN" "")
 (setq p1 (list 428.00 1709.03) p2 (list 434.00 1709.03) p3 (list 434.00 1707.84) p4 (list 428.00 1707.84))
 (command "PLINE" p1 p2 p3 p4 "c")
 (command "HATCH" "ZIGZAG" 0.80 0.00 "L" "")
 (command "COLOR" "BYLAYER")
 (command "LAYER" "S" "CGBLITHCD" "")
 (setq p1 (list 434.00 1708.44) p2 (list 435.35 1698.93))
 (command "LINE" p1 p2 "")
 (setq p1 (list 435.50 1698.56) p2 (list 0.00 0.00))
 (command "TEXT" "J" "ML" p1   0.75  0.00 "029")
 (command "LAYER" "S" "CGBTHK" "")
 (setq p1 (list 440.00 1698.56) p2 (list 0.00 0.00))
 (command "TEXT" "J" "ML" p1   0.75  0.00 "1.19")
 (command "LAYER" "S" "CGBHZID" "")
 (setq p1 (list 444.50 1698.56) p2 (list 0.00 0.00))
 (command "TEXT" "J" "ML" p1   0.75  0.00 "")
 (setq p1 (list 446.75 1698.56) p2 (list 0.00 0.00))
 (command "TEXT" "J" "ML" p1   0.75  0.00 "8000")
 (command "LAYER" "S" "CGBLITHTXT" "")
 (setq p1 (list 450.50 1698.56) p2 (list 0.00 0.00))
 (command "TEXT" "J" "ML" p1   0.75  0.00 "COAL W/PYRITE STKS")
 (command "LAYER" "S" "CGBCMNT" "")
 (setq p1 (list 470.75 1698.56) p2 (list 0.00 0.00))
 (command "TEXT" "J" "ML" p1   0.75  0.00 "PYRT, GB")
 (command "LAYER" "S" "CGBMAIN" "")
 (setq p1 (list 428.00 1707.84) p2 (list 434.00 1707.84) p3 (list 434.00 1707.56) p4 (list 428.00 1707.56))
 (command "PLINE" p1 p2 p3 p4 "c")
 (command "HATCH" "ZIGZAG" 5.00 0.00 "L" "")
 (command "COLOR" "BYLAYER")
 (command "LAYER" "S" "CGBLITHCD" "")
 (setq p1 (list 434.00 1707.70) p2 (list 435.35 1697.68))
 (command "LINE" p1 p2 "")
 (setq p1 (list 435.50 1697.31) p2 (list 0.00 0.00))
 (command "TEXT" "J" "ML" p1   0.75  0.00 "033")
 (command "LAYER" "S" "CGBTHK" "")
 (setq p1 (list 440.00 1697.31) p2 (list 0.00 0.00))
 (command "TEXT" "J" "ML" p1   0.75  0.00 "0.28")
 (command "LAYER" "S" "CGBHZID" "")
 (setq p1 (list 444.50 1697.31) p2 (list 0.00 0.00))
 (command "TEXT" "J" "ML" p1   0.75  0.00 "")
 (setq p1 (list 446.75 1697.31) p2 (list 0.00 0.00))
 (command "TEXT" "J" "ML" p1   0.75  0.00 "7951")
 (command "LAYER" "S" "CGBLITHTXT" "")
 (setq p1 (list 450.50 1697.31) p2 (list 0.00 0.00))
 (command "TEXT" "J" "ML" p1   0.75  0.00 "BONE W/COAL STKS")
 (command "LAYER" "S" "CGBCMNT" "")
 (setq p1 (list 470.75 1697.31) p2 (list 0.00 0.00))
 (command "TEXT" "J" "ML" p1   0.75  0.00 "DULL W/VIT ST")
 (command "LAYER" "S" "CGBMAIN" "")
 (setq p1 (list 428.00 1707.56) p2 (list 434.00 1707.56) p3 (list 434.00 1707.38) p4 (list 428.00 1707.38))
 (command "PLINE" p1 p2 p3 p4 "c")
 (command "HATCH" "ZIGZAG" 4.00 0.00 "L" "")
 (command "COLOR" "BYLAYER")
 (command "LAYER" "S" "CGBLITHCD" "")
 (setq p1 (list 434.00 1707.47) p2 (list 435.35 1696.43))
 (command "LINE" p1 p2 "")
 (setq p1 (list 435.50 1696.06) p2 (list 0.00 0.00))
 (command "TEXT" "J" "ML" p1   0.75  0.00 "123")
 (command "LAYER" "S" "CGBTHK" "")
 (setq p1 (list 440.00 1696.06) p2 (list 0.00 0.00))
 (command "TEXT" "J" "ML" p1   0.75  0.00 "0.18")
 (command "LAYER" "S" "CGBHZID" "")
 (setq p1 (list 444.50 1696.06) p2 (list 0.00 0.00))
 (command "TEXT" "J" "ML" p1   0.75  0.00 "")
 (setq p1 (list 446.75 1696.06) p2 (list 0.00 0.00))
 (command "TEXT" "J" "ML" p1   0.75  0.00 "7951")
 (command "LAYER" "S" "CGBLITHTXT" "")
 (setq p1 (list 450.50 1696.06) p2 (list 0.00 0.00))
 (command "TEXT" "J" "ML" p1   0.75  0.00 "DRK GRY SH W/COAL STKS")
 (command "LAYER" "S" "CGBCMNT" "")
 (setq p1 (list 470.75 1696.06) p2 (list 0.00 0.00))
 (command "TEXT" "J" "ML" p1   0.75  0.00 "")
 (command "LAYER" "S" "CGBMAIN" "")
 (setq p1 (list 428.00 1707.38) p2 (list 434.00 1707.38) p3 (list 434.00 1707.24) p4 (list 428.00 1707.24))
 (command "PLINE" p1 p2 p3 p4 "c")
 (command "COLOR" "BLUE")
 (command "SOLID" p1 p2 p4 p3 "")
 (command "COLOR" "BYLAYER")
 (command "LAYER" "S" "CGBLITHCD" "")
 (setq p1 (list 434.00 1707.31) p2 (list 435.35 1695.18))
 (command "LINE" p1 p2 "")
 (setq p1 (list 435.50 1694.81) p2 (list 0.00 0.00))
 (command "TEXT" "J" "ML" p1   0.75  0.00 "021")
 (command "LAYER" "S" "CGBTHK" "")
 (setq p1 (list 440.00 1694.81) p2 (list 0.00 0.00))
 (command "TEXT" "J" "ML" p1   0.75  0.00 "0.14")
 (command "LAYER" "S" "CGBHZID" "")
 (setq p1 (list 444.50 1694.81) p2 (list 0.00 0.00))
 (command "TEXT" "J" "ML" p1   0.75  0.00 "")
 (setq p1 (list 446.75 1694.81) p2 (list 0.00 0.00))
 (command "TEXT" "J" "ML" p1   0.75  0.00 "7951")
 (command "LAYER" "S" "CGBLITHTXT" "")
 (setq p1 (list 450.50 1694.81) p2 (list 0.00 0.00))
 (command "TEXT" "J" "ML" p1   0.75  0.00 "COMMON BANDED COAL")
 (command "LAYER" "S" "CGBCMNT" "")
 (setq p1 (list 470.75 1694.81) p2 (list 0.00 0.00))
 (command "TEXT" "J" "ML" p1   0.75  0.00 "THK VIT BNDS")
 (command "LAYER" "S" "CGBMAIN" "")
 (setq p1 (list 428.00 1707.24) p2 (list 434.00 1707.24) p3 (list 434.00 1707.17) p4 (list 428.00 1707.17))
 (command "PLINE" p1 p2 p3 p4 "c")
 (command "HATCH" "ZIGZAG" 0.25 0.00 "L" "")
 (command "COLOR" "BYLAYER")
 (command "LAYER" "S" "CGBLITHCD" "")
 (setq p1 (list 434.00 1707.21) p2 (list 435.35 1693.93))
 (command "LINE" p1 p2 "")
 (setq p1 (list 435.50 1693.56) p2 (list 0.00 0.00))
 (command "TEXT" "J" "ML" p1   0.75  0.00 "127")
 (command "LAYER" "S" "CGBTHK" "")
 (setq p1 (list 440.00 1693.56) p2 (list 0.00 0.00))
 (command "TEXT" "J" "ML" p1   0.75  0.00 "0.07")
 (command "LAYER" "S" "CGBHZID" "")
 (setq p1 (list 444.50 1693.56) p2 (list 0.00 0.00))
 (command "TEXT" "J" "ML" p1   0.75  0.00 "")
 (setq p1 (list 446.75 1693.56) p2 (list 0.00 0.00))
 (command "TEXT" "J" "ML" p1   0.75  0.00 "7951")
 (command "LAYER" "S" "CGBLITHTXT" "")
 (setq p1 (list 450.50 1693.56) p2 (list 0.00 0.00))
 (command "TEXT" "J" "ML" p1   0.75  0.00 "DRK GRY FIRECLAY")
 (command "LAYER" "S" "CGBCMNT" "")
 (setq p1 (list 470.75 1693.56) p2 (list 0.00 0.00))
 (command "TEXT" "J" "ML" p1   0.75  0.00 "")
 (command "LAYER" "S" "CGBMAIN" "")
 (setq p1 (list 428.00 1707.17) p2 (list 434.00 1707.17) p3 (list 434.00 1705.78) p4 (list 428.00 1705.78))
 (command "PLINE" p1 p2 p3 p4 "c")
 (command "HATCH" "ZIGZAG" 0.25 0.00 "L" "")
 (command "COLOR" "BYLAYER")
 (command "LAYER" "S" "CGBLITHCD" "")
 (setq p1 (list 434.00 1706.48) p2 (list 435.35 1692.68))
 (command "LINE" p1 p2 "")
 (setq p1 (list 435.50 1692.31) p2 (list 0.00 0.00))
 (command "TEXT" "J" "ML" p1   0.75  0.00 "327")
 (command "LAYER" "S" "CGBTHK" "")
 (setq p1 (list 440.00 1692.31) p2 (list 0.00 0.00))
 (command "TEXT" "J" "ML" p1   0.75  0.00 "1.39")
 (command "LAYER" "S" "CGBHZID" "")
 (setq p1 (list 444.50 1692.31) p2 (list 0.00 0.00))
 (command "TEXT" "J" "ML" p1   0.75  0.00 "")
 (setq p1 (list 446.75 1692.31) p2 (list 0.00 0.00))
 (command "TEXT" "J" "ML" p1   0.75  0.00 "7951")
 (command "LAYER" "S" "CGBLITHTXT" "")
 (setq p1 (list 450.50 1692.31) p2 (list 0.00 0.00))
 (command "TEXT" "J" "ML" p1   0.75  0.00 "DRK GRY SDY FIRECLAY")
 (command "LAYER" "S" "CGBCMNT" "")
 (setq p1 (list 470.75 1692.31) p2 (list 0.00 0.00))
 (command "TEXT" "J" "ML" p1   0.75  0.00 "")
 (command "LAYER" "S" "CGBMAIN" "")
 (setq p1 (list 428.00 1705.78) p2 (list 434.00 1705.78) p3 (list 434.00 1699.81) p4 (list 428.00 1699.81))
 (command "PLINE" p1 p2 p3 p4 "c")
 (command "HATCH" "ZIGZAG" 2.50 90.00 "L" "")
 (command "COLOR" "BYLAYER")
 (command "LAYER" "S" "CGBLITHCD" "")
 (setq p1 (list 434.00 1702.80) p2 (list 435.35 1691.43))
 (command "LINE" p1 p2 "")
 (setq p1 (list 435.50 1691.06) p2 (list 0.00 0.00))
 (command "TEXT" "J" "ML" p1   0.75  0.00 "324")
 (command "LAYER" "S" "CGBTHK" "")
 (setq p1 (list 440.00 1691.06) p2 (list 0.00 0.00))
 (command "TEXT" "J" "ML" p1   0.75  0.00 "5.97")
 (command "LAYER" "S" "CGBHZID" "")
 (setq p1 (list 444.50 1691.06) p2 (list 0.00 0.00))
 (command "TEXT" "J" "ML" p1   0.75  0.00 "")
 (setq p1 (list 446.75 1691.06) p2 (list 0.00 0.00))
 (command "TEXT" "J" "ML" p1   0.75  0.00 "7951")
 (command "LAYER" "S" "CGBLITHTXT" "")
 (setq p1 (list 450.50 1691.06) p2 (list 0.00 0.00))
 (command "TEXT" "J" "ML" p1   0.75  0.00 "DRK GRY MASS SDY SH")
 (command "LAYER" "S" "CGBCMNT" "")
 (setq p1 (list 470.75 1691.06) p2 (list 0.00 0.00))
 (command "TEXT" "J" "ML" p1   0.75  0.00 "")
 (command "LAYER" "S" "CGBMAIN" "")
 (setq p1 (list 428.00 1699.81) p2 (list 434.00 1699.81) p3 (list 434.00 1692.16) p4 (list 428.00 1692.16))
 (command "PLINE" p1 p2 p3 p4 "c")
 (command "HATCH" "ZIGZAG" 5.00 0.00 "L" "")
 (command "COLOR" "BYLAYER")
 (command "LAYER" "S" "CGBLITHCD" "")
 (setq p1 (list 434.00 1695.99) p2 (list 435.35 1690.18))
 (command "LINE" p1 p2 "")
 (setq p1 (list 435.50 1689.81) p2 (list 0.00 0.00))
 (command "TEXT" "J" "ML" p1   0.75  0.00 "322")
 (command "LAYER" "S" "CGBTHK" "")
 (setq p1 (list 440.00 1689.81) p2 (list 0.00 0.00))
 (command "TEXT" "J" "ML" p1   0.75  0.00 "7.65")
 (command "LAYER" "S" "CGBHZID" "")
 (setq p1 (list 444.50 1689.81) p2 (list 0.00 0.00))
 (command "TEXT" "J" "ML" p1   0.75  0.00 "")
 (setq p1 (list 446.75 1689.81) p2 (list 0.00 0.00))
 (command "TEXT" "J" "ML" p1   0.75  0.00 "7951")
 (command "LAYER" "S" "CGBLITHTXT" "")
 (setq p1 (list 450.50 1689.81) p2 (list 0.00 0.00))
 (command "TEXT" "J" "ML" p1   0.75  0.00 "DRK GRY SH+INTERBED SS")
 (command "LAYER" "S" "CGBCMNT" "")
 (setq p1 (list 470.75 1689.81) p2 (list 0.00 0.00))
 (command "TEXT" "J" "ML" p1   0.75  0.00 "DRK")
 (command "LAYER" "S" "CGBMAIN" "")
 (setq p1 (list 428.00 1692.16) p2 (list 434.00 1692.16) p3 (list 434.00 1690.31) p4 (list 428.00 1690.31))
 (command "PLINE" p1 p2 p3 p4 "c")
 (command "HATCH" "ZIGZAG" 0.25 0.00 "L" "")
 (command "COLOR" "BYLAYER")
 (command "LAYER" "S" "CGBLITHCD" "")
 (setq p1 (list 434.00 1691.24) p2 (list 435.35 1688.93))
 (command "LINE" p1 p2 "")
 (setq p1 (list 435.50 1688.56) p2 (list 0.00 0.00))
 (command "TEXT" "J" "ML" p1   0.75  0.00 "742")
 (command "LAYER" "S" "CGBTHK" "")
 (setq p1 (list 440.00 1688.56) p2 (list 0.00 0.00))
 (command "TEXT" "J" "ML" p1   0.75  0.00 "1.85")
 (command "LAYER" "S" "CGBHZID" "")
 (setq p1 (list 444.50 1688.56) p2 (list 0.00 0.00))
 (command "TEXT" "J" "ML" p1   0.75  0.00 "")
 (setq p1 (list 446.75 1688.56) p2 (list 0.00 0.00))
 (command "TEXT" "J" "ML" p1   0.75  0.00 "7951")
 (command "LAYER" "S" "CGBLITHTXT" "")
 (setq p1 (list 450.50 1688.56) p2 (list 0.00 0.00))
 (command "TEXT" "J" "ML" p1   0.75  0.00 "GRY SH PEB CGL")
 (command "LAYER" "S" "CGBCMNT" "")
 (setq p1 (list 470.75 1688.56) p2 (list 0.00 0.00))
 (command "TEXT" "J" "ML" p1   0.75  0.00 "")
 (command "LAYER" "S" "CGBMAIN" "")
 (setq p1 (list 428.00 1690.31) p2 (list 434.00 1690.31) p3 (list 434.00 1687.21) p4 (list 428.00 1687.21))
 (command "PLINE" p1 p2 p3 p4 "c")
 (command "HATCH" "ZIGZAG" 4.00 0.00 "L" "")
 (command "COLOR" "BYLAYER")
 (command "LAYER" "S" "CGBLITHCD" "")
 (setq p1 (list 434.00 1688.76) p2 (list 435.35 1687.68))
 (command "LINE" p1 p2 "")
 (setq p1 (list 435.50 1687.31) p2 (list 0.00 0.00))
 (command "TEXT" "J" "ML" p1   0.75  0.00 "563")
 (command "LAYER" "S" "CGBTHK" "")
 (setq p1 (list 440.00 1687.31) p2 (list 0.00 0.00))
 (command "TEXT" "J" "ML" p1   0.75  0.00 "3.10")
 (command "LAYER" "S" "CGBHZID" "")
 (setq p1 (list 444.50 1687.31) p2 (list 0.00 0.00))
 (command "TEXT" "J" "ML" p1   0.75  0.00 "")
 (setq p1 (list 446.75 1687.31) p2 (list 0.00 0.00))
 (command "TEXT" "J" "ML" p1   0.75  0.00 "7951")
 (command "LAYER" "S" "CGBLITHTXT" "")
 (setq p1 (list 450.50 1687.31) p2 (list 0.00 0.00))
 (command "TEXT" "J" "ML" p1   0.75  0.00 "HARD SS W/SH STKS")
 (command "LAYER" "S" "CGBCMNT" "")
 (setq p1 (list 470.75 1687.31) p2 (list 0.00 0.00))
 (command "TEXT" "J" "ML" p1   0.75  0.00 "FNS DWN")
 (command "LAYER" "S" "CGBMAIN" "")
 (setq p1 (list 428.00 1687.21) p2 (list 434.00 1687.21) p3 (list 434.00 1684.71) p4 (list 428.00 1684.71))
 (command "PLINE" p1 p2 p3 p4 "c")
 (command "HATCH" "ZIGZAG" 5.00 0.00 "L" "")
 (command "COLOR" "BYLAYER")
 (command "LAYER" "S" "CGBLITHCD" "")
 (setq p1 (list 434.00 1685.96) p2 (list 435.35 1685.96))
 (command "LINE" p1 p2 "")
 (setq p1 (list 435.50 1685.59) p2 (list 0.00 0.00))
 (command "TEXT" "J" "ML" p1   0.75  0.00 "322")
 (command "LAYER" "S" "CGBTHK" "")
 (setq p1 (list 440.00 1685.59) p2 (list 0.00 0.00))
 (command "TEXT" "J" "ML" p1   0.75  0.00 "2.50")
 (command "LAYER" "S" "CGBHZID" "")
 (setq p1 (list 444.50 1685.59) p2 (list 0.00 0.00))
 (command "TEXT" "J" "ML" p1   0.75  0.00 "")
 (setq p1 (list 446.75 1685.59) p2 (list 0.00 0.00))
 (command "TEXT" "J" "ML" p1   0.75  0.00 "7951")
 (command "LAYER" "S" "CGBLITHTXT" "")
 (setq p1 (list 450.50 1685.59) p2 (list 0.00 0.00))
 (command "TEXT" "J" "ML" p1   0.75  0.00 "DRK GRY SH+INTERBED SS")
 (command "LAYER" "S" "CGBCMNT" "")
 (setq p1 (list 470.75 1685.59) p2 (list 0.00 0.00))
 (command "TEXT" "J" "ML" p1   0.75  0.00 "")
 (command "LAYER" "S" "CGBMAIN" "")
 (setq p1 (list 428.00 1684.71) p2 (list 434.00 1684.71) p3 (list 434.00 1682.83) p4 (list 428.00 1682.83))
 (command "PLINE" p1 p2 p3 p4 "c")
 (command "HATCH" "ZIGZAG" 5.00 0.00 "L" "")
 (command "COLOR" "BYLAYER")
 (command "LAYER" "S" "CGBLITHCD" "")
 (setq p1 (list 434.00 1683.77) p2 (list 435.35 1683.77))
 (command "LINE" p1 p2 "")
 (setq p1 (list 435.50 1683.40) p2 (list 0.00 0.00))
 (command "TEXT" "J" "ML" p1   0.75  0.00 "322")
 (command "LAYER" "S" "CGBTHK" "")
 (setq p1 (list 440.00 1683.40) p2 (list 0.00 0.00))
 (command "TEXT" "J" "ML" p1   0.75  0.00 "1.88")
 (command "LAYER" "S" "CGBHZID" "")
 (setq p1 (list 444.50 1683.40) p2 (list 0.00 0.00))
 (command "TEXT" "J" "ML" p1   0.75  0.00 "")
 (setq p1 (list 446.75 1683.40) p2 (list 0.00 0.00))
 (command "TEXT" "J" "ML" p1   0.75  0.00 "7951")
 (command "LAYER" "S" "CGBLITHTXT" "")
 (setq p1 (list 450.50 1683.40) p2 (list 0.00 0.00))
 (command "TEXT" "J" "ML" p1   0.75  0.00 "DRK GRY SH+INTERBED SS")
 (command "LAYER" "S" "CGBCMNT" "")
 (setq p1 (list 470.75 1683.40) p2 (list 0.00 0.00))
 (command "TEXT" "J" "ML" p1   0.75  0.00 "")
 (command "LAYER" "S" "CGBMAIN" "")
 (setq p1 (list 428.00 1682.83) p2 (list 434.00 1682.83) p3 (list 434.00 1680.18) p4 (list 428.00 1680.18))
 (command "PLINE" p1 p2 p3 p4 "c")
 (command "HATCH" "ZIGZAG" 4.00 0.00 "L" "")
 (command "COLOR" "BYLAYER")
 (command "LAYER" "S" "CGBLITHCD" "")
 (setq p1 (list 434.00 1681.51) p2 (list 435.35 1681.51))
 (command "LINE" p1 p2 "")
 (setq p1 (list 435.50 1681.13) p2 (list 0.00 0.00))
 (command "TEXT" "J" "ML" p1   0.75  0.00 "474")
 (command "LAYER" "S" "CGBTHK" "")
 (setq p1 (list 440.00 1681.13) p2 (list 0.00 0.00))
 (command "TEXT" "J" "ML" p1   0.75  0.00 "2.65")
 (command "LAYER" "S" "CGBHZID" "")
 (setq p1 (list 444.50 1681.13) p2 (list 0.00 0.00))
 (command "TEXT" "J" "ML" p1   0.75  0.00 "")
 (setq p1 (list 446.75 1681.13) p2 (list 0.00 0.00))
 (command "TEXT" "J" "ML" p1   0.75  0.00 "7951")
 (command "LAYER" "S" "CGBLITHTXT" "")
 (setq p1 (list 450.50 1681.13) p2 (list 0.00 0.00))
 (command "TEXT" "J" "ML" p1   0.75  0.00 "GRY/GRN SDY SH W/LS NODS")
 (command "LAYER" "S" "CGBCMNT" "")
 (setq p1 (list 470.75 1681.13) p2 (list 0.00 0.00))
 (command "TEXT" "J" "ML" p1   0.75  0.00 "")
 (command "LAYER" "S" "CGBMAIN" "")
 (setq p1 (list 428.00 1680.18) p2 (list 434.00 1680.18) p3 (list 434.00 1678.60) p4 (list 428.00 1678.60))
 (command "PLINE" p1 p2 p3 p4 "c")
 (command "HATCH" "ZIGZAG" 4.00 0.00 "L" "")
 (command "COLOR" "BYLAYER")
 (command "LAYER" "S" "CGBLITHCD" "")
 (setq p1 (list 434.00 1679.39) p2 (list 435.35 1679.39))
 (command "LINE" p1 p2 "")
 (setq p1 (list 435.50 1679.02) p2 (list 0.00 0.00))
 (command "TEXT" "J" "ML" p1   0.75  0.00 "125")
 (command "LAYER" "S" "CGBTHK" "")
 (setq p1 (list 440.00 1679.02) p2 (list 0.00 0.00))
 (command "TEXT" "J" "ML" p1   0.75  0.00 "1.58")
 (command "LAYER" "S" "CGBHZID" "")
 (setq p1 (list 444.50 1679.02) p2 (list 0.00 0.00))
 (command "TEXT" "J" "ML" p1   0.75  0.00 "")
 (setq p1 (list 446.75 1679.02) p2 (list 0.00 0.00))
 (command "TEXT" "J" "ML" p1   0.75  0.00 "7951")
 (command "LAYER" "S" "CGBLITHTXT" "")
 (setq p1 (list 450.50 1679.02) p2 (list 0.00 0.00))
 (command "TEXT" "J" "ML" p1   0.75  0.00 "DRK GRY CHRND SH")
 (command "LAYER" "S" "CGBCMNT" "")
 (setq p1 (list 470.75 1679.02) p2 (list 0.00 0.00))
 (command "TEXT" "J" "ML" p1   0.75  0.00 "")
 (command "LAYER" "S" "CGBMAIN" "")
 (setq p1 (list 428.00 1678.60) p2 (list 434.00 1678.60) p3 (list 434.00 1677.10) p4 (list 428.00 1677.10))
 (command "PLINE" p1 p2 p3 p4 "c")
 (command "HATCH" "ZIGZAG" 5.00 0.00 "L" "")
 (command "COLOR" "BYLAYER")
 (command "LAYER" "S" "CGBLITHCD" "")
 (setq p1 (list 434.00 1677.85) p2 (list 435.35 1677.85))
 (command "LINE" p1 p2 "")
 (setq p1 (list 435.50 1677.48) p2 (list 0.00 0.00))
 (command "TEXT" "J" "ML" p1   0.75  0.00 "144")
 (command "LAYER" "S" "CGBTHK" "")
 (setq p1 (list 440.00 1677.48) p2 (list 0.00 0.00))
 (command "TEXT" "J" "ML" p1   0.75  0.00 "1.50")
 (command "LAYER" "S" "CGBHZID" "")
 (setq p1 (list 444.50 1677.48) p2 (list 0.00 0.00))
 (command "TEXT" "J" "ML" p1   0.75  0.00 "")
 (setq p1 (list 446.75 1677.48) p2 (list 0.00 0.00))
 (command "TEXT" "J" "ML" p1   0.75  0.00 "7951")
 (command "LAYER" "S" "CGBLITHTXT" "")
 (setq p1 (list 450.50 1677.48) p2 (list 0.00 0.00))
 (command "TEXT" "J" "ML" p1   0.75  0.00 "GRN SH")
 (command "LAYER" "S" "CGBCMNT" "")
 (setq p1 (list 470.75 1677.48) p2 (list 0.00 0.00))
 (command "TEXT" "J" "ML" p1   0.75  0.00 "")
 (command "LAYER" "S" "CGBMAIN" "")
 (setq p1 (list 428.00 1677.10) p2 (list 434.00 1677.10) p3 (list 434.00 1675.21) p4 (list 428.00 1675.21))
 (command "PLINE" p1 p2 p3 p4 "c")
 (command "HATCH" "ZIGZAG" 5.00 0.00 "L" "")
 (command "COLOR" "BYLAYER")
 (command "LAYER" "S" "CGBLITHCD" "")
 (setq p1 (list 434.00 1676.16) p2 (list 435.35 1676.16))
 (command "LINE" p1 p2 "")
 (setq p1 (list 435.50 1675.78) p2 (list 0.00 0.00))
 (command "TEXT" "J" "ML" p1   0.75  0.00 "147")
 (command "LAYER" "S" "CGBTHK" "")
 (setq p1 (list 440.00 1675.78) p2 (list 0.00 0.00))
 (command "TEXT" "J" "ML" p1   0.75  0.00 "1.89")
 (command "LAYER" "S" "CGBHZID" "")
 (setq p1 (list 444.50 1675.78) p2 (list 0.00 0.00))
 (command "TEXT" "J" "ML" p1   0.75  0.00 "")
 (setq p1 (list 446.75 1675.78) p2 (list 0.00 0.00))
 (command "TEXT" "J" "ML" p1   0.75  0.00 "7951")
 (command "LAYER" "S" "CGBLITHTXT" "")
 (setq p1 (list 450.50 1675.78) p2 (list 0.00 0.00))
 (command "TEXT" "J" "ML" p1   0.75  0.00 "GRN CLYSTN")
 (command "LAYER" "S" "CGBCMNT" "")
 (setq p1 (list 470.75 1675.78) p2 (list 0.00 0.00))
 (command "TEXT" "J" "ML" p1   0.75  0.00 "")
 (command "LAYER" "S" "CGBMAIN" "")
 (setq p1 (list 428.00 1675.21) p2 (list 434.00 1675.21) p3 (list 434.00 1671.31) p4 (list 428.00 1671.31))
 (command "PLINE" p1 p2 p3 p4 "c")
 (command "HATCH" "ZIGZAG" 4.00 0.00 "L" "")
 (command "COLOR" "BYLAYER")
 (command "LAYER" "S" "CGBLITHCD" "")
 (setq p1 (list 434.00 1673.26) p2 (list 435.35 1673.26))
 (command "LINE" p1 p2 "")
 (setq p1 (list 435.50 1672.89) p2 (list 0.00 0.00))
 (command "TEXT" "J" "ML" p1   0.75  0.00 "474")
 (command "LAYER" "S" "CGBTHK" "")
 (setq p1 (list 440.00 1672.89) p2 (list 0.00 0.00))
 (command "TEXT" "J" "ML" p1   0.75  0.00 "3.90")
 (command "LAYER" "S" "CGBHZID" "")
 (setq p1 (list 444.50 1672.89) p2 (list 0.00 0.00))
 (command "TEXT" "J" "ML" p1   0.75  0.00 "")
 (setq p1 (list 446.75 1672.89) p2 (list 0.00 0.00))
 (command "TEXT" "J" "ML" p1   0.75  0.00 "7951")
 (command "LAYER" "S" "CGBLITHTXT" "")
 (setq p1 (list 450.50 1672.89) p2 (list 0.00 0.00))
 (command "TEXT" "J" "ML" p1   0.75  0.00 "GRY/GRN SDY SH W/LS NODS")
 (command "LAYER" "S" "CGBCMNT" "")
 (setq p1 (list 470.75 1672.89) p2 (list 0.00 0.00))
 (command "TEXT" "J" "ML" p1   0.75  0.00 "VEINS")
 (command "LAYER" "S" "CGBMAIN" "")
 (setq p1 (list 428.00 1671.31) p2 (list 434.00 1671.31) p3 (list 434.00 1670.09) p4 (list 428.00 1670.09))
 (command "PLINE" p1 p2 p3 p4 "c")
 (command "HATCH" "ZIGZAG" 5.00 0.00 "L" "")
 (command "COLOR" "BYLAYER")
 (command "LAYER" "S" "CGBLITHCD" "")
 (setq p1 (list 434.00 1670.70) p2 (list 435.35 1670.70))
 (command "LINE" p1 p2 "")
 (setq p1 (list 435.50 1670.33) p2 (list 0.00 0.00))
 (command "TEXT" "J" "ML" p1   0.75  0.00 "147")
 (command "LAYER" "S" "CGBTHK" "")
 (setq p1 (list 440.00 1670.33) p2 (list 0.00 0.00))
 (command "TEXT" "J" "ML" p1   0.75  0.00 "1.22")
 (command "LAYER" "S" "CGBHZID" "")
 (setq p1 (list 444.50 1670.33) p2 (list 0.00 0.00))
 (command "TEXT" "J" "ML" p1   0.75  0.00 "")
 (setq p1 (list 446.75 1670.33) p2 (list 0.00 0.00))
 (command "TEXT" "J" "ML" p1   0.75  0.00 "7951")
 (command "LAYER" "S" "CGBLITHTXT" "")
 (setq p1 (list 450.50 1670.33) p2 (list 0.00 0.00))
 (command "TEXT" "J" "ML" p1   0.75  0.00 "GRN CLYSTN")
 (command "LAYER" "S" "CGBCMNT" "")
 (setq p1 (list 470.75 1670.33) p2 (list 0.00 0.00))
 (command "TEXT" "J" "ML" p1   0.75  0.00 "")
 (command "LAYER" "S" "CGBMAIN" "")
 (setq p1 (list 428.00 1670.09) p2 (list 434.00 1670.09) p3 (list 434.00 1669.60) p4 (list 428.00 1669.60))
 (command "PLINE" p1 p2 p3 p4 "c")
 (command "HATCH" "ZIGZAG" 4.00 0.00 "L" "")
 (command "COLOR" "BYLAYER")
 (command "LAYER" "S" "CGBLITHCD" "")
 (setq p1 (list 434.00 1669.85) p2 (list 435.35 1668.60))
 (command "LINE" p1 p2 "")
 (setq p1 (list 435.50 1668.22) p2 (list 0.00 0.00))
 (command "TEXT" "J" "ML" p1   0.75  0.00 "424")
 (command "LAYER" "S" "CGBTHK" "")
 (setq p1 (list 440.00 1668.22) p2 (list 0.00 0.00))
 (command "TEXT" "J" "ML" p1   0.75  0.00 "0.49")
 (command "LAYER" "S" "CGBHZID" "")
 (setq p1 (list 444.50 1668.22) p2 (list 0.00 0.00))
 (command "TEXT" "J" "ML" p1   0.75  0.00 "")
 (setq p1 (list 446.75 1668.22) p2 (list 0.00 0.00))
 (command "TEXT" "J" "ML" p1   0.75  0.00 "7951")
 (command "LAYER" "S" "CGBLITHTXT" "")
 (setq p1 (list 450.50 1668.22) p2 (list 0.00 0.00))
 (command "TEXT" "J" "ML" p1   0.75  0.00 "DRK GRY SDY SH W/LS NODS")
 (command "LAYER" "S" "CGBCMNT" "")
 (setq p1 (list 470.75 1668.22) p2 (list 0.00 0.00))
 (command "TEXT" "J" "ML" p1   0.75  0.00 "")
 (command "LAYER" "S" "CGBMAIN" "")
 (setq p1 (list 428.00 1669.60) p2 (list 434.00 1669.60) p3 (list 434.00 1668.92) p4 (list 428.00 1668.92))
 (command "PLINE" p1 p2 p3 p4 "c")
 (command "HATCH" "ZIGZAG" 4.00 0.00 "L" "")
 (command "COLOR" "BYLAYER")
 (command "LAYER" "S" "CGBLITHCD" "")
 (setq p1 (list 434.00 1669.26) p2 (list 435.35 1667.35))
 (command "LINE" p1 p2 "")
 (setq p1 (list 435.50 1666.97) p2 (list 0.00 0.00))
 (command "TEXT" "J" "ML" p1   0.75  0.00 "444")
 (command "LAYER" "S" "CGBTHK" "")
 (setq p1 (list 440.00 1666.97) p2 (list 0.00 0.00))
 (command "TEXT" "J" "ML" p1   0.75  0.00 "0.68")
 (command "LAYER" "S" "CGBHZID" "")
 (setq p1 (list 444.50 1666.97) p2 (list 0.00 0.00))
 (command "TEXT" "J" "ML" p1   0.75  0.00 "")
 (setq p1 (list 446.75 1666.97) p2 (list 0.00 0.00))
 (command "TEXT" "J" "ML" p1   0.75  0.00 "7951")
 (command "LAYER" "S" "CGBLITHTXT" "")
 (setq p1 (list 450.50 1666.97) p2 (list 0.00 0.00))
 (command "TEXT" "J" "ML" p1   0.75  0.00 "GRN SDY SH W/LS NODS")
 (command "LAYER" "S" "CGBCMNT" "")
 (setq p1 (list 470.75 1666.97) p2 (list 0.00 0.00))
 (command "TEXT" "J" "ML" p1   0.75  0.00 "")
 (command "LAYER" "S" "CGBMAIN" "")
 (setq p1 (list 428.00 1668.92) p2 (list 434.00 1668.92) p3 (list 434.00 1666.72) p4 (list 428.00 1666.72))
 (command "PLINE" p1 p2 p3 p4 "c")
 (command "HATCH" "ZIGZAG" 0.50 0.00 "L" "")
 (command "COLOR" "BYLAYER")
 (command "LAYER" "S" "CGBLITHCD" "")
 (setq p1 (list 434.00 1667.82) p2 (list 435.35 1666.10))
 (command "LINE" p1 p2 "")
 (setq p1 (list 435.50 1665.72) p2 (list 0.00 0.00))
 (command "TEXT" "J" "ML" p1   0.75  0.00 "323")
 (command "LAYER" "S" "CGBTHK" "")
 (setq p1 (list 440.00 1665.72) p2 (list 0.00 0.00))
 (command "TEXT" "J" "ML" p1   0.75  0.00 "2.20")
 (command "LAYER" "S" "CGBHZID" "")
 (setq p1 (list 444.50 1665.72) p2 (list 0.00 0.00))
 (command "TEXT" "J" "ML" p1   0.75  0.00 "")
 (setq p1 (list 446.75 1665.72) p2 (list 0.00 0.00))
 (command "TEXT" "J" "ML" p1   0.75  0.00 "7951")
 (command "LAYER" "S" "CGBLITHTXT" "")
 (setq p1 (list 450.50 1665.72) p2 (list 0.00 0.00))
 (command "TEXT" "J" "ML" p1   0.75  0.00 "DRK GRY SH W/SS STKS")
 (command "LAYER" "S" "CGBCMNT" "")
 (setq p1 (list 470.75 1665.72) p2 (list 0.00 0.00))
 (command "TEXT" "J" "ML" p1   0.75  0.00 "")
 (command "LAYER" "S" "CGBMAIN" "")
 (setq p1 (list 428.00 1666.72) p2 (list 434.00 1666.72) p3 (list 434.00 1661.51) p4 (list 428.00 1661.51))
 (command "PLINE" p1 p2 p3 p4 "c")
 (command "HATCH" "ZIGZAG" 2.50 90.00 "L" "")
 (command "COLOR" "BYLAYER")
 (command "LAYER" "S" "CGBLITHCD" "")
 (setq p1 (list 434.00 1664.12) p2 (list 435.35 1664.12))
 (command "LINE" p1 p2 "")
 (setq p1 (list 435.50 1663.74) p2 (list 0.00 0.00))
 (command "TEXT" "J" "ML" p1   0.75  0.00 "324")
 (command "LAYER" "S" "CGBTHK" "")
 (setq p1 (list 440.00 1663.74) p2 (list 0.00 0.00))
 (command "TEXT" "J" "ML" p1   0.75  0.00 "5.21")
 (command "LAYER" "S" "CGBHZID" "")
 (setq p1 (list 444.50 1663.74) p2 (list 0.00 0.00))
 (command "TEXT" "J" "ML" p1   0.75  0.00 "")
 (setq p1 (list 446.75 1663.74) p2 (list 0.00 0.00))
 (command "TEXT" "J" "ML" p1   0.75  0.00 "7951")
 (command "LAYER" "S" "CGBLITHTXT" "")
 (setq p1 (list 450.50 1663.74) p2 (list 0.00 0.00))
 (command "TEXT" "J" "ML" p1   0.75  0.00 "DRK GRY MASS SDY SH")
 (command "LAYER" "S" "CGBCMNT" "")
 (setq p1 (list 470.75 1663.74) p2 (list 0.00 0.00))
 (command "TEXT" "J" "ML" p1   0.75  0.00 "")
 (command "LAYER" "S" "CGBMAIN" "")
 (setq p1 (list 428.00 1661.51) p2 (list 434.00 1661.51) p3 (list 434.00 1660.99) p4 (list 428.00 1660.99))
 (command "PLINE" p1 p2 p3 p4 "c")
 (command "HATCH" "ZIGZAG" 0.50 0.00 "L" "")
 (command "COLOR" "BYLAYER")
 (command "LAYER" "S" "CGBLITHCD" "")
 (setq p1 (list 434.00 1661.25) p2 (list 435.35 1661.25))
 (command "LINE" p1 p2 "")
 (setq p1 (list 435.50 1660.88) p2 (list 0.00 0.00))
 (command "TEXT" "J" "ML" p1   0.75  0.00 "806")
 (command "LAYER" "S" "CGBTHK" "")
 (setq p1 (list 440.00 1660.88) p2 (list 0.00 0.00))
 (command "TEXT" "J" "ML" p1   0.75  0.00 "0.52")
 (command "LAYER" "S" "CGBHZID" "")
 (setq p1 (list 444.50 1660.88) p2 (list 0.00 0.00))
 (command "TEXT" "J" "ML" p1   0.75  0.00 "")
 (setq p1 (list 446.75 1660.88) p2 (list 0.00 0.00))
 (command "TEXT" "J" "ML" p1   0.75  0.00 "7951")
 (command "LAYER" "S" "CGBLITHTXT" "")
 (setq p1 (list 450.50 1660.88) p2 (list 0.00 0.00))
 (command "TEXT" "J" "ML" p1   0.75  0.00 "FN GRND SHLY LS W/LS NODS")
 (command "LAYER" "S" "CGBCMNT" "")
 (setq p1 (list 470.75 1660.88) p2 (list 0.00 0.00))
 (command "TEXT" "J" "ML" p1   0.75  0.00 "")
 (command "LAYER" "S" "CGBMAIN" "")
 (setq p1 (list 428.00 1660.99) p2 (list 434.00 1660.99) p3 (list 434.00 1658.95) p4 (list 428.00 1658.95))
 (command "PLINE" p1 p2 p3 p4 "c")
 (command "HATCH" "ZIGZAG" 0.50 0.00 "L" "")
 (command "COLOR" "BYLAYER")
 (command "LAYER" "S" "CGBLITHCD" "")
 (setq p1 (list 434.00 1659.97) p2 (list 435.35 1659.97))
 (command "LINE" p1 p2 "")
 (setq p1 (list 435.50 1659.60) p2 (list 0.00 0.00))
 (command "TEXT" "J" "ML" p1   0.75  0.00 "323")
 (command "LAYER" "S" "CGBTHK" "")
 (setq p1 (list 440.00 1659.60) p2 (list 0.00 0.00))
 (command "TEXT" "J" "ML" p1   0.75  0.00 "2.04")
 (command "LAYER" "S" "CGBHZID" "")
 (setq p1 (list 444.50 1659.60) p2 (list 0.00 0.00))
 (command "TEXT" "J" "ML" p1   0.75  0.00 "")
 (setq p1 (list 446.75 1659.60) p2 (list 0.00 0.00))
 (command "TEXT" "J" "ML" p1   0.75  0.00 "7951")
 (command "LAYER" "S" "CGBLITHTXT" "")
 (setq p1 (list 450.50 1659.60) p2 (list 0.00 0.00))
 (command "TEXT" "J" "ML" p1   0.75  0.00 "DRK GRY SH W/SS STKS")
 (command "LAYER" "S" "CGBCMNT" "")
 (setq p1 (list 470.75 1659.60) p2 (list 0.00 0.00))
 (command "TEXT" "J" "ML" p1   0.75  0.00 "CRSN DWN")
 (command "LAYER" "S" "CGBMAIN" "")
 (setq p1 (list 428.00 1658.95) p2 (list 434.00 1658.95) p3 (list 434.00 1654.71) p4 (list 428.00 1654.71))
 (command "PLINE" p1 p2 p3 p4 "c")
 (command "HATCH" "ZIGZAG" 4.00 0.00 "L" "")
 (command "COLOR" "BYLAYER")
 (command "LAYER" "S" "CGBLITHCD" "")
 (setq p1 (list 434.00 1656.83) p2 (list 435.35 1656.83))
 (command "LINE" p1 p2 "")
 (setq p1 (list 435.50 1656.46) p2 (list 0.00 0.00))
 (command "TEXT" "J" "ML" p1   0.75  0.00 "541")
 (command "LAYER" "S" "CGBTHK" "")
 (setq p1 (list 440.00 1656.46) p2 (list 0.00 0.00))
 (command "TEXT" "J" "ML" p1   0.75  0.00 "4.24")
 (command "LAYER" "S" "CGBHZID" "")
 (setq p1 (list 444.50 1656.46) p2 (list 0.00 0.00))
 (command "TEXT" "J" "ML" p1   0.75  0.00 "")
 (setq p1 (list 446.75 1656.46) p2 (list 0.00 0.00))
 (command "TEXT" "J" "ML" p1   0.75  0.00 "7951")
 (command "LAYER" "S" "CGBLITHTXT" "")
 (setq p1 (list 450.50 1656.46) p2 (list 0.00 0.00))
 (command "TEXT" "J" "ML" p1   0.75  0.00 "GRY CROSSBED SS")
 (command "LAYER" "S" "CGBCMNT" "")
 (setq p1 (list 470.75 1656.46) p2 (list 0.00 0.00))
 (command "TEXT" "J" "ML" p1   0.75  0.00 "CRSN DWN")
 (command "LAYER" "S" "CGBMAIN" "")
 (setq p1 (list 428.00 1654.71) p2 (list 434.00 1654.71) p3 (list 434.00 1653.46) p4 (list 428.00 1653.46))
 (command "PLINE" p1 p2 p3 p4 "c")
 (command "HATCH" "ZIGZAG" 4.00 0.00 "L" "")
 (command "COLOR" "BYLAYER")
 (command "LAYER" "S" "CGBLITHCD" "")
 (setq p1 (list 434.00 1654.09) p2 (list 435.35 1654.09))
 (command "LINE" p1 p2 "")
 (setq p1 (list 435.50 1653.71) p2 (list 0.00 0.00))
 (command "TEXT" "J" "ML" p1   0.75  0.00 "541")
 (command "LAYER" "S" "CGBTHK" "")
 (setq p1 (list 440.00 1653.71) p2 (list 0.00 0.00))
 (command "TEXT" "J" "ML" p1   0.75  0.00 "1.25")
 (command "LAYER" "S" "CGBHZID" "")
 (setq p1 (list 444.50 1653.71) p2 (list 0.00 0.00))
 (command "TEXT" "J" "ML" p1   0.75  0.00 "")
 (setq p1 (list 446.75 1653.71) p2 (list 0.00 0.00))
 (command "TEXT" "J" "ML" p1   0.75  0.00 "7951")
 (command "LAYER" "S" "CGBLITHTXT" "")
 (setq p1 (list 450.50 1653.71) p2 (list 0.00 0.00))
 (command "TEXT" "J" "ML" p1   0.75  0.00 "GRY CROSSBED SS")
 (command "LAYER" "S" "CGBCMNT" "")
 (setq p1 (list 470.75 1653.71) p2 (list 0.00 0.00))
 (command "TEXT" "J" "ML" p1   0.75  0.00 "SLC")
 (command "LAYER" "S" "CGBMAIN" "")
 (setq p1 (list 428.00 1653.46) p2 (list 434.00 1653.46) p3 (list 434.00 1644.39) p4 (list 428.00 1644.39))
 (command "PLINE" p1 p2 p3 p4 "c")
 (command "HATCH" "ZIGZAG" 2.50 90.00 "L" "")
 (command "COLOR" "BYLAYER")
 (command "LAYER" "S" "CGBLITHCD" "")
 (setq p1 (list 434.00 1648.93) p2 (list 435.35 1648.93))
 (command "LINE" p1 p2 "")
 (setq p1 (list 435.50 1648.55) p2 (list 0.00 0.00))
 (command "TEXT" "J" "ML" p1   0.75  0.00 "324")
 (command "LAYER" "S" "CGBTHK" "")
 (setq p1 (list 440.00 1648.55) p2 (list 0.00 0.00))
 (command "TEXT" "J" "ML" p1   0.75  0.00 "9.07")
 (command "LAYER" "S" "CGBHZID" "")
 (setq p1 (list 444.50 1648.55) p2 (list 0.00 0.00))
 (command "TEXT" "J" "ML" p1   0.75  0.00 "")
 (setq p1 (list 446.75 1648.55) p2 (list 0.00 0.00))
 (command "TEXT" "J" "ML" p1   0.75  0.00 "7951")
 (command "LAYER" "S" "CGBLITHTXT" "")
 (setq p1 (list 450.50 1648.55) p2 (list 0.00 0.00))
 (command "TEXT" "J" "ML" p1   0.75  0.00 "DRK GRY MASS SDY SH")
 (command "LAYER" "S" "CGBCMNT" "")
 (setq p1 (list 470.75 1648.55) p2 (list 0.00 0.00))
 (command "TEXT" "J" "ML" p1   0.75  0.00 "FNS DWN")
 (command "LAYER" "S" "CGBMAIN" "")
 (setq p1 (list 428.00 1644.39) p2 (list 434.00 1644.39) p3 (list 434.00 1639.95) p4 (list 428.00 1639.95))
 (command "PLINE" p1 p2 p3 p4 "c")
 (command "HATCH" "ZIGZAG" 4.00 0.00 "L" "")
 (command "COLOR" "BYLAYER")
 (command "LAYER" "S" "CGBLITHCD" "")
 (setq p1 (list 434.00 1642.17) p2 (list 435.35 1642.17))
 (command "LINE" p1 p2 "")
 (setq p1 (list 435.50 1641.80) p2 (list 0.00 0.00))
 (command "TEXT" "J" "ML" p1   0.75  0.00 "124")
 (command "LAYER" "S" "CGBTHK" "")
 (setq p1 (list 440.00 1641.80) p2 (list 0.00 0.00))
 (command "TEXT" "J" "ML" p1   0.75  0.00 "4.44")
 (command "LAYER" "S" "CGBHZID" "")
 (setq p1 (list 444.50 1641.80) p2 (list 0.00 0.00))
 (command "TEXT" "J" "ML" p1   0.75  0.00 "")
 (setq p1 (list 446.75 1641.80) p2 (list 0.00 0.00))
 (command "TEXT" "J" "ML" p1   0.75  0.00 "7951")
 (command "LAYER" "S" "CGBLITHTXT" "")
 (setq p1 (list 450.50 1641.80) p2 (list 0.00 0.00))
 (command "TEXT" "J" "ML" p1   0.75  0.00 "DRK GRY SH")
 (command "LAYER" "S" "CGBCMNT" "")
 (setq p1 (list 470.75 1641.80) p2 (list 0.00 0.00))
 (command "TEXT" "J" "ML" p1   0.75  0.00 "")
 (command "LAYER" "S" "CGBMAIN" "")
 (setq p1 (list 428.00 1639.95) p2 (list 434.00 1639.95) p3 (list 434.00 1639.54) p4 (list 428.00 1639.54))
 (command "PLINE" p1 p2 p3 p4 "c")
 (command "HATCH" "ZIGZAG" 0.80 0.00 "L" "")
 (command "COLOR" "BYLAYER")
 (command "LAYER" "S" "CGBLITHCD" "")
 (setq p1 (list 434.00 1639.75) p2 (list 435.35 1639.75))
 (command "LINE" p1 p2 "")
 (setq p1 (list 435.50 1639.37) p2 (list 0.00 0.00))
 (command "TEXT" "J" "ML" p1   0.75  0.00 "029")
 (command "LAYER" "S" "CGBTHK" "")
 (setq p1 (list 440.00 1639.37) p2 (list 0.00 0.00))
 (command "TEXT" "J" "ML" p1   0.75  0.00 "0.41")
 (command "LAYER" "S" "CGBHZID" "")
 (setq p1 (list 444.50 1639.37) p2 (list 0.00 0.00))
 (command "TEXT" "J" "ML" p1   0.75  0.00 "")
 (setq p1 (list 446.75 1639.37) p2 (list 0.00 0.00))
 (command "TEXT" "J" "ML" p1   0.75  0.00 "7500")
 (command "LAYER" "S" "CGBLITHTXT" "")
 (setq p1 (list 450.50 1639.37) p2 (list 0.00 0.00))
 (command "TEXT" "J" "ML" p1   0.75  0.00 "COAL W/PYRITE STKS")
 (command "LAYER" "S" "CGBCMNT" "")
 (setq p1 (list 470.75 1639.37) p2 (list 0.00 0.00))
 (command "TEXT" "J" "ML" p1   0.75  0.00 "")
 (command "LAYER" "S" "CGBMAIN" "")
 (setq p1 (list 428.00 1639.54) p2 (list 434.00 1639.54) p3 (list 434.00 1639.14) p4 (list 428.00 1639.14))
 (command "PLINE" p1 p2 p3 p4 "c")
 (command "HATCH" "ZIGZAG" 0.80 0.00 "L" "")
 (command "COLOR" "BYLAYER")
 (command "LAYER" "S" "CGBLITHCD" "")
 (setq p1 (list 434.00 1639.34) p2 (list 435.35 1638.09))
 (command "LINE" p1 p2 "")
 (setq p1 (list 435.50 1637.72) p2 (list 0.00 0.00))
 (command "TEXT" "J" "ML" p1   0.75  0.00 "029")
 (command "LAYER" "S" "CGBTHK" "")
 (setq p1 (list 440.00 1637.72) p2 (list 0.00 0.00))
 (command "TEXT" "J" "ML" p1   0.75  0.00 "0.40")
 (command "LAYER" "S" "CGBHZID" "")
 (setq p1 (list 444.50 1637.72) p2 (list 0.00 0.00))
 (command "TEXT" "J" "ML" p1   0.75  0.00 "")
 (setq p1 (list 446.75 1637.72) p2 (list 0.00 0.00))
 (command "TEXT" "J" "ML" p1   0.75  0.00 "7500")
 (command "LAYER" "S" "CGBLITHTXT" "")
 (setq p1 (list 450.50 1637.72) p2 (list 0.00 0.00))
 (command "TEXT" "J" "ML" p1   0.75  0.00 "COAL W/PYRITE STKS")
 (command "LAYER" "S" "CGBCMNT" "")
 (setq p1 (list 470.75 1637.72) p2 (list 0.00 0.00))
 (command "TEXT" "J" "ML" p1   0.75  0.00 "")
 (command "LAYER" "S" "CGBMAIN" "")
 (setq p1 (list 428.00 1639.14) p2 (list 434.00 1639.14) p3 (list 434.00 1637.41) p4 (list 428.00 1637.41))
 (command "PLINE" p1 p2 p3 p4 "c")
 (command "HATCH" "ZIGZAG" 0.25 0.00 "L" "")
 (command "COLOR" "BYLAYER")
 (command "LAYER" "S" "CGBLITHCD" "")
 (setq p1 (list 434.00 1638.28) p2 (list 435.35 1636.84))
 (command "LINE" p1 p2 "")
 (setq p1 (list 435.50 1636.47) p2 (list 0.00 0.00))
 (command "TEXT" "J" "ML" p1   0.75  0.00 "327")
 (command "LAYER" "S" "CGBTHK" "")
 (setq p1 (list 440.00 1636.47) p2 (list 0.00 0.00))
 (command "TEXT" "J" "ML" p1   0.75  0.00 "1.73")
 (command "LAYER" "S" "CGBHZID" "")
 (setq p1 (list 444.50 1636.47) p2 (list 0.00 0.00))
 (command "TEXT" "J" "ML" p1   0.75  0.00 "")
 (setq p1 (list 446.75 1636.47) p2 (list 0.00 0.00))
 (command "TEXT" "J" "ML" p1   0.75  0.00 "7451")
 (command "LAYER" "S" "CGBLITHTXT" "")
 (setq p1 (list 450.50 1636.47) p2 (list 0.00 0.00))
 (command "TEXT" "J" "ML" p1   0.75  0.00 "DRK GRY SDY FIRECLAY")
 (command "LAYER" "S" "CGBCMNT" "")
 (setq p1 (list 470.75 1636.47) p2 (list 0.00 0.00))
 (command "TEXT" "J" "ML" p1   0.75  0.00 "")
 (command "LAYER" "S" "CGBMAIN" "")
 (setq p1 (list 428.00 1637.41) p2 (list 434.00 1637.41) p3 (list 434.00 1632.09) p4 (list 428.00 1632.09))
 (command "PLINE" p1 p2 p3 p4 "c")
 (command "HATCH" "ZIGZAG" 0.50 0.00 "L" "")
 (command "COLOR" "BYLAYER")
 (command "LAYER" "S" "CGBLITHCD" "")
 (setq p1 (list 434.00 1634.75) p2 (list 435.35 1634.75))
 (command "LINE" p1 p2 "")
 (setq p1 (list 435.50 1634.38) p2 (list 0.00 0.00))
 (command "TEXT" "J" "ML" p1   0.75  0.00 "323")
 (command "LAYER" "S" "CGBTHK" "")
 (setq p1 (list 440.00 1634.38) p2 (list 0.00 0.00))
 (command "TEXT" "J" "ML" p1   0.75  0.00 "5.32")
 (command "LAYER" "S" "CGBHZID" "")
 (setq p1 (list 444.50 1634.38) p2 (list 0.00 0.00))
 (command "TEXT" "J" "ML" p1   0.75  0.00 "")
 (setq p1 (list 446.75 1634.38) p2 (list 0.00 0.00))
 (command "TEXT" "J" "ML" p1   0.75  0.00 "7451")
 (command "LAYER" "S" "CGBLITHTXT" "")
 (setq p1 (list 450.50 1634.38) p2 (list 0.00 0.00))
 (command "TEXT" "J" "ML" p1   0.75  0.00 "DRK GRY SH W/SS STKS")
 (command "LAYER" "S" "CGBCMNT" "")
 (setq p1 (list 470.75 1634.38) p2 (list 0.00 0.00))
 (command "TEXT" "J" "ML" p1   0.75  0.00 "FNS DWN")
 (command "LAYER" "S" "CGBMAIN" "")
 (setq p1 (list 428.00 1632.09) p2 (list 434.00 1632.09) p3 (list 434.00 1625.17) p4 (list 428.00 1625.17))
 (command "PLINE" p1 p2 p3 p4 "c")
 (command "HATCH" "ZIGZAG" 4.00 0.00 "L" "")
 (command "COLOR" "BYLAYER")
 (command "LAYER" "S" "CGBLITHCD" "")
 (setq p1 (list 434.00 1628.63) p2 (list 435.35 1628.63))
 (command "LINE" p1 p2 "")
 (setq p1 (list 435.50 1628.26) p2 (list 0.00 0.00))
 (command "TEXT" "J" "ML" p1   0.75  0.00 "124")
 (command "LAYER" "S" "CGBTHK" "")
 (setq p1 (list 440.00 1628.26) p2 (list 0.00 0.00))
 (command "TEXT" "J" "ML" p1   0.75  0.00 "6.92")
 (command "LAYER" "S" "CGBHZID" "")
 (setq p1 (list 444.50 1628.26) p2 (list 0.00 0.00))
 (command "TEXT" "J" "ML" p1   0.75  0.00 "")
 (setq p1 (list 446.75 1628.26) p2 (list 0.00 0.00))
 (command "TEXT" "J" "ML" p1   0.75  0.00 "7451")
 (command "LAYER" "S" "CGBLITHTXT" "")
 (setq p1 (list 450.50 1628.26) p2 (list 0.00 0.00))
 (command "TEXT" "J" "ML" p1   0.75  0.00 "DRK GRY SH")
 (command "LAYER" "S" "CGBCMNT" "")
 (setq p1 (list 470.75 1628.26) p2 (list 0.00 0.00))
 (command "TEXT" "J" "ML" p1   0.75  0.00 "SID LAYRS")
 (command "LAYER" "S" "CGBMAIN" "")
 (setq p1 (list 428.00 1625.17) p2 (list 434.00 1625.17) p3 (list 434.00 1624.39) p4 (list 428.00 1624.39))
 (command "PLINE" p1 p2 p3 p4 "c")
 (command "HATCH" "ZIGZAG" 5.00 0.00 "L" "")
 (command "COLOR" "BYLAYER")
 (command "LAYER" "S" "CGBLITHCD" "")
 (setq p1 (list 434.00 1624.78) p2 (list 435.35 1624.78))
 (command "LINE" p1 p2 "")
 (setq p1 (list 435.50 1624.41) p2 (list 0.00 0.00))
 (command "TEXT" "J" "ML" p1   0.75  0.00 "224")
 (command "LAYER" "S" "CGBTHK" "")
 (setq p1 (list 440.00 1624.41) p2 (list 0.00 0.00))
 (command "TEXT" "J" "ML" p1   0.75  0.00 "0.78")
 (command "LAYER" "S" "CGBHZID" "")
 (setq p1 (list 444.50 1624.41) p2 (list 0.00 0.00))
 (command "TEXT" "J" "ML" p1   0.75  0.00 "")
 (setq p1 (list 446.75 1624.41) p2 (list 0.00 0.00))
 (command "TEXT" "J" "ML" p1   0.75  0.00 "7451")
 (command "LAYER" "S" "CGBLITHTXT" "")
 (setq p1 (list 450.50 1624.41) p2 (list 0.00 0.00))
 (command "TEXT" "J" "ML" p1   0.75  0.00 "DRK GRY SH W/LS NODS")
 (command "LAYER" "S" "CGBCMNT" "")
 (setq p1 (list 470.75 1624.41) p2 (list 0.00 0.00))
 (command "TEXT" "J" "ML" p1   0.75  0.00 "")
 (command "LAYER" "S" "CGBMAIN" "")
 (setq p1 (list 428.00 1624.39) p2 (list 434.00 1624.39) p3 (list 434.00 1623.73) p4 (list 428.00 1623.73))
 (command "PLINE" p1 p2 p3 p4 "c")
 (command "HATCH" "ZIGZAG" 5.00 0.00 "L" "")
 (command "COLOR" "BYLAYER")
 (command "LAYER" "S" "CGBLITHCD" "")
 (setq p1 (list 434.00 1624.06) p2 (list 435.35 1622.81))
 (command "LINE" p1 p2 "")
 (setq p1 (list 435.50 1622.44) p2 (list 0.00 0.00))
 (command "TEXT" "J" "ML" p1   0.75  0.00 "224")
 (command "LAYER" "S" "CGBTHK" "")
 (setq p1 (list 440.00 1622.44) p2 (list 0.00 0.00))
 (command "TEXT" "J" "ML" p1   0.75  0.00 "0.66")
 (command "LAYER" "S" "CGBHZID" "")
 (setq p1 (list 444.50 1622.44) p2 (list 0.00 0.00))
 (command "TEXT" "J" "ML" p1   0.75  0.00 "")
 (setq p1 (list 446.75 1622.44) p2 (list 0.00 0.00))
 (command "TEXT" "J" "ML" p1   0.75  0.00 "7451")
 (command "LAYER" "S" "CGBLITHTXT" "")
 (setq p1 (list 450.50 1622.44) p2 (list 0.00 0.00))
 (command "TEXT" "J" "ML" p1   0.75  0.00 "DRK GRY SH W/LS NODS")
 (command "LAYER" "S" "CGBCMNT" "")
 (setq p1 (list 470.75 1622.44) p2 (list 0.00 0.00))
 (command "TEXT" "J" "ML" p1   0.75  0.00 "")
 (command "LAYER" "S" "CGBMAIN" "")
 (setq p1 (list 428.00 1623.73) p2 (list 434.00 1623.73) p3 (list 434.00 1621.67) p4 (list 428.00 1621.67))
 (command "PLINE" p1 p2 p3 p4 "c")
 (command "HATCH" "ZIGZAG" 4.00 0.00 "L" "")
 (command "COLOR" "BYLAYER")
 (command "LAYER" "S" "CGBLITHCD" "")
 (setq p1 (list 434.00 1622.70) p2 (list 435.35 1621.56))
 (command "LINE" p1 p2 "")
 (setq p1 (list 435.50 1621.19) p2 (list 0.00 0.00))
 (command "TEXT" "J" "ML" p1   0.75  0.00 "424")
 (command "LAYER" "S" "CGBTHK" "")
 (setq p1 (list 440.00 1621.19) p2 (list 0.00 0.00))
 (command "TEXT" "J" "ML" p1   0.75  0.00 "2.06")
 (command "LAYER" "S" "CGBHZID" "")
 (setq p1 (list 444.50 1621.19) p2 (list 0.00 0.00))
 (command "TEXT" "J" "ML" p1   0.75  0.00 "")
 (setq p1 (list 446.75 1621.19) p2 (list 0.00 0.00))
 (command "TEXT" "J" "ML" p1   0.75  0.00 "7451")
 (command "LAYER" "S" "CGBLITHTXT" "")
 (setq p1 (list 450.50 1621.19) p2 (list 0.00 0.00))
 (command "TEXT" "J" "ML" p1   0.75  0.00 "DRK GRY SDY SH W/LS NODS")
 (command "LAYER" "S" "CGBCMNT" "")
 (setq p1 (list 470.75 1621.19) p2 (list 0.00 0.00))
 (command "TEXT" "J" "ML" p1   0.75  0.00 "BRKN W/SLX")
 (command "LAYER" "S" "CGBMAIN" "")
 (setq p1 (list 428.00 1621.67) p2 (list 434.00 1621.67) p3 (list 434.00 1619.45) p4 (list 428.00 1619.45))
 (command "PLINE" p1 p2 p3 p4 "c")
 (command "HATCH" "ZIGZAG" 0.50 0.00 "L" "")
 (command "COLOR" "BYLAYER")
 (command "LAYER" "S" "CGBLITHCD" "")
 (setq p1 (list 434.00 1620.56) p2 (list 435.35 1620.31))
 (command "LINE" p1 p2 "")
 (setq p1 (list 435.50 1619.94) p2 (list 0.00 0.00))
 (command "TEXT" "J" "ML" p1   0.75  0.00 "806")
 (command "LAYER" "S" "CGBTHK" "")
 (setq p1 (list 440.00 1619.94) p2 (list 0.00 0.00))
 (command "TEXT" "J" "ML" p1   0.75  0.00 "2.22")
 (command "LAYER" "S" "CGBHZID" "")
 (setq p1 (list 444.50 1619.94) p2 (list 0.00 0.00))
 (command "TEXT" "J" "ML" p1   0.75  0.00 "")
 (setq p1 (list 446.75 1619.94) p2 (list 0.00 0.00))
 (command "TEXT" "J" "ML" p1   0.75  0.00 "7451")
 (command "LAYER" "S" "CGBLITHTXT" "")
 (setq p1 (list 450.50 1619.94) p2 (list 0.00 0.00))
 (command "TEXT" "J" "ML" p1   0.75  0.00 "FN GRND SHLY LS W/LS NODS")
 (command "LAYER" "S" "CGBCMNT" "")
 (setq p1 (list 470.75 1619.94) p2 (list 0.00 0.00))
 (command "TEXT" "J" "ML" p1   0.75  0.00 "")
 (command "LAYER" "S" "CGBMAIN" "")
 (setq p1 (list 428.00 1619.45) p2 (list 434.00 1619.45) p3 (list 434.00 1613.71) p4 (list 428.00 1613.71))
 (command "PLINE" p1 p2 p3 p4 "c")
 (command "HATCH" "ZIGZAG" 4.00 0.00 "L" "")
 (command "COLOR" "BYLAYER")
 (command "LAYER" "S" "CGBLITHCD" "")
 (setq p1 (list 434.00 1616.58) p2 (list 435.35 1616.58))
 (command "LINE" p1 p2 "")
 (setq p1 (list 435.50 1616.21) p2 (list 0.00 0.00))
 (command "TEXT" "J" "ML" p1   0.75  0.00 "125")
 (command "LAYER" "S" "CGBTHK" "")
 (setq p1 (list 440.00 1616.21) p2 (list 0.00 0.00))
 (command "TEXT" "J" "ML" p1   0.75  0.00 "5.74")
 (command "LAYER" "S" "CGBHZID" "")
 (setq p1 (list 444.50 1616.21) p2 (list 0.00 0.00))
 (command "TEXT" "J" "ML" p1   0.75  0.00 "")
 (setq p1 (list 446.75 1616.21) p2 (list 0.00 0.00))
 (command "TEXT" "J" "ML" p1   0.75  0.00 "7451")
 (command "LAYER" "S" "CGBLITHTXT" "")
 (setq p1 (list 450.50 1616.21) p2 (list 0.00 0.00))
 (command "TEXT" "J" "ML" p1   0.75  0.00 "DRK GRY CHRND SH")
 (command "LAYER" "S" "CGBCMNT" "")
 (setq p1 (list 470.75 1616.21) p2 (list 0.00 0.00))
 (command "TEXT" "J" "ML" p1   0.75  0.00 "SLX")
 (command "LAYER" "S" "CGBMAIN" "")
 (setq p1 (list 428.00 1613.71) p2 (list 434.00 1613.71) p3 (list 434.00 1611.29) p4 (list 428.00 1611.29))
 (command "PLINE" p1 p2 p3 p4 "c")
 (command "HATCH" "ZIGZAG" 4.00 22.50 "L" "")
 (command "COLOR" "BYLAYER")
 (command "LAYER" "S" "CGBLITHCD" "")
 (setq p1 (list 434.00 1612.50) p2 (list 435.35 1612.50))
 (command "LINE" p1 p2 "")
 (setq p1 (list 435.50 1612.13) p2 (list 0.00 0.00))
 (command "TEXT" "J" "ML" p1   0.75  0.00 "135")
 (command "LAYER" "S" "CGBTHK" "")
 (setq p1 (list 440.00 1612.13) p2 (list 0.00 0.00))
 (command "TEXT" "J" "ML" p1   0.75  0.00 "2.42")
 (command "LAYER" "S" "CGBHZID" "")
 (setq p1 (list 444.50 1612.13) p2 (list 0.00 0.00))
 (command "TEXT" "J" "ML" p1   0.75  0.00 "")
 (setq p1 (list 446.75 1612.13) p2 (list 0.00 0.00))
 (command "TEXT" "J" "ML" p1   0.75  0.00 "7451")
 (command "LAYER" "S" "CGBLITHTXT" "")
 (setq p1 (list 450.50 1612.13) p2 (list 0.00 0.00))
 (command "TEXT" "J" "ML" p1   0.75  0.00 "LT GRY CHRND SH")
 (command "LAYER" "S" "CGBCMNT" "")
 (setq p1 (list 470.75 1612.13) p2 (list 0.00 0.00))
 (command "TEXT" "J" "ML" p1   0.75  0.00 "")
 (command "LAYER" "S" "CGBMAIN" "")
 (setq p1 (list 428.00 1611.29) p2 (list 434.00 1611.29) p3 (list 434.00 1609.27) p4 (list 428.00 1609.27))
 (command "PLINE" p1 p2 p3 p4 "c")
 (command "HATCH" "ZIGZAG" 4.00 0.00 "L" "")
 (command "COLOR" "BYLAYER")
 (command "LAYER" "S" "CGBLITHCD" "")
 (setq p1 (list 434.00 1610.28) p2 (list 435.35 1610.28))
 (command "LINE" p1 p2 "")
 (setq p1 (list 435.50 1609.91) p2 (list 0.00 0.00))
 (command "TEXT" "J" "ML" p1   0.75  0.00 "424")
 (command "LAYER" "S" "CGBTHK" "")
 (setq p1 (list 440.00 1609.91) p2 (list 0.00 0.00))
 (command "TEXT" "J" "ML" p1   0.75  0.00 "2.02")
 (command "LAYER" "S" "CGBHZID" "")
 (setq p1 (list 444.50 1609.91) p2 (list 0.00 0.00))
 (command "TEXT" "J" "ML" p1   0.75  0.00 "")
 (setq p1 (list 446.75 1609.91) p2 (list 0.00 0.00))
 (command "TEXT" "J" "ML" p1   0.75  0.00 "7451")
 (command "LAYER" "S" "CGBLITHTXT" "")
 (setq p1 (list 450.50 1609.91) p2 (list 0.00 0.00))
 (command "TEXT" "J" "ML" p1   0.75  0.00 "DRK GRY SDY SH W/LS NODS")
 (command "LAYER" "S" "CGBCMNT" "")
 (setq p1 (list 470.75 1609.91) p2 (list 0.00 0.00))
 (command "TEXT" "J" "ML" p1   0.75  0.00 "")
 (command "LAYER" "S" "CGBMAIN" "")
 (setq p1 (list 428.00 1609.27) p2 (list 434.00 1609.27) p3 (list 434.00 1601.49) p4 (list 428.00 1601.49))
 (command "PLINE" p1 p2 p3 p4 "c")
 (command "HATCH" "ZIGZAG" 4.00 0.00 "L" "")
 (command "COLOR" "BYLAYER")
 (command "LAYER" "S" "CGBLITHCD" "")
 (setq p1 (list 434.00 1605.38) p2 (list 435.35 1605.38))
 (command "LINE" p1 p2 "")
 (setq p1 (list 435.50 1605.01) p2 (list 0.00 0.00))
 (command "TEXT" "J" "ML" p1   0.75  0.00 "424")
 (command "LAYER" "S" "CGBTHK" "")
 (setq p1 (list 440.00 1605.01) p2 (list 0.00 0.00))
 (command "TEXT" "J" "ML" p1   0.75  0.00 "7.78")
 (command "LAYER" "S" "CGBHZID" "")
 (setq p1 (list 444.50 1605.01) p2 (list 0.00 0.00))
 (command "TEXT" "J" "ML" p1   0.75  0.00 "")
 (setq p1 (list 446.75 1605.01) p2 (list 0.00 0.00))
 (command "TEXT" "J" "ML" p1   0.75  0.00 "7451")
 (command "LAYER" "S" "CGBLITHTXT" "")
 (setq p1 (list 450.50 1605.01) p2 (list 0.00 0.00))
 (command "TEXT" "J" "ML" p1   0.75  0.00 "DRK GRY SDY SH W/LS NODS")
 (command "LAYER" "S" "CGBCMNT" "")
 (setq p1 (list 470.75 1605.01) p2 (list 0.00 0.00))
 (command "TEXT" "J" "ML" p1   0.75  0.00 "W/ VEINS")
 (command "LAYER" "S" "CGBMAIN" "")
 (setq p1 (list 428.00 1601.49) p2 (list 434.00 1601.49) p3 (list 434.00 1597.77) p4 (list 428.00 1597.77))
 (command "PLINE" p1 p2 p3 p4 "c")
 (command "HATCH" "ZIGZAG" 2.50 90.00 "L" "")
 (command "COLOR" "BYLAYER")
 (command "LAYER" "S" "CGBLITHCD" "")
 (setq p1 (list 434.00 1599.63) p2 (list 435.35 1599.63))
 (command "LINE" p1 p2 "")
 (setq p1 (list 435.50 1599.26) p2 (list 0.00 0.00))
 (command "TEXT" "J" "ML" p1   0.75  0.00 "324")
 (command "LAYER" "S" "CGBTHK" "")
 (setq p1 (list 440.00 1599.26) p2 (list 0.00 0.00))
 (command "TEXT" "J" "ML" p1   0.75  0.00 "3.72")
 (command "LAYER" "S" "CGBHZID" "")
 (setq p1 (list 444.50 1599.26) p2 (list 0.00 0.00))
 (command "TEXT" "J" "ML" p1   0.75  0.00 "")
 (setq p1 (list 446.75 1599.26) p2 (list 0.00 0.00))
 (command "TEXT" "J" "ML" p1   0.75  0.00 "7451")
 (command "LAYER" "S" "CGBLITHTXT" "")
 (setq p1 (list 450.50 1599.26) p2 (list 0.00 0.00))
 (command "TEXT" "J" "ML" p1   0.75  0.00 "DRK GRY MASS SDY SH")
 (command "LAYER" "S" "CGBCMNT" "")
 (setq p1 (list 470.75 1599.26) p2 (list 0.00 0.00))
 (command "TEXT" "J" "ML" p1   0.75  0.00 "")
 (command "LAYER" "S" "CGBMAIN" "")
 (setq p1 (list 428.00 1597.77) p2 (list 434.00 1597.77) p3 (list 434.00 1594.15) p4 (list 428.00 1594.15))
 (command "PLINE" p1 p2 p3 p4 "c")
 (command "HATCH" "ZIGZAG" 5.00 0.00 "L" "")
 (command "COLOR" "BYLAYER")
 (command "LAYER" "S" "CGBLITHCD" "")
 (setq p1 (list 434.00 1595.96) p2 (list 435.35 1595.96))
 (command "LINE" p1 p2 "")
 (setq p1 (list 435.50 1595.59) p2 (list 0.00 0.00))
 (command "TEXT" "J" "ML" p1   0.75  0.00 "174")
 (command "LAYER" "S" "CGBTHK" "")
 (setq p1 (list 440.00 1595.59) p2 (list 0.00 0.00))
 (command "TEXT" "J" "ML" p1   0.75  0.00 "3.62")
 (command "LAYER" "S" "CGBHZID" "")
 (setq p1 (list 444.50 1595.59) p2 (list 0.00 0.00))
 (command "TEXT" "J" "ML" p1   0.75  0.00 "")
 (setq p1 (list 446.75 1595.59) p2 (list 0.00 0.00))
 (command "TEXT" "J" "ML" p1   0.75  0.00 "7451")
 (command "LAYER" "S" "CGBLITHTXT" "")
 (setq p1 (list 450.50 1595.59) p2 (list 0.00 0.00))
 (command "TEXT" "J" "ML" p1   0.75  0.00 "GRY/GRN SH")
 (command "LAYER" "S" "CGBCMNT" "")
 (setq p1 (list 470.75 1595.59) p2 (list 0.00 0.00))
 (command "TEXT" "J" "ML" p1   0.75  0.00 "")
 (command "LAYER" "S" "CGBMAIN" "")
 (setq p1 (list 428.00 1594.15) p2 (list 434.00 1594.15) p3 (list 434.00 1592.92) p4 (list 428.00 1592.92))
 (command "PLINE" p1 p2 p3 p4 "c")
 (command "HATCH" "ZIGZAG" 5.00 0.00 "L" "")
 (command "COLOR" "BYLAYER")
 (command "LAYER" "S" "CGBLITHCD" "")
 (setq p1 (list 434.00 1593.54) p2 (list 435.35 1593.54))
 (command "LINE" p1 p2 "")
 (setq p1 (list 435.50 1593.16) p2 (list 0.00 0.00))
 (command "TEXT" "J" "ML" p1   0.75  0.00 "174")
 (command "LAYER" "S" "CGBTHK" "")
 (setq p1 (list 440.00 1593.16) p2 (list 0.00 0.00))
 (command "TEXT" "J" "ML" p1   0.75  0.00 "1.23")
 (command "LAYER" "S" "CGBHZID" "")
 (setq p1 (list 444.50 1593.16) p2 (list 0.00 0.00))
 (command "TEXT" "J" "ML" p1   0.75  0.00 "")
 (setq p1 (list 446.75 1593.16) p2 (list 0.00 0.00))
 (command "TEXT" "J" "ML" p1   0.75  0.00 "7451")
 (command "LAYER" "S" "CGBLITHTXT" "")
 (setq p1 (list 450.50 1593.16) p2 (list 0.00 0.00))
 (command "TEXT" "J" "ML" p1   0.75  0.00 "GRY/GRN SH")
 (command "LAYER" "S" "CGBCMNT" "")
 (setq p1 (list 470.75 1593.16) p2 (list 0.00 0.00))
 (command "TEXT" "J" "ML" p1   0.75  0.00 "")
 (command "LAYER" "S" "CGBMAIN" "")
 (setq p1 (list 428.00 1592.92) p2 (list 434.00 1592.92) p3 (list 434.00 1590.88) p4 (list 428.00 1590.88))
 (command "PLINE" p1 p2 p3 p4 "c")
 (command "HATCH" "ZIGZAG" 4.00 0.00 "L" "")
 (command "COLOR" "BYLAYER")
 (command "LAYER" "S" "CGBLITHCD" "")
 (setq p1 (list 434.00 1591.90) p2 (list 435.35 1591.90))
 (command "LINE" p1 p2 "")
 (setq p1 (list 435.50 1591.53) p2 (list 0.00 0.00))
 (command "TEXT" "J" "ML" p1   0.75  0.00 "424")
 (command "LAYER" "S" "CGBTHK" "")
 (setq p1 (list 440.00 1591.53) p2 (list 0.00 0.00))
 (command "TEXT" "J" "ML" p1   0.75  0.00 "2.04")
 (command "LAYER" "S" "CGBHZID" "")
 (setq p1 (list 444.50 1591.53) p2 (list 0.00 0.00))
 (command "TEXT" "J" "ML" p1   0.75  0.00 "")
 (setq p1 (list 446.75 1591.53) p2 (list 0.00 0.00))
 (command "TEXT" "J" "ML" p1   0.75  0.00 "7451")
 (command "LAYER" "S" "CGBLITHTXT" "")
 (setq p1 (list 450.50 1591.53) p2 (list 0.00 0.00))
 (command "TEXT" "J" "ML" p1   0.75  0.00 "DRK GRY SDY SH W/LS NODS")
 (command "LAYER" "S" "CGBCMNT" "")
 (setq p1 (list 470.75 1591.53) p2 (list 0.00 0.00))
 (command "TEXT" "J" "ML" p1   0.75  0.00 "")
 (command "LAYER" "S" "CGBMAIN" "")
 (setq p1 (list 428.00 1590.88) p2 (list 434.00 1590.88) p3 (list 434.00 1590.41) p4 (list 428.00 1590.41))
 (command "PLINE" p1 p2 p3 p4 "c")
 (command "HATCH" "ZIGZAG" 10.00 45.00 "L" "")
 (command "COLOR" "BYLAYER")
 (command "LAYER" "S" "CGBLITHCD" "")
 (setq p1 (list 434.00 1590.65) p2 (list 435.35 1590.65))
 (command "LINE" p1 p2 "")
 (setq p1 (list 435.50 1590.27) p2 (list 0.00 0.00))
 (command "TEXT" "J" "ML" p1   0.75  0.00 "096")
 (command "LAYER" "S" "CGBTHK" "")
 (setq p1 (list 440.00 1590.27) p2 (list 0.00 0.00))
 (command "TEXT" "J" "ML" p1   0.75  0.00 "0.47")
 (command "LAYER" "S" "CGBHZID" "")
 (setq p1 (list 444.50 1590.27) p2 (list 0.00 0.00))
 (command "TEXT" "J" "ML" p1   0.75  0.00 "")
 (setq p1 (list 446.75 1590.27) p2 (list 0.00 0.00))
 (command "TEXT" "J" "ML" p1   0.75  0.00 "7451")
 (command "LAYER" "S" "CGBLITHTXT" "")
 (setq p1 (list 450.50 1590.27) p2 (list 0.00 0.00))
 (command "TEXT" "J" "ML" p1   0.75  0.00 "NODULAR FLINT CLAY")
 (command "LAYER" "S" "CGBCMNT" "")
 (setq p1 (list 470.75 1590.27) p2 (list 0.00 0.00))
 (command "TEXT" "J" "ML" p1   0.75  0.00 "")
 (command "LAYER" "S" "CGBMAIN" "")
 (setq p1 (list 428.00 1590.41) p2 (list 434.00 1590.41) p3 (list 434.00 1581.95) p4 (list 428.00 1581.95))
 (command "PLINE" p1 p2 p3 p4 "c")
 (command "HATCH" "ZIGZAG" 10.00 0.00 "L" "")
 (command "COLOR" "BYLAYER")
 (command "LAYER" "S" "CGBLITHCD" "")
 (setq p1 (list 434.00 1586.18) p2 (list 435.35 1586.18))
 (command "LINE" p1 p2 "")
 (setq p1 (list 435.50 1585.81) p2 (list 0.00 0.00))
 (command "TEXT" "J" "ML" p1   0.75  0.00 "372")
 (command "LAYER" "S" "CGBTHK" "")
 (setq p1 (list 440.00 1585.81) p2 (list 0.00 0.00))
 (command "TEXT" "J" "ML" p1   0.75  0.00 "8.46")
 (command "LAYER" "S" "CGBHZID" "")
 (setq p1 (list 444.50 1585.81) p2 (list 0.00 0.00))
 (command "TEXT" "J" "ML" p1   0.75  0.00 "")
 (setq p1 (list 446.75 1585.81) p2 (list 0.00 0.00))
 (command "TEXT" "J" "ML" p1   0.75  0.00 "7451")
 (command "LAYER" "S" "CGBLITHTXT" "")
 (setq p1 (list 450.50 1585.81) p2 (list 0.00 0.00))
 (command "TEXT" "J" "ML" p1   0.75  0.00 "GRY/GRN SH+INTERBED SS")
 (command "LAYER" "S" "CGBCMNT" "")
 (setq p1 (list 470.75 1585.81) p2 (list 0.00 0.00))
 (command "TEXT" "J" "ML" p1   0.75  0.00 "")
 (command "LAYER" "S" "CGBMAIN" "")
 (setq p1 (list 428.00 1581.95) p2 (list 434.00 1581.95) p3 (list 434.00 1579.00) p4 (list 428.00 1579.00))
 (command "PLINE" p1 p2 p3 p4 "c")
 (command "HATCH" "ZIGZAG" 4.00 0.00 "L" "")
 (command "COLOR" "BYLAYER")
 (command "LAYER" "S" "CGBLITHCD" "")
 (setq p1 (list 434.00 1580.48) p2 (list 435.35 1580.48))
 (command "LINE" p1 p2 "")
 (setq p1 (list 435.50 1580.10) p2 (list 0.00 0.00))
 (command "TEXT" "J" "ML" p1   0.75  0.00 "124")
 (command "LAYER" "S" "CGBTHK" "")
 (setq p1 (list 440.00 1580.10) p2 (list 0.00 0.00))
 (command "TEXT" "J" "ML" p1   0.75  0.00 "2.95")
 (command "LAYER" "S" "CGBHZID" "")
 (setq p1 (list 444.50 1580.10) p2 (list 0.00 0.00))
 (command "TEXT" "J" "ML" p1   0.75  0.00 "")
 (setq p1 (list 446.75 1580.10) p2 (list 0.00 0.00))
 (command "TEXT" "J" "ML" p1   0.75  0.00 "7451")
 (command "LAYER" "S" "CGBLITHTXT" "")
 (setq p1 (list 450.50 1580.10) p2 (list 0.00 0.00))
 (command "TEXT" "J" "ML" p1   0.75  0.00 "DRK GRY SH")
 (command "LAYER" "S" "CGBCMNT" "")
 (setq p1 (list 470.75 1580.10) p2 (list 0.00 0.00))
 (command "TEXT" "J" "ML" p1   0.75  0.00 "")
 (command "LAYER" "S" "CGBMAIN" "")
 (setq p1 (list 428.00 1579.00) p2 (list 434.00 1579.00) p3 (list 434.00 1573.76) p4 (list 428.00 1573.76))
 (command "PLINE" p1 p2 p3 p4 "c")
 (command "HATCH" "ZIGZAG" 4.00 0.00 "L" "")
 (command "COLOR" "BYLAYER")
 (command "LAYER" "S" "CGBLITHCD" "")
 (setq p1 (list 434.00 1576.38) p2 (list 435.35 1576.38))
 (command "LINE" p1 p2 "")
 (setq p1 (list 435.50 1576.01) p2 (list 0.00 0.00))
 (command "TEXT" "J" "ML" p1   0.75  0.00 "124")
 (command "LAYER" "S" "CGBTHK" "")
 (setq p1 (list 440.00 1576.01) p2 (list 0.00 0.00))
 (command "TEXT" "J" "ML" p1   0.75  0.00 "5.24")
 (command "LAYER" "S" "CGBHZID" "")
 (setq p1 (list 444.50 1576.01) p2 (list 0.00 0.00))
 (command "TEXT" "J" "ML" p1   0.75  0.00 "")
 (setq p1 (list 446.75 1576.01) p2 (list 0.00 0.00))
 (command "TEXT" "J" "ML" p1   0.75  0.00 "7451")
 (command "LAYER" "S" "CGBLITHTXT" "")
 (setq p1 (list 450.50 1576.01) p2 (list 0.00 0.00))
 (command "TEXT" "J" "ML" p1   0.75  0.00 "DRK GRY SH")
 (command "LAYER" "S" "CGBCMNT" "")
 (setq p1 (list 470.75 1576.01) p2 (list 0.00 0.00))
 (command "TEXT" "J" "ML" p1   0.75  0.00 "SID LAYRS")
 (command "LAYER" "S" "CGBMAIN" "")
 (command "LAYER" "S" "CGBLITHCD" "")
 (setq p1 (list 434.00 1573.76) p2 (list 435.35 1573.76))
 (command "LINE" p1 p2 "")
 (setq p1 (list 435.50 1573.39) p2 (list 0.00 0.00))
 (command "TEXT" "J" "ML" p1   0.75  0.00 "021")
 (command "LAYER" "S" "CGBTHK" "")
 (setq p1 (list 440.00 1573.39) p2 (list 0.00 0.00))
 (command "TEXT" "J" "ML" p1   0.75  0.00 "0.00")
 (command "LAYER" "S" "CGBHZID" "")
 (setq p1 (list 444.50 1573.39) p2 (list 0.00 0.00))
 (command "TEXT" "J" "ML" p1   0.75  0.00 "")
 (setq p1 (list 446.75 1573.39) p2 (list 0.00 0.00))
 (command "TEXT" "J" "ML" p1   0.75  0.00 "7000")
 (command "LAYER" "S" "CGBLITHTXT" "")
 (setq p1 (list 450.50 1573.39) p2 (list 0.00 0.00))
 (command "TEXT" "J" "ML" p1   0.75  0.00 "COMMON BANDED COAL")
 (command "LAYER" "S" "CGBCMNT" "")
 (setq p1 (list 470.75 1573.39) p2 (list 0.00 0.00))
 (command "TEXT" "J" "ML" p1   0.75  0.00 "MAH HRZN ??")
 (command "LAYER" "S" "CGBMAIN" "")
 (setq p1 (list 428.00 1573.76) p2 (list 434.00 1573.76) p3 (list 434.00 1571.58) p4 (list 428.00 1571.58))
 (command "PLINE" p1 p2 p3 p4 "c")
 (command "HATCH" "ZIGZAG" 4.00 0.00 "L" "")
 (command "COLOR" "BYLAYER")
 (command "LAYER" "S" "CGBLITHCD" "")
 (setq p1 (list 434.00 1572.67) p2 (list 435.35 1571.42))
 (command "LINE" p1 p2 "")
 (setq p1 (list 435.50 1571.05) p2 (list 0.00 0.00))
 (command "TEXT" "J" "ML" p1   0.75  0.00 "125")
 (command "LAYER" "S" "CGBTHK" "")
 (setq p1 (list 440.00 1571.05) p2 (list 0.00 0.00))
 (command "TEXT" "J" "ML" p1   0.75  0.00 "2.18")
 (command "LAYER" "S" "CGBHZID" "")
 (setq p1 (list 444.50 1571.05) p2 (list 0.00 0.00))
 (command "TEXT" "J" "ML" p1   0.75  0.00 "")
 (setq p1 (list 446.75 1571.05) p2 (list 0.00 0.00))
 (command "TEXT" "J" "ML" p1   0.75  0.00 "6951")
 (command "LAYER" "S" "CGBLITHTXT" "")
 (setq p1 (list 450.50 1571.05) p2 (list 0.00 0.00))
 (command "TEXT" "J" "ML" p1   0.75  0.00 "DRK GRY CHRND SH")
 (command "LAYER" "S" "CGBCMNT" "")
 (setq p1 (list 470.75 1571.05) p2 (list 0.00 0.00))
 (command "TEXT" "J" "ML" p1   0.75  0.00 "")
 (command "LAYER" "S" "CGBMAIN" "")
 (setq p1 (list 428.00 1571.58) p2 (list 434.00 1571.58) p3 (list 434.00 1563.95) p4 (list 428.00 1563.95))
 (command "PLINE" p1 p2 p3 p4 "c")
 (command "HATCH" "ZIGZAG" 2.50 90.00 "L" "")
 (command "COLOR" "BYLAYER")
 (command "LAYER" "S" "CGBLITHCD" "")
 (setq p1 (list 434.00 1567.77) p2 (list 435.35 1567.77))
 (command "LINE" p1 p2 "")
 (setq p1 (list 435.50 1567.39) p2 (list 0.00 0.00))
 (command "TEXT" "J" "ML" p1   0.75  0.00 "324")
 (command "LAYER" "S" "CGBTHK" "")
 (setq p1 (list 440.00 1567.39) p2 (list 0.00 0.00))
 (command "TEXT" "J" "ML" p1   0.75  0.00 "7.63")
 (command "LAYER" "S" "CGBHZID" "")
 (setq p1 (list 444.50 1567.39) p2 (list 0.00 0.00))
 (command "TEXT" "J" "ML" p1   0.75  0.00 "")
 (setq p1 (list 446.75 1567.39) p2 (list 0.00 0.00))
 (command "TEXT" "J" "ML" p1   0.75  0.00 "6951")
 (command "LAYER" "S" "CGBLITHTXT" "")
 (setq p1 (list 450.50 1567.39) p2 (list 0.00 0.00))
 (command "TEXT" "J" "ML" p1   0.75  0.00 "DRK GRY MASS SDY SH")
 (command "LAYER" "S" "CGBCMNT" "")
 (setq p1 (list 470.75 1567.39) p2 (list 0.00 0.00))
 (command "TEXT" "J" "ML" p1   0.75  0.00 "")
 (command "LAYER" "S" "CGBMAIN" "")
 (setq p1 (list 428.00 1563.95) p2 (list 434.00 1563.95) p3 (list 434.00 1548.78) p4 (list 428.00 1548.78))
 (command "PLINE" p1 p2 p3 p4 "c")
 (command "HATCH" "ZIGZAG" 5.00 0.00 "L" "")
 (command "COLOR" "BYLAYER")
 (command "LAYER" "S" "CGBLITHCD" "")
 (setq p1 (list 434.00 1556.37) p2 (list 435.35 1556.37))
 (command "LINE" p1 p2 "")
 (setq p1 (list 435.50 1555.99) p2 (list 0.00 0.00))
 (command "TEXT" "J" "ML" p1   0.75  0.00 "322")
 (command "LAYER" "S" "CGBTHK" "")
 (setq p1 (list 440.00 1555.99) p2 (list 0.00 0.00))
 (command "TEXT" "J" "ML" p1   0.75  0.00 "15.17")
 (command "LAYER" "S" "CGBHZID" "")
 (setq p1 (list 444.50 1555.99) p2 (list 0.00 0.00))
 (command "TEXT" "J" "ML" p1   0.75  0.00 "")
 (setq p1 (list 446.75 1555.99) p2 (list 0.00 0.00))
 (command "TEXT" "J" "ML" p1   0.75  0.00 "6951")
 (command "LAYER" "S" "CGBLITHTXT" "")
 (setq p1 (list 450.50 1555.99) p2 (list 0.00 0.00))
 (command "TEXT" "J" "ML" p1   0.75  0.00 "DRK GRY SH+INTERBED SS")
 (command "LAYER" "S" "CGBCMNT" "")
 (setq p1 (list 470.75 1555.99) p2 (list 0.00 0.00))
 (command "TEXT" "J" "ML" p1   0.75  0.00 "")
 (command "LAYER" "S" "CGBMAIN" "")
 (setq p1 (list 428.00 1548.78) p2 (list 434.00 1548.78) p3 (list 434.00 1545.06) p4 (list 428.00 1545.06))
 (command "PLINE" p1 p2 p3 p4 "c")
 (command "HATCH" "ZIGZAG" 2.50 90.00 "L" "")
 (command "COLOR" "BYLAYER")
 (command "LAYER" "S" "CGBLITHCD" "")
 (setq p1 (list 434.00 1546.92) p2 (list 435.35 1546.92))
 (command "LINE" p1 p2 "")
 (setq p1 (list 435.50 1546.55) p2 (list 0.00 0.00))
 (command "TEXT" "J" "ML" p1   0.75  0.00 "324")
 (command "LAYER" "S" "CGBTHK" "")
 (setq p1 (list 440.00 1546.55) p2 (list 0.00 0.00))
 (command "TEXT" "J" "ML" p1   0.75  0.00 "3.72")
 (command "LAYER" "S" "CGBHZID" "")
 (setq p1 (list 444.50 1546.55) p2 (list 0.00 0.00))
 (command "TEXT" "J" "ML" p1   0.75  0.00 "")
 (setq p1 (list 446.75 1546.55) p2 (list 0.00 0.00))
 (command "TEXT" "J" "ML" p1   0.75  0.00 "6951")
 (command "LAYER" "S" "CGBLITHTXT" "")
 (setq p1 (list 450.50 1546.55) p2 (list 0.00 0.00))
 (command "TEXT" "J" "ML" p1   0.75  0.00 "DRK GRY MASS SDY SH")
 (command "LAYER" "S" "CGBCMNT" "")
 (setq p1 (list 470.75 1546.55) p2 (list 0.00 0.00))
 (command "TEXT" "J" "ML" p1   0.75  0.00 "SLC, FEW BURS")
 (command "LAYER" "S" "CGBMAIN" "")
 (setq p1 (list 428.00 1545.06) p2 (list 434.00 1545.06) p3 (list 434.00 1540.89) p4 (list 428.00 1540.89))
 (command "PLINE" p1 p2 p3 p4 "c")
 (command "HATCH" "ZIGZAG" 4.00 0.00 "L" "")
 (command "COLOR" "BYLAYER")
 (command "LAYER" "S" "CGBLITHCD" "")
 (setq p1 (list 434.00 1542.98) p2 (list 435.35 1542.98))
 (command "LINE" p1 p2 "")
 (setq p1 (list 435.50 1542.60) p2 (list 0.00 0.00))
 (command "TEXT" "J" "ML" p1   0.75  0.00 "543")
 (command "LAYER" "S" "CGBTHK" "")
 (setq p1 (list 440.00 1542.60) p2 (list 0.00 0.00))
 (command "TEXT" "J" "ML" p1   0.75  0.00 "4.17")
 (command "LAYER" "S" "CGBHZID" "")
 (setq p1 (list 444.50 1542.60) p2 (list 0.00 0.00))
 (command "TEXT" "J" "ML" p1   0.75  0.00 "")
 (setq p1 (list 446.75 1542.60) p2 (list 0.00 0.00))
 (command "TEXT" "J" "ML" p1   0.75  0.00 "6700")
 (command "LAYER" "S" "CGBLITHTXT" "")
 (setq p1 (list 450.50 1542.60) p2 (list 0.00 0.00))
 (command "TEXT" "J" "ML" p1   0.75  0.00 "GRY SS W/SH STKS")
 (command "LAYER" "S" "CGBCMNT" "")
 (setq p1 (list 470.75 1542.60) p2 (list 0.00 0.00))
 (command "TEXT" "J" "ML" p1   0.75  0.00 "")
 (command "LAYER" "S" "CGBMAIN" "")
 (setq p1 (list 428.00 1540.89) p2 (list 434.00 1540.89) p3 (list 434.00 1533.68) p4 (list 428.00 1533.68))
 (command "PLINE" p1 p2 p3 p4 "c")
 (command "HATCH" "ZIGZAG" 0.25 0.00 "L" "")
 (command "COLOR" "BYLAYER")
 (command "LAYER" "S" "CGBLITHCD" "")
 (setq p1 (list 434.00 1537.29) p2 (list 435.35 1537.29))
 (command "LINE" p1 p2 "")
 (setq p1 (list 435.50 1536.91) p2 (list 0.00 0.00))
 (command "TEXT" "J" "ML" p1   0.75  0.00 "744")
 (command "LAYER" "S" "CGBTHK" "")
 (setq p1 (list 440.00 1536.91) p2 (list 0.00 0.00))
 (command "TEXT" "J" "ML" p1   0.75  0.00 "7.21")
 (command "LAYER" "S" "CGBHZID" "")
 (setq p1 (list 444.50 1536.91) p2 (list 0.00 0.00))
 (command "TEXT" "J" "ML" p1   0.75  0.00 "")
 (setq p1 (list 446.75 1536.91) p2 (list 0.00 0.00))
 (command "TEXT" "J" "ML" p1   0.75  0.00 "6700")
 (command "LAYER" "S" "CGBLITHTXT" "")
 (setq p1 (list 450.50 1536.91) p2 (list 0.00 0.00))
 (command "TEXT" "J" "ML" p1   0.75  0.00 "GRY QTZ PEB CGL")
 (command "LAYER" "S" "CGBCMNT" "")
 (setq p1 (list 470.75 1536.91) p2 (list 0.00 0.00))
 (command "TEXT" "J" "ML" p1   0.75  0.00 "")
 (command "LAYER" "S" "CGBMAIN" "")
 (setq p1 (list 428.00 1533.68) p2 (list 434.00 1533.68) p3 (list 434.00 1520.05) p4 (list 428.00 1520.05))
 (command "PLINE" p1 p2 p3 p4 "c")
 (command "HATCH" "ZIGZAG" 0.25 0.00 "L" "")
 (command "COLOR" "BYLAYER")
 (command "LAYER" "S" "CGBLITHCD" "")
 (setq p1 (list 434.00 1526.87) p2 (list 435.35 1526.87))
 (command "LINE" p1 p2 "")
 (setq p1 (list 435.50 1526.49) p2 (list 0.00 0.00))
 (command "TEXT" "J" "ML" p1   0.75  0.00 "744")
 (command "LAYER" "S" "CGBTHK" "")
 (setq p1 (list 440.00 1526.49) p2 (list 0.00 0.00))
 (command "TEXT" "J" "ML" p1   0.75  0.00 "13.63")
 (command "LAYER" "S" "CGBHZID" "")
 (setq p1 (list 444.50 1526.49) p2 (list 0.00 0.00))
 (command "TEXT" "J" "ML" p1   0.75  0.00 "")
 (setq p1 (list 446.75 1526.49) p2 (list 0.00 0.00))
 (command "TEXT" "J" "ML" p1   0.75  0.00 "6700")
 (command "LAYER" "S" "CGBLITHTXT" "")
 (setq p1 (list 450.50 1526.49) p2 (list 0.00 0.00))
 (command "TEXT" "J" "ML" p1   0.75  0.00 "GRY QTZ PEB CGL")
 (command "LAYER" "S" "CGBCMNT" "")
 (setq p1 (list 470.75 1526.49) p2 (list 0.00 0.00))
 (command "TEXT" "J" "ML" p1   0.75  0.00 "")
 (command "LAYER" "S" "CGBMAIN" "")
 (setq p1 (list 428.00 1520.05) p2 (list 434.00 1520.05) p3 (list 434.00 1514.93) p4 (list 428.00 1514.93))
 (command "PLINE" p1 p2 p3 p4 "c")
 (command "HATCH" "ZIGZAG" 0.25 0.00 "L" "")
 (command "COLOR" "BYLAYER")
 (command "LAYER" "S" "CGBLITHCD" "")
 (setq p1 (list 434.00 1517.49) p2 (list 435.35 1517.49))
 (command "LINE" p1 p2 "")
 (setq p1 (list 435.50 1517.12) p2 (list 0.00 0.00))
 (command "TEXT" "J" "ML" p1   0.75  0.00 "744")
 (command "LAYER" "S" "CGBTHK" "")
 (setq p1 (list 440.00 1517.12) p2 (list 0.00 0.00))
 (command "TEXT" "J" "ML" p1   0.75  0.00 "5.12")
 (command "LAYER" "S" "CGBHZID" "")
 (setq p1 (list 444.50 1517.12) p2 (list 0.00 0.00))
 (command "TEXT" "J" "ML" p1   0.75  0.00 "")
 (setq p1 (list 446.75 1517.12) p2 (list 0.00 0.00))
 (command "TEXT" "J" "ML" p1   0.75  0.00 "6700")
 (command "LAYER" "S" "CGBLITHTXT" "")
 (setq p1 (list 450.50 1517.12) p2 (list 0.00 0.00))
 (command "TEXT" "J" "ML" p1   0.75  0.00 "GRY QTZ PEB CGL")
 (command "LAYER" "S" "CGBCMNT" "")
 (setq p1 (list 470.75 1517.12) p2 (list 0.00 0.00))
 (command "TEXT" "J" "ML" p1   0.75  0.00 "")
 (command "LAYER" "S" "CGBMAIN" "")
 (setq p1 (list 428.00 1514.93) p2 (list 434.00 1514.93) p3 (list 434.00 1511.19) p4 (list 428.00 1511.19))
 (command "PLINE" p1 p2 p3 p4 "c")
 (command "HATCH" "ZIGZAG" 2.00 45.00 "L" "")
 (command "COLOR" "BYLAYER")
 (command "LAYER" "S" "CGBLITHCD" "")
 (setq p1 (list 434.00 1513.06) p2 (list 435.35 1513.06))
 (command "LINE" p1 p2 "")
 (setq p1 (list 435.50 1512.69) p2 (list 0.00 0.00))
 (command "TEXT" "J" "ML" p1   0.75  0.00 "013")
 (command "LAYER" "S" "CGBTHK" "")
 (setq p1 (list 440.00 1512.69) p2 (list 0.00 0.00))
 (command "TEXT" "J" "ML" p1   0.75  0.00 "3.74")
 (command "LAYER" "S" "CGBHZID" "")
 (setq p1 (list 444.50 1512.69) p2 (list 0.00 0.00))
 (command "TEXT" "J" "ML" p1   0.75  0.00 "")
 (setq p1 (list 446.75 1512.69) p2 (list 0.00 0.00))
 (command "TEXT" "J" "ML" p1   0.75  0.00 "6400")
 (command "LAYER" "S" "CGBLITHTXT" "")
 (setq p1 (list 450.50 1512.69) p2 (list 0.00 0.00))
 (command "TEXT" "J" "ML" p1   0.75  0.00 "SLUMPED SH")
 (command "LAYER" "S" "CGBCMNT" "")
 (setq p1 (list 470.75 1512.69) p2 (list 0.00 0.00))
 (command "TEXT" "J" "ML" p1   0.75  0.00 "SFT")
 (command "LAYER" "S" "CGBMAIN" "")
 (setq p1 (list 428.00 1511.19) p2 (list 434.00 1511.19) p3 (list 434.00 1510.26) p4 (list 428.00 1510.26))
 (command "PLINE" p1 p2 p3 p4 "c")
 (command "HATCH" "ZIGZAG" 2.00 45.00 "L" "")
 (command "COLOR" "BYLAYER")
 (command "LAYER" "S" "CGBLITHCD" "")
 (setq p1 (list 434.00 1510.73) p2 (list 435.35 1510.73))
 (command "LINE" p1 p2 "")
 (setq p1 (list 435.50 1510.35) p2 (list 0.00 0.00))
 (command "TEXT" "J" "ML" p1   0.75  0.00 "014")
 (command "LAYER" "S" "CGBTHK" "")
 (setq p1 (list 440.00 1510.35) p2 (list 0.00 0.00))
 (command "TEXT" "J" "ML" p1   0.75  0.00 "0.93")
 (command "LAYER" "S" "CGBHZID" "")
 (setq p1 (list 444.50 1510.35) p2 (list 0.00 0.00))
 (command "TEXT" "J" "ML" p1   0.75  0.00 "")
 (setq p1 (list 446.75 1510.35) p2 (list 0.00 0.00))
 (command "TEXT" "J" "ML" p1   0.75  0.00 "6400")
 (command "LAYER" "S" "CGBLITHTXT" "")
 (setq p1 (list 450.50 1510.35) p2 (list 0.00 0.00))
 (command "TEXT" "J" "ML" p1   0.75  0.00 "SLUMPED SDY SH")
 (command "LAYER" "S" "CGBCMNT" "")
 (setq p1 (list 470.75 1510.35) p2 (list 0.00 0.00))
 (command "TEXT" "J" "ML" p1   0.75  0.00 "")
 (command "LAYER" "S" "CGBMAIN" "")
 (setq p1 (list 428.00 1510.26) p2 (list 434.00 1510.26) p3 (list 434.00 1510.11) p4 (list 428.00 1510.11))
 (command "PLINE" p1 p2 p3 p4 "c")
 (command "HATCH" "ZIGZAG" 5.00 0.00 "L" "")
 (command "COLOR" "BYLAYER")
 (command "LAYER" "S" "CGBLITHCD" "")
 (setq p1 (list 434.00 1510.19) p2 (list 435.35 1508.94))
 (command "LINE" p1 p2 "")
 (setq p1 (list 435.50 1508.56) p2 (list 0.00 0.00))
 (command "TEXT" "J" "ML" p1   0.75  0.00 "137")
 (command "LAYER" "S" "CGBTHK" "")
 (setq p1 (list 440.00 1508.56) p2 (list 0.00 0.00))
 (command "TEXT" "J" "ML" p1   0.75  0.00 "0.15")
 (command "LAYER" "S" "CGBHZID" "")
 (setq p1 (list 444.50 1508.56) p2 (list 0.00 0.00))
 (command "TEXT" "J" "ML" p1   0.75  0.00 "")
 (setq p1 (list 446.75 1508.56) p2 (list 0.00 0.00))
 (command "TEXT" "J" "ML" p1   0.75  0.00 "6400")
 (command "LAYER" "S" "CGBLITHTXT" "")
 (setq p1 (list 450.50 1508.56) p2 (list 0.00 0.00))
 (command "TEXT" "J" "ML" p1   0.75  0.00 "LT GRY GRN FIRECLAY")
 (command "LAYER" "S" "CGBCMNT" "")
 (setq p1 (list 470.75 1508.56) p2 (list 0.00 0.00))
 (command "TEXT" "J" "ML" p1   0.75  0.00 "V SFT")
 (command "LAYER" "S" "CGBMAIN" "")
 (setq p1 (list 428.00 1510.11) p2 (list 434.00 1510.11) p3 (list 434.00 1510.01) p4 (list 428.00 1510.01))
 (command "PLINE" p1 p2 p3 p4 "c")
 (command "HATCH" "ZIGZAG" 2.00 45.00 "L" "")
 (command "COLOR" "BYLAYER")
 (command "LAYER" "S" "CGBLITHCD" "")
 (setq p1 (list 434.00 1510.06) p2 (list 435.35 1507.69))
 (command "LINE" p1 p2 "")
 (setq p1 (list 435.50 1507.31) p2 (list 0.00 0.00))
 (command "TEXT" "J" "ML" p1   0.75  0.00 "013")
 (command "LAYER" "S" "CGBTHK" "")
 (setq p1 (list 440.00 1507.31) p2 (list 0.00 0.00))
 (command "TEXT" "J" "ML" p1   0.75  0.00 "0.10")
 (command "LAYER" "S" "CGBHZID" "")
 (setq p1 (list 444.50 1507.31) p2 (list 0.00 0.00))
 (command "TEXT" "J" "ML" p1   0.75  0.00 "")
 (setq p1 (list 446.75 1507.31) p2 (list 0.00 0.00))
 (command "TEXT" "J" "ML" p1   0.75  0.00 "6400")
 (command "LAYER" "S" "CGBLITHTXT" "")
 (setq p1 (list 450.50 1507.31) p2 (list 0.00 0.00))
 (command "TEXT" "J" "ML" p1   0.75  0.00 "SLUMPED SH")
 (command "LAYER" "S" "CGBCMNT" "")
 (setq p1 (list 470.75 1507.31) p2 (list 0.00 0.00))
 (command "TEXT" "J" "ML" p1   0.75  0.00 "SFT")
 (command "LAYER" "S" "CGBMAIN" "")
 (setq p1 (list 428.00 1510.01) p2 (list 434.00 1510.01) p3 (list 434.00 1509.91) p4 (list 428.00 1509.91))
 (command "PLINE" p1 p2 p3 p4 "c")
 (command "HATCH" "ZIGZAG" 5.00 0.00 "L" "")
 (command "COLOR" "BYLAYER")
 (command "LAYER" "S" "CGBLITHCD" "")
 (setq p1 (list 434.00 1509.96) p2 (list 435.35 1506.44))
 (command "LINE" p1 p2 "")
 (setq p1 (list 435.50 1506.06) p2 (list 0.00 0.00))
 (command "TEXT" "J" "ML" p1   0.75  0.00 "074")
 (command "LAYER" "S" "CGBTHK" "")
 (setq p1 (list 440.00 1506.06) p2 (list 0.00 0.00))
 (command "TEXT" "J" "ML" p1   0.75  0.00 "0.10")
 (command "LAYER" "S" "CGBHZID" "")
 (setq p1 (list 444.50 1506.06) p2 (list 0.00 0.00))
 (command "TEXT" "J" "ML" p1   0.75  0.00 "")
 (setq p1 (list 446.75 1506.06) p2 (list 0.00 0.00))
 (command "TEXT" "J" "ML" p1   0.75  0.00 "6400")
 (command "LAYER" "S" "CGBLITHTXT" "")
 (setq p1 (list 450.50 1506.06) p2 (list 0.00 0.00))
 (command "TEXT" "J" "ML" p1   0.75  0.00 "MASS IRNSTN")
 (command "LAYER" "S" "CGBCMNT" "")
 (setq p1 (list 470.75 1506.06) p2 (list 0.00 0.00))
 (command "TEXT" "J" "ML" p1   0.75  0.00 "SID NOD OR LA")
 (command "LAYER" "S" "CGBMAIN" "")
 (setq p1 (list 428.00 1509.91) p2 (list 434.00 1509.91) p3 (list 434.00 1509.05) p4 (list 428.00 1509.05))
 (command "PLINE" p1 p2 p3 p4 "c")
 (command "HATCH" "ZIGZAG" 0.25 0.00 "L" "")
 (command "COLOR" "BYLAYER")
 (command "LAYER" "S" "CGBLITHCD" "")
 (setq p1 (list 434.00 1509.48) p2 (list 435.35 1505.19))
 (command "LINE" p1 p2 "")
 (setq p1 (list 435.50 1504.81) p2 (list 0.00 0.00))
 (command "TEXT" "J" "ML" p1   0.75  0.00 "762")
 (command "LAYER" "S" "CGBTHK" "")
 (setq p1 (list 440.00 1504.81) p2 (list 0.00 0.00))
 (command "TEXT" "J" "ML" p1   0.75  0.00 "0.86")
 (command "LAYER" "S" "CGBHZID" "")
 (setq p1 (list 444.50 1504.81) p2 (list 0.00 0.00))
 (command "TEXT" "J" "ML" p1   0.75  0.00 "")
 (setq p1 (list 446.75 1504.81) p2 (list 0.00 0.00))
 (command "TEXT" "J" "ML" p1   0.75  0.00 "6400")
 (command "LAYER" "S" "CGBLITHTXT" "")
 (setq p1 (list 450.50 1504.81) p2 (list 0.00 0.00))
 (command "TEXT" "J" "ML" p1   0.75  0.00 "HARD SH PEB CGL")
 (command "LAYER" "S" "CGBCMNT" "")
 (setq p1 (list 470.75 1504.81) p2 (list 0.00 0.00))
 (command "TEXT" "J" "ML" p1   0.75  0.00 "FRAC @ BASE")
 (command "LAYER" "S" "CGBMAIN" "")
 (setq p1 (list 428.00 1509.05) p2 (list 434.00 1509.05) p3 (list 434.00 1509.02) p4 (list 428.00 1509.02))
 (command "PLINE" p1 p2 p3 p4 "c")
 (command "HATCH" "ZIGZAG" 5.00 0.00 "L" "")
 (command "COLOR" "BYLAYER")
 (command "LAYER" "S" "CGBLITHCD" "")
 (setq p1 (list 434.00 1509.04) p2 (list 435.35 1503.94))
 (command "LINE" p1 p2 "")
 (setq p1 (list 435.50 1503.56) p2 (list 0.00 0.00))
 (command "TEXT" "J" "ML" p1   0.75  0.00 "137")
 (command "LAYER" "S" "CGBTHK" "")
 (setq p1 (list 440.00 1503.56) p2 (list 0.00 0.00))
 (command "TEXT" "J" "ML" p1   0.75  0.00 "0.03")
 (command "LAYER" "S" "CGBHZID" "")
 (setq p1 (list 444.50 1503.56) p2 (list 0.00 0.00))
 (command "TEXT" "J" "ML" p1   0.75  0.00 "")
 (setq p1 (list 446.75 1503.56) p2 (list 0.00 0.00))
 (command "TEXT" "J" "ML" p1   0.75  0.00 "6351")
 (command "LAYER" "S" "CGBLITHTXT" "")
 (setq p1 (list 450.50 1503.56) p2 (list 0.00 0.00))
 (command "TEXT" "J" "ML" p1   0.75  0.00 "LT GRY GRN FIRECLAY")
 (command "LAYER" "S" "CGBCMNT" "")
 (setq p1 (list 470.75 1503.56) p2 (list 0.00 0.00))
 (command "TEXT" "J" "ML" p1   0.75  0.00 "V SFT")
 (command "LAYER" "S" "CGBMAIN" "")
 (setq p1 (list 428.00 1509.02) p2 (list 434.00 1509.02) p3 (list 434.00 1506.92) p4 (list 428.00 1506.92))
 (command "PLINE" p1 p2 p3 p4 "c")
 (command "HATCH" "ZIGZAG" 4.00 22.50 "L" "")
 (command "COLOR" "BYLAYER")
 (command "LAYER" "S" "CGBLITHCD" "")
 (setq p1 (list 434.00 1507.97) p2 (list 435.35 1502.69))
 (command "LINE" p1 p2 "")
 (setq p1 (list 435.50 1502.31) p2 (list 0.00 0.00))
 (command "TEXT" "J" "ML" p1   0.75  0.00 "114")
 (command "LAYER" "S" "CGBTHK" "")
 (setq p1 (list 440.00 1502.31) p2 (list 0.00 0.00))
 (command "TEXT" "J" "ML" p1   0.75  0.00 "2.10")
 (command "LAYER" "S" "CGBHZID" "")
 (setq p1 (list 444.50 1502.31) p2 (list 0.00 0.00))
 (command "TEXT" "J" "ML" p1   0.75  0.00 "")
 (setq p1 (list 446.75 1502.31) p2 (list 0.00 0.00))
 (command "TEXT" "J" "ML" p1   0.75  0.00 "6351")
 (command "LAYER" "S" "CGBLITHTXT" "")
 (setq p1 (list 450.50 1502.31) p2 (list 0.00 0.00))
 (command "TEXT" "J" "ML" p1   0.75  0.00 "BLK SH")
 (command "LAYER" "S" "CGBCMNT" "")
 (setq p1 (list 470.75 1502.31) p2 (list 0.00 0.00))
 (command "TEXT" "J" "ML" p1   0.75  0.00 "FRACS, PYRTIC")
 (command "LAYER" "S" "CGBMAIN" "")
 (setq p1 (list 428.00 1506.92) p2 (list 434.00 1506.92) p3 (list 434.00 1506.54) p4 (list 428.00 1506.54))
 (command "PLINE" p1 p2 p3 p4 "c")
 (command "HATCH" "ZIGZAG" 4.00 22.50 "L" "")
 (command "COLOR" "BYLAYER")
 (command "LAYER" "S" "CGBLITHCD" "")
 (setq p1 (list 434.00 1506.73) p2 (list 435.35 1501.44))
 (command "LINE" p1 p2 "")
 (setq p1 (list 435.50 1501.06) p2 (list 0.00 0.00))
 (command "TEXT" "J" "ML" p1   0.75  0.00 "114")
 (command "LAYER" "S" "CGBTHK" "")
 (setq p1 (list 440.00 1501.06) p2 (list 0.00 0.00))
 (command "TEXT" "J" "ML" p1   0.75  0.00 "0.38")
 (command "LAYER" "S" "CGBHZID" "")
 (setq p1 (list 444.50 1501.06) p2 (list 0.00 0.00))
 (command "TEXT" "J" "ML" p1   0.75  0.00 "")
 (setq p1 (list 446.75 1501.06) p2 (list 0.00 0.00))
 (command "TEXT" "J" "ML" p1   0.75  0.00 "6351")
 (command "LAYER" "S" "CGBLITHTXT" "")
 (setq p1 (list 450.50 1501.06) p2 (list 0.00 0.00))
 (command "TEXT" "J" "ML" p1   0.75  0.00 "BLK SH")
 (command "LAYER" "S" "CGBCMNT" "")
 (setq p1 (list 470.75 1501.06) p2 (list 0.00 0.00))
 (command "TEXT" "J" "ML" p1   0.75  0.00 "PYRT @ CNCT")
 (command "LAYER" "S" "CGBMAIN" "")
 (setq p1 (list 428.00 1506.54) p2 (list 434.00 1506.54) p3 (list 434.00 1505.76) p4 (list 428.00 1505.76))
 (command "PLINE" p1 p2 p3 p4 "c")
 (command "HATCH" "ZIGZAG" 0.40 45.00 "L" "")
 (command "COLOR" "BYLAYER")
 (command "LAYER" "S" "CGBLITHCD" "")
 (setq p1 (list 434.00 1506.15) p2 (list 435.35 1500.19))
 (command "LINE" p1 p2 "")
 (setq p1 (list 435.50 1499.81) p2 (list 0.00 0.00))
 (command "TEXT" "J" "ML" p1   0.75  0.00 "022")
 (command "LAYER" "S" "CGBTHK" "")
 (setq p1 (list 440.00 1499.81) p2 (list 0.00 0.00))
 (command "TEXT" "J" "ML" p1   0.75  0.00 "0.78")
 (command "LAYER" "S" "CGBHZID" "")
 (setq p1 (list 444.50 1499.81) p2 (list 0.00 0.00))
 (command "TEXT" "J" "ML" p1   0.75  0.00 "")
 (setq p1 (list 446.75 1499.81) p2 (list 0.00 0.00))
 (command "TEXT" "J" "ML" p1   0.75  0.00 "6000")
 (command "LAYER" "S" "CGBLITHTXT" "")
 (setq p1 (list 450.50 1499.81) p2 (list 0.00 0.00))
 (command "TEXT" "J" "ML" p1   0.75  0.00 "COAL W/BONE LAYERS")
 (command "LAYER" "S" "CGBCMNT" "")
 (setq p1 (list 470.75 1499.81) p2 (list 0.00 0.00))
 (command "TEXT" "J" "ML" p1   0.75  0.00 "DULL, PYRITIC")
 (command "LAYER" "S" "CGBMAIN" "")
 (setq p1 (list 428.00 1505.76) p2 (list 434.00 1505.76) p3 (list 434.00 1505.26) p4 (list 428.00 1505.26))
 (command "PLINE" p1 p2 p3 p4 "c")
 (command "HATCH" "ZIGZAG" 0.40 45.00 "L" "")
 (command "COLOR" "BYLAYER")
 (command "LAYER" "S" "CGBLITHCD" "")
 (setq p1 (list 434.00 1505.51) p2 (list 435.35 1498.94))
 (command "LINE" p1 p2 "")
 (setq p1 (list 435.50 1498.56) p2 (list 0.00 0.00))
 (command "TEXT" "J" "ML" p1   0.75  0.00 "023")
 (command "LAYER" "S" "CGBTHK" "")
 (setq p1 (list 440.00 1498.56) p2 (list 0.00 0.00))
 (command "TEXT" "J" "ML" p1   0.75  0.00 "0.50")
 (command "LAYER" "S" "CGBHZID" "")
 (setq p1 (list 444.50 1498.56) p2 (list 0.00 0.00))
 (command "TEXT" "J" "ML" p1   0.75  0.00 "")
 (setq p1 (list 446.75 1498.56) p2 (list 0.00 0.00))
 (command "TEXT" "J" "ML" p1   0.75  0.00 "6000")
 (command "LAYER" "S" "CGBLITHTXT" "")
 (setq p1 (list 450.50 1498.56) p2 (list 0.00 0.00))
 (command "TEXT" "J" "ML" p1   0.75  0.00 "COAL W/BONE STKS")
 (command "LAYER" "S" "CGBCMNT" "")
 (setq p1 (list 470.75 1498.56) p2 (list 0.00 0.00))
 (command "TEXT" "J" "ML" p1   0.75  0.00 "BRIGHT & DULL")
 (command "LAYER" "S" "CGBMAIN" "")
 (setq p1 (list 428.00 1505.26) p2 (list 434.00 1505.26) p3 (list 434.00 1504.77) p4 (list 428.00 1504.77))
 (command "PLINE" p1 p2 p3 p4 "c")
 (command "COLOR" "BLUE")
 (command "SOLID" p1 p2 p4 p3 "")
 (command "COLOR" "BYLAYER")
 (command "LAYER" "S" "CGBLITHCD" "")
 (setq p1 (list 434.00 1505.02) p2 (list 435.35 1497.69))
 (command "LINE" p1 p2 "")
 (setq p1 (list 435.50 1497.31) p2 (list 0.00 0.00))
 (command "TEXT" "J" "ML" p1   0.75  0.00 "021")
 (command "LAYER" "S" "CGBTHK" "")
 (setq p1 (list 440.00 1497.31) p2 (list 0.00 0.00))
 (command "TEXT" "J" "ML" p1   0.75  0.00 "0.49")
 (command "LAYER" "S" "CGBHZID" "")
 (setq p1 (list 444.50 1497.31) p2 (list 0.00 0.00))
 (command "TEXT" "J" "ML" p1   0.75  0.00 "")
 (setq p1 (list 446.75 1497.31) p2 (list 0.00 0.00))
 (command "TEXT" "J" "ML" p1   0.75  0.00 "6000")
 (command "LAYER" "S" "CGBLITHTXT" "")
 (setq p1 (list 450.50 1497.31) p2 (list 0.00 0.00))
 (command "TEXT" "J" "ML" p1   0.75  0.00 "COMMON BANDED COAL")
 (command "LAYER" "S" "CGBCMNT" "")
 (setq p1 (list 470.75 1497.31) p2 (list 0.00 0.00))
 (command "TEXT" "J" "ML" p1   0.75  0.00 "CRMBLD VIT")
 (command "LAYER" "S" "CGBMAIN" "")
 (setq p1 (list 428.00 1504.77) p2 (list 434.00 1504.77) p3 (list 434.00 1504.74) p4 (list 428.00 1504.74))
 (command "PLINE" p1 p2 p3 p4 "c")
 (command "HATCH" "ZIGZAG" 0.80 0.00 "L" "")
 (command "COLOR" "BYLAYER")
 (command "LAYER" "S" "CGBLITHCD" "")
 (setq p1 (list 434.00 1504.76) p2 (list 435.35 1496.44))
 (command "LINE" p1 p2 "")
 (setq p1 (list 435.50 1496.06) p2 (list 0.00 0.00))
 (command "TEXT" "J" "ML" p1   0.75  0.00 "029")
 (command "LAYER" "S" "CGBTHK" "")
 (setq p1 (list 440.00 1496.06) p2 (list 0.00 0.00))
 (command "TEXT" "J" "ML" p1   0.75  0.00 "0.03")
 (command "LAYER" "S" "CGBHZID" "")
 (setq p1 (list 444.50 1496.06) p2 (list 0.00 0.00))
 (command "TEXT" "J" "ML" p1   0.75  0.00 "")
 (setq p1 (list 446.75 1496.06) p2 (list 0.00 0.00))
 (command "TEXT" "J" "ML" p1   0.75  0.00 "6000")
 (command "LAYER" "S" "CGBLITHTXT" "")
 (setq p1 (list 450.50 1496.06) p2 (list 0.00 0.00))
 (command "TEXT" "J" "ML" p1   0.75  0.00 "COAL W/PYRITE STKS")
 (command "LAYER" "S" "CGBCMNT" "")
 (setq p1 (list 470.75 1496.06) p2 (list 0.00 0.00))
 (command "TEXT" "J" "ML" p1   0.75  0.00 "PYRT LAYR, FU")
 (command "LAYER" "S" "CGBMAIN" "")
 (setq p1 (list 428.00 1504.74) p2 (list 434.00 1504.74) p3 (list 434.00 1504.20) p4 (list 428.00 1504.20))
 (command "PLINE" p1 p2 p3 p4 "c")
 (command "HATCH" "ZIGZAG" 0.40 45.00 "L" "")
 (command "COLOR" "BYLAYER")
 (command "LAYER" "S" "CGBLITHCD" "")
 (setq p1 (list 434.00 1504.47) p2 (list 435.35 1495.19))
 (command "LINE" p1 p2 "")
 (setq p1 (list 435.50 1494.81) p2 (list 0.00 0.00))
 (command "TEXT" "J" "ML" p1   0.75  0.00 "023")
 (command "LAYER" "S" "CGBTHK" "")
 (setq p1 (list 440.00 1494.81) p2 (list 0.00 0.00))
 (command "TEXT" "J" "ML" p1   0.75  0.00 "0.54")
 (command "LAYER" "S" "CGBHZID" "")
 (setq p1 (list 444.50 1494.81) p2 (list 0.00 0.00))
 (command "TEXT" "J" "ML" p1   0.75  0.00 "")
 (setq p1 (list 446.75 1494.81) p2 (list 0.00 0.00))
 (command "TEXT" "J" "ML" p1   0.75  0.00 "6000")
 (command "LAYER" "S" "CGBLITHTXT" "")
 (setq p1 (list 450.50 1494.81) p2 (list 0.00 0.00))
 (command "TEXT" "J" "ML" p1   0.75  0.00 "COAL W/BONE STKS")
 (command "LAYER" "S" "CGBCMNT" "")
 (setq p1 (list 470.75 1494.81) p2 (list 0.00 0.00))
 (command "TEXT" "J" "ML" p1   0.75  0.00 "CRMBLD VITRAI")
 (command "LAYER" "S" "CGBMAIN" "")
 (setq p1 (list 428.00 1504.20) p2 (list 434.00 1504.20) p3 (list 434.00 1503.88) p4 (list 428.00 1503.88))
 (command "PLINE" p1 p2 p3 p4 "c")
 (command "HATCH" "ZIGZAG" 5.00 0.00 "L" "")
 (command "COLOR" "BYLAYER")
 (command "LAYER" "S" "CGBLITHCD" "")
 (setq p1 (list 434.00 1504.04) p2 (list 435.35 1493.94))
 (command "LINE" p1 p2 "")
 (setq p1 (list 435.50 1493.56) p2 (list 0.00 0.00))
 (command "TEXT" "J" "ML" p1   0.75  0.00 "032")
 (command "LAYER" "S" "CGBTHK" "")
 (setq p1 (list 440.00 1493.56) p2 (list 0.00 0.00))
 (command "TEXT" "J" "ML" p1   0.75  0.00 "0.32")
 (command "LAYER" "S" "CGBHZID" "")
 (setq p1 (list 444.50 1493.56) p2 (list 0.00 0.00))
 (command "TEXT" "J" "ML" p1   0.75  0.00 "")
 (setq p1 (list 446.75 1493.56) p2 (list 0.00 0.00))
 (command "TEXT" "J" "ML" p1   0.75  0.00 "5951")
 (command "LAYER" "S" "CGBLITHTXT" "")
 (setq p1 (list 450.50 1493.56) p2 (list 0.00 0.00))
 (command "TEXT" "J" "ML" p1   0.75  0.00 "BONE W/COAL LAYERS")
 (command "LAYER" "S" "CGBCMNT" "")
 (setq p1 (list 470.75 1493.56) p2 (list 0.00 0.00))
 (command "TEXT" "J" "ML" p1   0.75  0.00 "DULL W/ THIN")
 (command "LAYER" "S" "CGBMAIN" "")
 (setq p1 (list 428.00 1503.88) p2 (list 434.00 1503.88) p3 (list 434.00 1503.77) p4 (list 428.00 1503.77))
 (command "PLINE" p1 p2 p3 p4 "c")
 (command "HATCH" "ZIGZAG" 4.00 0.00 "L" "")
 (command "COLOR" "BYLAYER")
 (command "LAYER" "S" "CGBLITHCD" "")
 (setq p1 (list 434.00 1503.83) p2 (list 435.35 1492.69))
 (command "LINE" p1 p2 "")
 (setq p1 (list 435.50 1492.31) p2 (list 0.00 0.00))
 (command "TEXT" "J" "ML" p1   0.75  0.00 "123")
 (command "LAYER" "S" "CGBTHK" "")
 (setq p1 (list 440.00 1492.31) p2 (list 0.00 0.00))
 (command "TEXT" "J" "ML" p1   0.75  0.00 "0.11")
 (command "LAYER" "S" "CGBHZID" "")
 (setq p1 (list 444.50 1492.31) p2 (list 0.00 0.00))
 (command "TEXT" "J" "ML" p1   0.75  0.00 "")
 (setq p1 (list 446.75 1492.31) p2 (list 0.00 0.00))
 (command "TEXT" "J" "ML" p1   0.75  0.00 "5951")
 (command "LAYER" "S" "CGBLITHTXT" "")
 (setq p1 (list 450.50 1492.31) p2 (list 0.00 0.00))
 (command "TEXT" "J" "ML" p1   0.75  0.00 "DRK GRY SH W/COAL STKS")
 (command "LAYER" "S" "CGBCMNT" "")
 (setq p1 (list 470.75 1492.31) p2 (list 0.00 0.00))
 (command "TEXT" "J" "ML" p1   0.75  0.00 "")
 (command "LAYER" "S" "CGBMAIN" "")
 (setq p1 (list 428.00 1503.77) p2 (list 434.00 1503.77) p3 (list 434.00 1503.66) p4 (list 428.00 1503.66))
 (command "PLINE" p1 p2 p3 p4 "c")
 (command "HATCH" "ZIGZAG" 0.30 22.50 "L" "")
 (command "COLOR" "BYLAYER")
 (command "LAYER" "S" "CGBLITHCD" "")
 (setq p1 (list 434.00 1503.72) p2 (list 435.35 1491.44))
 (command "LINE" p1 p2 "")
 (setq p1 (list 435.50 1491.06) p2 (list 0.00 0.00))
 (command "TEXT" "J" "ML" p1   0.75  0.00 "027")
 (command "LAYER" "S" "CGBTHK" "")
 (setq p1 (list 440.00 1491.06) p2 (list 0.00 0.00))
 (command "TEXT" "J" "ML" p1   0.75  0.00 "0.11")
 (command "LAYER" "S" "CGBHZID" "")
 (setq p1 (list 444.50 1491.06) p2 (list 0.00 0.00))
 (command "TEXT" "J" "ML" p1   0.75  0.00 "")
 (setq p1 (list 446.75 1491.06) p2 (list 0.00 0.00))
 (command "TEXT" "J" "ML" p1   0.75  0.00 "5951")
 (command "LAYER" "S" "CGBLITHTXT" "")
 (setq p1 (list 450.50 1491.06) p2 (list 0.00 0.00))
 (command "TEXT" "J" "ML" p1   0.75  0.00 "COAL W/SH LAYERS")
 (command "LAYER" "S" "CGBCMNT" "")
 (setq p1 (list 470.75 1491.06) p2 (list 0.00 0.00))
 (command "TEXT" "J" "ML" p1   0.75  0.00 "DULL")
 (command "LAYER" "S" "CGBMAIN" "")
 (setq p1 (list 428.00 1503.66) p2 (list 434.00 1503.66) p3 (list 434.00 1503.48) p4 (list 428.00 1503.48))
 (command "PLINE" p1 p2 p3 p4 "c")
 (command "HATCH" "ZIGZAG" 4.00 0.00 "L" "")
 (command "COLOR" "BYLAYER")
 (command "LAYER" "S" "CGBLITHCD" "")
 (setq p1 (list 434.00 1503.57) p2 (list 435.35 1490.19))
 (command "LINE" p1 p2 "")
 (setq p1 (list 435.50 1489.81) p2 (list 0.00 0.00))
 (command "TEXT" "J" "ML" p1   0.75  0.00 "123")
 (command "LAYER" "S" "CGBTHK" "")
 (setq p1 (list 440.00 1489.81) p2 (list 0.00 0.00))
 (command "TEXT" "J" "ML" p1   0.75  0.00 "0.18")
 (command "LAYER" "S" "CGBHZID" "")
 (setq p1 (list 444.50 1489.81) p2 (list 0.00 0.00))
 (command "TEXT" "J" "ML" p1   0.75  0.00 "")
 (setq p1 (list 446.75 1489.81) p2 (list 0.00 0.00))
 (command "TEXT" "J" "ML" p1   0.75  0.00 "5951")
 (command "LAYER" "S" "CGBLITHTXT" "")
 (setq p1 (list 450.50 1489.81) p2 (list 0.00 0.00))
 (command "TEXT" "J" "ML" p1   0.75  0.00 "DRK GRY SH W/COAL STKS")
 (command "LAYER" "S" "CGBCMNT" "")
 (setq p1 (list 470.75 1489.81) p2 (list 0.00 0.00))
 (command "TEXT" "J" "ML" p1   0.75  0.00 "")
 (command "LAYER" "S" "CGBMAIN" "")
 (setq p1 (list 428.00 1503.48) p2 (list 434.00 1503.48) p3 (list 434.00 1503.28) p4 (list 428.00 1503.28))
 (command "PLINE" p1 p2 p3 p4 "c")
 (command "COLOR" "BLUE")
 (command "SOLID" p1 p2 p4 p3 "")
 (command "COLOR" "BYLAYER")
 (command "LAYER" "S" "CGBLITHCD" "")
 (setq p1 (list 434.00 1503.38) p2 (list 435.35 1488.94))
 (command "LINE" p1 p2 "")
 (setq p1 (list 435.50 1488.56) p2 (list 0.00 0.00))
 (command "TEXT" "J" "ML" p1   0.75  0.00 "021")
 (command "LAYER" "S" "CGBTHK" "")
 (setq p1 (list 440.00 1488.56) p2 (list 0.00 0.00))
 (command "TEXT" "J" "ML" p1   0.75  0.00 "0.20")
 (command "LAYER" "S" "CGBHZID" "")
 (setq p1 (list 444.50 1488.56) p2 (list 0.00 0.00))
 (command "TEXT" "J" "ML" p1   0.75  0.00 "")
 (setq p1 (list 446.75 1488.56) p2 (list 0.00 0.00))
 (command "TEXT" "J" "ML" p1   0.75  0.00 "5500")
 (command "LAYER" "S" "CGBLITHTXT" "")
 (setq p1 (list 450.50 1488.56) p2 (list 0.00 0.00))
 (command "TEXT" "J" "ML" p1   0.75  0.00 "COMMON BANDED COAL")
 (command "LAYER" "S" "CGBCMNT" "")
 (setq p1 (list 470.75 1488.56) p2 (list 0.00 0.00))
 (command "TEXT" "J" "ML" p1   0.75  0.00 "THK VIT BND")
 (command "LAYER" "S" "CGBMAIN" "")
 (setq p1 (list 428.00 1503.28) p2 (list 434.00 1503.28) p3 (list 434.00 1503.08) p4 (list 428.00 1503.08))
 (command "PLINE" p1 p2 p3 p4 "c")
 (command "HATCH" "ZIGZAG" 0.40 45.00 "L" "")
 (command "COLOR" "BYLAYER")
 (command "LAYER" "S" "CGBLITHCD" "")
 (setq p1 (list 434.00 1503.18) p2 (list 435.35 1487.69))
 (command "LINE" p1 p2 "")
 (setq p1 (list 435.50 1487.31) p2 (list 0.00 0.00))
 (command "TEXT" "J" "ML" p1   0.75  0.00 "023")
 (command "LAYER" "S" "CGBTHK" "")
 (setq p1 (list 440.00 1487.31) p2 (list 0.00 0.00))
 (command "TEXT" "J" "ML" p1   0.75  0.00 "0.20")
 (command "LAYER" "S" "CGBHZID" "")
 (setq p1 (list 444.50 1487.31) p2 (list 0.00 0.00))
 (command "TEXT" "J" "ML" p1   0.75  0.00 "")
 (setq p1 (list 446.75 1487.31) p2 (list 0.00 0.00))
 (command "TEXT" "J" "ML" p1   0.75  0.00 "5500")
 (command "LAYER" "S" "CGBLITHTXT" "")
 (setq p1 (list 450.50 1487.31) p2 (list 0.00 0.00))
 (command "TEXT" "J" "ML" p1   0.75  0.00 "COAL W/BONE STKS")
 (command "LAYER" "S" "CGBCMNT" "")
 (setq p1 (list 470.75 1487.31) p2 (list 0.00 0.00))
 (command "TEXT" "J" "ML" p1   0.75  0.00 "DULL W/THIN V")
 (command "LAYER" "S" "CGBMAIN" "")
 (setq p1 (list 428.00 1503.08) p2 (list 434.00 1503.08) p3 (list 434.00 1502.98) p4 (list 428.00 1502.98))
 (command "PLINE" p1 p2 p3 p4 "c")
 (command "HATCH" "ZIGZAG" 4.00 0.00 "L" "")
 (command "COLOR" "BYLAYER")
 (command "LAYER" "S" "CGBLITHCD" "")
 (setq p1 (list 434.00 1503.03) p2 (list 435.35 1486.44))
 (command "LINE" p1 p2 "")
 (setq p1 (list 435.50 1486.06) p2 (list 0.00 0.00))
 (command "TEXT" "J" "ML" p1   0.75  0.00 "123")
 (command "LAYER" "S" "CGBTHK" "")
 (setq p1 (list 440.00 1486.06) p2 (list 0.00 0.00))
 (command "TEXT" "J" "ML" p1   0.75  0.00 "0.10")
 (command "LAYER" "S" "CGBHZID" "")
 (setq p1 (list 444.50 1486.06) p2 (list 0.00 0.00))
 (command "TEXT" "J" "ML" p1   0.75  0.00 "")
 (setq p1 (list 446.75 1486.06) p2 (list 0.00 0.00))
 (command "TEXT" "J" "ML" p1   0.75  0.00 "5500")
 (command "LAYER" "S" "CGBLITHTXT" "")
 (setq p1 (list 450.50 1486.06) p2 (list 0.00 0.00))
 (command "TEXT" "J" "ML" p1   0.75  0.00 "DRK GRY SH W/COAL STKS")
 (command "LAYER" "S" "CGBCMNT" "")
 (setq p1 (list 470.75 1486.06) p2 (list 0.00 0.00))
 (command "TEXT" "J" "ML" p1   0.75  0.00 "")
 (command "LAYER" "S" "CGBMAIN" "")
 (setq p1 (list 428.00 1502.98) p2 (list 434.00 1502.98) p3 (list 434.00 1502.32) p4 (list 428.00 1502.32))
 (command "PLINE" p1 p2 p3 p4 "c")
 (command "HATCH" "ZIGZAG" 0.40 45.00 "L" "")
 (command "COLOR" "BYLAYER")
 (command "LAYER" "S" "CGBLITHCD" "")
 (setq p1 (list 434.00 1502.65) p2 (list 435.35 1485.19))
 (command "LINE" p1 p2 "")
 (setq p1 (list 435.50 1484.81) p2 (list 0.00 0.00))
 (command "TEXT" "J" "ML" p1   0.75  0.00 "023")
 (command "LAYER" "S" "CGBTHK" "")
 (setq p1 (list 440.00 1484.81) p2 (list 0.00 0.00))
 (command "TEXT" "J" "ML" p1   0.75  0.00 "0.66")
 (command "LAYER" "S" "CGBHZID" "")
 (setq p1 (list 444.50 1484.81) p2 (list 0.00 0.00))
 (command "TEXT" "J" "ML" p1   0.75  0.00 "")
 (setq p1 (list 446.75 1484.81) p2 (list 0.00 0.00))
 (command "TEXT" "J" "ML" p1   0.75  0.00 "5500")
 (command "LAYER" "S" "CGBLITHTXT" "")
 (setq p1 (list 450.50 1484.81) p2 (list 0.00 0.00))
 (command "TEXT" "J" "ML" p1   0.75  0.00 "COAL W/BONE STKS")
 (command "LAYER" "S" "CGBCMNT" "")
 (setq p1 (list 470.75 1484.81) p2 (list 0.00 0.00))
 (command "TEXT" "J" "ML" p1   0.75  0.00 "DULLS DWN, GB")
 (command "LAYER" "S" "CGBMAIN" "")
 (setq p1 (list 428.00 1502.32) p2 (list 434.00 1502.32) p3 (list 434.00 1502.25) p4 (list 428.00 1502.25))
 (command "PLINE" p1 p2 p3 p4 "c")
 (command "HATCH" "ZIGZAG" 4.00 22.50 "L" "")
 (command "COLOR" "BYLAYER")
 (command "LAYER" "S" "CGBLITHCD" "")
 (setq p1 (list 434.00 1502.29) p2 (list 435.35 1483.94))
 (command "LINE" p1 p2 "")
 (setq p1 (list 435.50 1483.56) p2 (list 0.00 0.00))
 (command "TEXT" "J" "ML" p1   0.75  0.00 "114")
 (command "LAYER" "S" "CGBTHK" "")
 (setq p1 (list 440.00 1483.56) p2 (list 0.00 0.00))
 (command "TEXT" "J" "ML" p1   0.75  0.00 "0.07")
 (command "LAYER" "S" "CGBHZID" "")
 (setq p1 (list 444.50 1483.56) p2 (list 0.00 0.00))
 (command "TEXT" "J" "ML" p1   0.75  0.00 "")
 (setq p1 (list 446.75 1483.56) p2 (list 0.00 0.00))
 (command "TEXT" "J" "ML" p1   0.75  0.00 "5500")
 (command "LAYER" "S" "CGBLITHTXT" "")
 (setq p1 (list 450.50 1483.56) p2 (list 0.00 0.00))
 (command "TEXT" "J" "ML" p1   0.75  0.00 "BLK SH")
 (command "LAYER" "S" "CGBCMNT" "")
 (setq p1 (list 470.75 1483.56) p2 (list 0.00 0.00))
 (command "TEXT" "J" "ML" p1   0.75  0.00 "")
 (command "LAYER" "S" "CGBMAIN" "")
 (setq p1 (list 428.00 1502.25) p2 (list 434.00 1502.25) p3 (list 434.00 1502.10) p4 (list 428.00 1502.10))
 (command "PLINE" p1 p2 p3 p4 "c")
 (command "HATCH" "ZIGZAG" 0.40 45.00 "L" "")
 (command "COLOR" "BYLAYER")
 (command "LAYER" "S" "CGBLITHCD" "")
 (setq p1 (list 434.00 1502.18) p2 (list 435.35 1482.69))
 (command "LINE" p1 p2 "")
 (setq p1 (list 435.50 1482.31) p2 (list 0.00 0.00))
 (command "TEXT" "J" "ML" p1   0.75  0.00 "023")
 (command "LAYER" "S" "CGBTHK" "")
 (setq p1 (list 440.00 1482.31) p2 (list 0.00 0.00))
 (command "TEXT" "J" "ML" p1   0.75  0.00 "0.15")
 (command "LAYER" "S" "CGBHZID" "")
 (setq p1 (list 444.50 1482.31) p2 (list 0.00 0.00))
 (command "TEXT" "J" "ML" p1   0.75  0.00 "")
 (setq p1 (list 446.75 1482.31) p2 (list 0.00 0.00))
 (command "TEXT" "J" "ML" p1   0.75  0.00 "5500")
 (command "LAYER" "S" "CGBLITHTXT" "")
 (setq p1 (list 450.50 1482.31) p2 (list 0.00 0.00))
 (command "TEXT" "J" "ML" p1   0.75  0.00 "COAL W/BONE STKS")
 (command "LAYER" "S" "CGBCMNT" "")
 (setq p1 (list 470.75 1482.31) p2 (list 0.00 0.00))
 (command "TEXT" "J" "ML" p1   0.75  0.00 "DULL W/THIN V")
 (command "LAYER" "S" "CGBMAIN" "")
 (setq p1 (list 428.00 1502.10) p2 (list 434.00 1502.10) p3 (list 434.00 1501.57) p4 (list 428.00 1501.57))
 (command "PLINE" p1 p2 p3 p4 "c")
 (command "COLOR" "BLUE")
 (command "SOLID" p1 p2 p4 p3 "")
 (command "COLOR" "BYLAYER")
 (command "LAYER" "S" "CGBLITHCD" "")
 (setq p1 (list 434.00 1501.84) p2 (list 435.35 1481.44))
 (command "LINE" p1 p2 "")
 (setq p1 (list 435.50 1481.06) p2 (list 0.00 0.00))
 (command "TEXT" "J" "ML" p1   0.75  0.00 "021")
 (command "LAYER" "S" "CGBTHK" "")
 (setq p1 (list 440.00 1481.06) p2 (list 0.00 0.00))
 (command "TEXT" "J" "ML" p1   0.75  0.00 "0.53")
 (command "LAYER" "S" "CGBHZID" "")
 (setq p1 (list 444.50 1481.06) p2 (list 0.00 0.00))
 (command "TEXT" "J" "ML" p1   0.75  0.00 "")
 (setq p1 (list 446.75 1481.06) p2 (list 0.00 0.00))
 (command "TEXT" "J" "ML" p1   0.75  0.00 "5500")
 (command "LAYER" "S" "CGBLITHTXT" "")
 (setq p1 (list 450.50 1481.06) p2 (list 0.00 0.00))
 (command "TEXT" "J" "ML" p1   0.75  0.00 "COMMON BANDED COAL")
 (command "LAYER" "S" "CGBCMNT" "")
 (setq p1 (list 470.75 1481.06) p2 (list 0.00 0.00))
 (command "TEXT" "J" "ML" p1   0.75  0.00 "MOSTLY BRIGHT")
 (command "LAYER" "S" "CGBMAIN" "")
 (setq p1 (list 428.00 1501.57) p2 (list 434.00 1501.57) p3 (list 434.00 1501.49) p4 (list 428.00 1501.49))
 (command "PLINE" p1 p2 p3 p4 "c")
 (command "HATCH" "ZIGZAG" 4.00 0.00 "L" "")
 (command "COLOR" "BYLAYER")
 (command "LAYER" "S" "CGBLITHCD" "")
 (setq p1 (list 434.00 1501.53) p2 (list 435.35 1480.19))
 (command "LINE" p1 p2 "")
 (setq p1 (list 435.50 1479.81) p2 (list 0.00 0.00))
 (command "TEXT" "J" "ML" p1   0.75  0.00 "124")
 (command "LAYER" "S" "CGBTHK" "")
 (setq p1 (list 440.00 1479.81) p2 (list 0.00 0.00))
 (command "TEXT" "J" "ML" p1   0.75  0.00 "0.08")
 (command "LAYER" "S" "CGBHZID" "")
 (setq p1 (list 444.50 1479.81) p2 (list 0.00 0.00))
 (command "TEXT" "J" "ML" p1   0.75  0.00 "")
 (setq p1 (list 446.75 1479.81) p2 (list 0.00 0.00))
 (command "TEXT" "J" "ML" p1   0.75  0.00 "5500")
 (command "LAYER" "S" "CGBLITHTXT" "")
 (setq p1 (list 450.50 1479.81) p2 (list 0.00 0.00))
 (command "TEXT" "J" "ML" p1   0.75  0.00 "DRK GRY SH")
 (command "LAYER" "S" "CGBCMNT" "")
 (setq p1 (list 470.75 1479.81) p2 (list 0.00 0.00))
 (command "TEXT" "J" "ML" p1   0.75  0.00 "")
 (command "LAYER" "S" "CGBMAIN" "")
 (setq p1 (list 428.00 1501.49) p2 (list 434.00 1501.49) p3 (list 434.00 1500.20) p4 (list 428.00 1500.20))
 (command "PLINE" p1 p2 p3 p4 "c")
 (command "HATCH" "ZIGZAG" 0.40 45.00 "L" "")
 (command "COLOR" "BYLAYER")
 (command "LAYER" "S" "CGBLITHCD" "")
 (setq p1 (list 434.00 1500.85) p2 (list 435.35 1478.94))
 (command "LINE" p1 p2 "")
 (setq p1 (list 435.50 1478.56) p2 (list 0.00 0.00))
 (command "TEXT" "J" "ML" p1   0.75  0.00 "022")
 (command "LAYER" "S" "CGBTHK" "")
 (setq p1 (list 440.00 1478.56) p2 (list 0.00 0.00))
 (command "TEXT" "J" "ML" p1   0.75  0.00 "1.29")
 (command "LAYER" "S" "CGBHZID" "")
 (setq p1 (list 444.50 1478.56) p2 (list 0.00 0.00))
 (command "TEXT" "J" "ML" p1   0.75  0.00 "")
 (setq p1 (list 446.75 1478.56) p2 (list 0.00 0.00))
 (command "TEXT" "J" "ML" p1   0.75  0.00 "5500")
 (command "LAYER" "S" "CGBLITHTXT" "")
 (setq p1 (list 450.50 1478.56) p2 (list 0.00 0.00))
 (command "TEXT" "J" "ML" p1   0.75  0.00 "COAL W/BONE LAYERS")
 (command "LAYER" "S" "CGBCMNT" "")
 (setq p1 (list 470.75 1478.56) p2 (list 0.00 0.00))
 (command "TEXT" "J" "ML" p1   0.75  0.00 "MOSTLY DULL")
 (command "LAYER" "S" "CGBMAIN" "")
 (setq p1 (list 428.00 1500.20) p2 (list 434.00 1500.20) p3 (list 434.00 1500.00) p4 (list 428.00 1500.00))
 (command "PLINE" p1 p2 p3 p4 "c")
 (command "HATCH" "ZIGZAG" 0.30 22.50 "L" "")
 (command "COLOR" "BYLAYER")
 (command "LAYER" "S" "CGBLITHCD" "")
 (setq p1 (list 434.00 1500.10) p2 (list 435.35 1477.69))
 (command "LINE" p1 p2 "")
 (setq p1 (list 435.50 1477.31) p2 (list 0.00 0.00))
 (command "TEXT" "J" "ML" p1   0.75  0.00 "027")
 (command "LAYER" "S" "CGBTHK" "")
 (setq p1 (list 440.00 1477.31) p2 (list 0.00 0.00))
 (command "TEXT" "J" "ML" p1   0.75  0.00 "0.20")
 (command "LAYER" "S" "CGBHZID" "")
 (setq p1 (list 444.50 1477.31) p2 (list 0.00 0.00))
 (command "TEXT" "J" "ML" p1   0.75  0.00 "")
 (setq p1 (list 446.75 1477.31) p2 (list 0.00 0.00))
 (command "TEXT" "J" "ML" p1   0.75  0.00 "5500")
 (command "LAYER" "S" "CGBLITHTXT" "")
 (setq p1 (list 450.50 1477.31) p2 (list 0.00 0.00))
 (command "TEXT" "J" "ML" p1   0.75  0.00 "COAL W/SH LAYERS")
 (command "LAYER" "S" "CGBCMNT" "")
 (setq p1 (list 470.75 1477.31) p2 (list 0.00 0.00))
 (command "TEXT" "J" "ML" p1   0.75  0.00 "DULL W/PYRT")
 (command "LAYER" "S" "CGBMAIN" "")
 (setq p1 (list 428.00 1500.00) p2 (list 434.00 1500.00) p3 (list 434.00 1499.70) p4 (list 428.00 1499.70))
 (command "PLINE" p1 p2 p3 p4 "c")
 (command "HATCH" "ZIGZAG" 0.25 0.00 "L" "")
 (command "COLOR" "BYLAYER")
 (command "LAYER" "S" "CGBLITHCD" "")
 (setq p1 (list 434.00 1499.85) p2 (list 435.35 1476.44))
 (command "LINE" p1 p2 "")
 (setq p1 (list 435.50 1476.06) p2 (list 0.00 0.00))
 (command "TEXT" "J" "ML" p1   0.75  0.00 "127")
 (command "LAYER" "S" "CGBTHK" "")
 (setq p1 (list 440.00 1476.06) p2 (list 0.00 0.00))
 (command "TEXT" "J" "ML" p1   0.75  0.00 "0.30")
 (command "LAYER" "S" "CGBHZID" "")
 (setq p1 (list 444.50 1476.06) p2 (list 0.00 0.00))
 (command "TEXT" "J" "ML" p1   0.75  0.00 "")
 (setq p1 (list 446.75 1476.06) p2 (list 0.00 0.00))
 (command "TEXT" "J" "ML" p1   0.75  0.00 "5451")
 (command "LAYER" "S" "CGBLITHTXT" "")
 (setq p1 (list 450.50 1476.06) p2 (list 0.00 0.00))
 (command "TEXT" "J" "ML" p1   0.75  0.00 "DRK GRY FIRECLAY")
 (command "LAYER" "S" "CGBCMNT" "")
 (setq p1 (list 470.75 1476.06) p2 (list 0.00 0.00))
 (command "TEXT" "J" "ML" p1   0.75  0.00 "")
 (command "LAYER" "S" "CGBMAIN" "")
 (setq p1 (list 428.00 1499.70) p2 (list 434.00 1499.70) p3 (list 434.00 1498.95) p4 (list 428.00 1498.95))
 (command "PLINE" p1 p2 p3 p4 "c")
 (command "HATCH" "ZIGZAG" 0.25 0.00 "L" "")
 (command "COLOR" "BYLAYER")
 (command "LAYER" "S" "CGBLITHCD" "")
 (setq p1 (list 434.00 1499.33) p2 (list 435.35 1475.19))
 (command "LINE" p1 p2 "")
 (setq p1 (list 435.50 1474.81) p2 (list 0.00 0.00))
 (command "TEXT" "J" "ML" p1   0.75  0.00 "127")
 (command "LAYER" "S" "CGBTHK" "")
 (setq p1 (list 440.00 1474.81) p2 (list 0.00 0.00))
 (command "TEXT" "J" "ML" p1   0.75  0.00 "0.75")
 (command "LAYER" "S" "CGBHZID" "")
 (setq p1 (list 444.50 1474.81) p2 (list 0.00 0.00))
 (command "TEXT" "J" "ML" p1   0.75  0.00 "")
 (setq p1 (list 446.75 1474.81) p2 (list 0.00 0.00))
 (command "TEXT" "J" "ML" p1   0.75  0.00 "5451")
 (command "LAYER" "S" "CGBLITHTXT" "")
 (setq p1 (list 450.50 1474.81) p2 (list 0.00 0.00))
 (command "TEXT" "J" "ML" p1   0.75  0.00 "DRK GRY FIRECLAY")
 (command "LAYER" "S" "CGBCMNT" "")
 (setq p1 (list 470.75 1474.81) p2 (list 0.00 0.00))
 (command "TEXT" "J" "ML" p1   0.75  0.00 "FRAC NEAR BAS")
 (command "LAYER" "S" "CGBMAIN" "")
 (setq p1 (list 428.00 1498.95) p2 (list 434.00 1498.95) p3 (list 434.00 1496.82) p4 (list 428.00 1496.82))
 (command "PLINE" p1 p2 p3 p4 "c")
 (command "HATCH" "ZIGZAG" 0.25 0.00 "L" "")
 (command "COLOR" "BYLAYER")
 (command "LAYER" "S" "CGBLITHCD" "")
 (setq p1 (list 434.00 1497.89) p2 (list 435.35 1473.94))
 (command "LINE" p1 p2 "")
 (setq p1 (list 435.50 1473.56) p2 (list 0.00 0.00))
 (command "TEXT" "J" "ML" p1   0.75  0.00 "327")
 (command "LAYER" "S" "CGBTHK" "")
 (setq p1 (list 440.00 1473.56) p2 (list 0.00 0.00))
 (command "TEXT" "J" "ML" p1   0.75  0.00 "2.13")
 (command "LAYER" "S" "CGBHZID" "")
 (setq p1 (list 444.50 1473.56) p2 (list 0.00 0.00))
 (command "TEXT" "J" "ML" p1   0.75  0.00 "")
 (setq p1 (list 446.75 1473.56) p2 (list 0.00 0.00))
 (command "TEXT" "J" "ML" p1   0.75  0.00 "5451")
 (command "LAYER" "S" "CGBLITHTXT" "")
 (setq p1 (list 450.50 1473.56) p2 (list 0.00 0.00))
 (command "TEXT" "J" "ML" p1   0.75  0.00 "DRK GRY SDY FIRECLAY")
 (command "LAYER" "S" "CGBCMNT" "")
 (setq p1 (list 470.75 1473.56) p2 (list 0.00 0.00))
 (command "TEXT" "J" "ML" p1   0.75  0.00 "")
 (command "LAYER" "S" "CGBMAIN" "")
 (setq p1 (list 428.00 1496.82) p2 (list 434.00 1496.82) p3 (list 434.00 1494.94) p4 (list 428.00 1494.94))
 (command "PLINE" p1 p2 p3 p4 "c")
 (command "HATCH" "ZIGZAG" 4.00 0.00 "L" "")
 (command "COLOR" "BYLAYER")
 (command "LAYER" "S" "CGBLITHCD" "")
 (setq p1 (list 434.00 1495.88) p2 (list 435.35 1472.69))
 (command "LINE" p1 p2 "")
 (setq p1 (list 435.50 1472.31) p2 (list 0.00 0.00))
 (command "TEXT" "J" "ML" p1   0.75  0.00 "124")
 (command "LAYER" "S" "CGBTHK" "")
 (setq p1 (list 440.00 1472.31) p2 (list 0.00 0.00))
 (command "TEXT" "J" "ML" p1   0.75  0.00 "1.88")
 (command "LAYER" "S" "CGBHZID" "")
 (setq p1 (list 444.50 1472.31) p2 (list 0.00 0.00))
 (command "TEXT" "J" "ML" p1   0.75  0.00 "")
 (setq p1 (list 446.75 1472.31) p2 (list 0.00 0.00))
 (command "TEXT" "J" "ML" p1   0.75  0.00 "5451")
 (command "LAYER" "S" "CGBLITHTXT" "")
 (setq p1 (list 450.50 1472.31) p2 (list 0.00 0.00))
 (command "TEXT" "J" "ML" p1   0.75  0.00 "DRK GRY SH")
 (command "LAYER" "S" "CGBCMNT" "")
 (setq p1 (list 470.75 1472.31) p2 (list 0.00 0.00))
 (command "TEXT" "J" "ML" p1   0.75  0.00 "")
 (command "LAYER" "S" "CGBMAIN" "")
 (setq p1 (list 428.00 1494.94) p2 (list 434.00 1494.94) p3 (list 434.00 1491.57) p4 (list 428.00 1491.57))
 (command "PLINE" p1 p2 p3 p4 "c")
 (command "HATCH" "ZIGZAG" 0.25 0.00 "L" "")
 (command "COLOR" "BYLAYER")
 (command "LAYER" "S" "CGBLITHCD" "")
 (setq p1 (list 434.00 1493.26) p2 (list 435.35 1471.44))
 (command "LINE" p1 p2 "")
 (setq p1 (list 435.50 1471.06) p2 (list 0.00 0.00))
 (command "TEXT" "J" "ML" p1   0.75  0.00 "127")
 (command "LAYER" "S" "CGBTHK" "")
 (setq p1 (list 440.00 1471.06) p2 (list 0.00 0.00))
 (command "TEXT" "J" "ML" p1   0.75  0.00 "3.37")
 (command "LAYER" "S" "CGBHZID" "")
 (setq p1 (list 444.50 1471.06) p2 (list 0.00 0.00))
 (command "TEXT" "J" "ML" p1   0.75  0.00 "")
 (setq p1 (list 446.75 1471.06) p2 (list 0.00 0.00))
 (command "TEXT" "J" "ML" p1   0.75  0.00 "5451")
 (command "LAYER" "S" "CGBLITHTXT" "")
 (setq p1 (list 450.50 1471.06) p2 (list 0.00 0.00))
 (command "TEXT" "J" "ML" p1   0.75  0.00 "DRK GRY FIRECLAY")
 (command "LAYER" "S" "CGBCMNT" "")
 (setq p1 (list 470.75 1471.06) p2 (list 0.00 0.00))
 (command "TEXT" "J" "ML" p1   0.75  0.00 "")
 (command "LAYER" "S" "CGBMAIN" "")
 (setq p1 (list 428.00 1491.57) p2 (list 434.00 1491.57) p3 (list 434.00 1491.42) p4 (list 428.00 1491.42))
 (command "PLINE" p1 p2 p3 p4 "c")
 (command "HATCH" "ZIGZAG" 4.00 22.50 "L" "")
 (command "COLOR" "BYLAYER")
 (command "LAYER" "S" "CGBLITHCD" "")
 (setq p1 (list 434.00 1491.50) p2 (list 435.35 1470.19))
 (command "LINE" p1 p2 "")
 (setq p1 (list 435.50 1469.81) p2 (list 0.00 0.00))
 (command "TEXT" "J" "ML" p1   0.75  0.00 "114")
 (command "LAYER" "S" "CGBTHK" "")
 (setq p1 (list 440.00 1469.81) p2 (list 0.00 0.00))
 (command "TEXT" "J" "ML" p1   0.75  0.00 "0.15")
 (command "LAYER" "S" "CGBHZID" "")
 (setq p1 (list 444.50 1469.81) p2 (list 0.00 0.00))
 (command "TEXT" "J" "ML" p1   0.75  0.00 "")
 (setq p1 (list 446.75 1469.81) p2 (list 0.00 0.00))
 (command "TEXT" "J" "ML" p1   0.75  0.00 "5451")
 (command "LAYER" "S" "CGBLITHTXT" "")
 (setq p1 (list 450.50 1469.81) p2 (list 0.00 0.00))
 (command "TEXT" "J" "ML" p1   0.75  0.00 "BLK SH")
 (command "LAYER" "S" "CGBCMNT" "")
 (setq p1 (list 470.75 1469.81) p2 (list 0.00 0.00))
 (command "TEXT" "J" "ML" p1   0.75  0.00 "")
 (command "LAYER" "S" "CGBMAIN" "")
 (setq p1 (list 427.50 1918.54) p2 (list 428.00 1918.54))
 (command "LINE" p1 p2 "")
 (setq p1 (list 427.13 1918.54) p2 (list 0.00 0.00))
 (command "TEXT" "J" "MR" p1   0.75  0.00 "0.00")
 (setq p1 (list 427.13 1917.42) p2 (list 0.00 0.00))
 (command "TEXT" "J" "MR" p1   0.75  0.00 "3237.84")
 (setq p1 (list 427.50 1908.54) p2 (list 428.00 1908.54))
 (command "LINE" p1 p2 "")
 (setq p1 (list 427.13 1908.54) p2 (list 0.00 0.00))
 (command "TEXT" "J" "MR" p1   0.75  0.00 "10.00")
 (setq p1 (list 427.13 1907.42) p2 (list 0.00 0.00))
 (command "TEXT" "J" "MR" p1   0.75  0.00 "3227.84")
 (setq p1 (list 427.50 1898.54) p2 (list 428.00 1898.54))
 (command "LINE" p1 p2 "")
 (setq p1 (list 427.13 1898.54) p2 (list 0.00 0.00))
 (command "TEXT" "J" "MR" p1   0.75  0.00 "20.00")
 (setq p1 (list 427.13 1897.42) p2 (list 0.00 0.00))
 (command "TEXT" "J" "MR" p1   0.75  0.00 "3217.84")
 (setq p1 (list 427.50 1888.54) p2 (list 428.00 1888.54))
 (command "LINE" p1 p2 "")
 (setq p1 (list 427.13 1888.54) p2 (list 0.00 0.00))
 (command "TEXT" "J" "MR" p1   0.75  0.00 "30.00")
 (setq p1 (list 427.13 1887.42) p2 (list 0.00 0.00))
 (command "TEXT" "J" "MR" p1   0.75  0.00 "3207.84")
 (setq p1 (list 427.50 1878.54) p2 (list 428.00 1878.54))
 (command "LINE" p1 p2 "")
 (setq p1 (list 427.13 1878.54) p2 (list 0.00 0.00))
 (command "TEXT" "J" "MR" p1   0.75  0.00 "40.00")
 (setq p1 (list 427.13 1877.42) p2 (list 0.00 0.00))
 (command "TEXT" "J" "MR" p1   0.75  0.00 "3197.84")
 (setq p1 (list 427.50 1868.54) p2 (list 428.00 1868.54))
 (command "LINE" p1 p2 "")
 (setq p1 (list 427.13 1868.54) p2 (list 0.00 0.00))
 (command "TEXT" "J" "MR" p1   0.75  0.00 "50.00")
 (setq p1 (list 427.13 1867.42) p2 (list 0.00 0.00))
 (command "TEXT" "J" "MR" p1   0.75  0.00 "3187.84")
 (setq p1 (list 427.50 1858.54) p2 (list 428.00 1858.54))
 (command "LINE" p1 p2 "")
 (setq p1 (list 427.13 1858.54) p2 (list 0.00 0.00))
 (command "TEXT" "J" "MR" p1   0.75  0.00 "60.00")
 (setq p1 (list 427.13 1857.42) p2 (list 0.00 0.00))
 (command "TEXT" "J" "MR" p1   0.75  0.00 "3177.84")
 (setq p1 (list 427.50 1848.54) p2 (list 428.00 1848.54))
 (command "LINE" p1 p2 "")
 (setq p1 (list 427.13 1848.54) p2 (list 0.00 0.00))
 (command "TEXT" "J" "MR" p1   0.75  0.00 "70.00")
 (setq p1 (list 427.13 1847.42) p2 (list 0.00 0.00))
 (command "TEXT" "J" "MR" p1   0.75  0.00 "3167.84")
 (setq p1 (list 427.50 1838.54) p2 (list 428.00 1838.54))
 (command "LINE" p1 p2 "")
 (setq p1 (list 427.13 1838.54) p2 (list 0.00 0.00))
 (command "TEXT" "J" "MR" p1   0.75  0.00 "80.00")
 (setq p1 (list 427.13 1837.42) p2 (list 0.00 0.00))
 (command "TEXT" "J" "MR" p1   0.75  0.00 "3157.84")
 (setq p1 (list 427.50 1828.54) p2 (list 428.00 1828.54))
 (command "LINE" p1 p2 "")
 (setq p1 (list 427.13 1828.54) p2 (list 0.00 0.00))
 (command "TEXT" "J" "MR" p1   0.75  0.00 "90.00")
 (setq p1 (list 427.13 1827.42) p2 (list 0.00 0.00))
 (command "TEXT" "J" "MR" p1   0.75  0.00 "3147.84")
 (setq p1 (list 427.50 1818.54) p2 (list 428.00 1818.54))
 (command "LINE" p1 p2 "")
 (setq p1 (list 427.13 1818.54) p2 (list 0.00 0.00))
 (command "TEXT" "J" "MR" p1   0.75  0.00 "100.00")
 (setq p1 (list 427.13 1817.42) p2 (list 0.00 0.00))
 (command "TEXT" "J" "MR" p1   0.75  0.00 "3137.84")
 (setq p1 (list 427.50 1808.54) p2 (list 428.00 1808.54))
 (command "LINE" p1 p2 "")
 (setq p1 (list 427.13 1808.54) p2 (list 0.00 0.00))
 (command "TEXT" "J" "MR" p1   0.75  0.00 "110.00")
 (setq p1 (list 427.13 1807.42) p2 (list 0.00 0.00))
 (command "TEXT" "J" "MR" p1   0.75  0.00 "3127.84")
 (setq p1 (list 427.50 1798.54) p2 (list 428.00 1798.54))
 (command "LINE" p1 p2 "")
 (setq p1 (list 427.13 1798.54) p2 (list 0.00 0.00))
 (command "TEXT" "J" "MR" p1   0.75  0.00 "120.00")
 (setq p1 (list 427.13 1797.42) p2 (list 0.00 0.00))
 (command "TEXT" "J" "MR" p1   0.75  0.00 "3117.84")
 (setq p1 (list 427.50 1788.54) p2 (list 428.00 1788.54))
 (command "LINE" p1 p2 "")
 (setq p1 (list 427.13 1788.54) p2 (list 0.00 0.00))
 (command "TEXT" "J" "MR" p1   0.75  0.00 "130.00")
 (setq p1 (list 427.13 1787.42) p2 (list 0.00 0.00))
 (command "TEXT" "J" "MR" p1   0.75  0.00 "3107.84")
 (setq p1 (list 427.50 1778.54) p2 (list 428.00 1778.54))
 (command "LINE" p1 p2 "")
 (setq p1 (list 427.13 1778.54) p2 (list 0.00 0.00))
 (command "TEXT" "J" "MR" p1   0.75  0.00 "140.00")
 (setq p1 (list 427.13 1777.42) p2 (list 0.00 0.00))
 (command "TEXT" "J" "MR" p1   0.75  0.00 "3097.84")
 (setq p1 (list 427.50 1768.54) p2 (list 428.00 1768.54))
 (command "LINE" p1 p2 "")
 (setq p1 (list 427.13 1768.54) p2 (list 0.00 0.00))
 (command "TEXT" "J" "MR" p1   0.75  0.00 "150.00")
 (setq p1 (list 427.13 1767.42) p2 (list 0.00 0.00))
 (command "TEXT" "J" "MR" p1   0.75  0.00 "3087.84")
 (setq p1 (list 427.50 1758.54) p2 (list 428.00 1758.54))
 (command "LINE" p1 p2 "")
 (setq p1 (list 427.13 1758.54) p2 (list 0.00 0.00))
 (command "TEXT" "J" "MR" p1   0.75  0.00 "160.00")
 (setq p1 (list 427.13 1757.42) p2 (list 0.00 0.00))
 (command "TEXT" "J" "MR" p1   0.75  0.00 "3077.84")
 (setq p1 (list 427.50 1748.54) p2 (list 428.00 1748.54))
 (command "LINE" p1 p2 "")
 (setq p1 (list 427.13 1748.54) p2 (list 0.00 0.00))
 (command "TEXT" "J" "MR" p1   0.75  0.00 "170.00")
 (setq p1 (list 427.13 1747.42) p2 (list 0.00 0.00))
 (command "TEXT" "J" "MR" p1   0.75  0.00 "3067.84")
 (setq p1 (list 427.50 1738.54) p2 (list 428.00 1738.54))
 (command "LINE" p1 p2 "")
 (setq p1 (list 427.13 1738.54) p2 (list 0.00 0.00))
 (command "TEXT" "J" "MR" p1   0.75  0.00 "180.00")
 (setq p1 (list 427.13 1737.42) p2 (list 0.00 0.00))
 (command "TEXT" "J" "MR" p1   0.75  0.00 "3057.84")
 (setq p1 (list 427.50 1728.54) p2 (list 428.00 1728.54))
 (command "LINE" p1 p2 "")
 (setq p1 (list 427.13 1728.54) p2 (list 0.00 0.00))
 (command "TEXT" "J" "MR" p1   0.75  0.00 "190.00")
 (setq p1 (list 427.13 1727.42) p2 (list 0.00 0.00))
 (command "TEXT" "J" "MR" p1   0.75  0.00 "3047.84")
 (setq p1 (list 427.50 1718.54) p2 (list 428.00 1718.54))
 (command "LINE" p1 p2 "")
 (setq p1 (list 427.13 1718.54) p2 (list 0.00 0.00))
 (command "TEXT" "J" "MR" p1   0.75  0.00 "200.00")
 (setq p1 (list 427.13 1717.42) p2 (list 0.00 0.00))
 (command "TEXT" "J" "MR" p1   0.75  0.00 "3037.84")
 (setq p1 (list 427.50 1708.54) p2 (list 428.00 1708.54))
 (command "LINE" p1 p2 "")
 (setq p1 (list 427.13 1708.54) p2 (list 0.00 0.00))
 (command "TEXT" "J" "MR" p1   0.75  0.00 "210.00")
 (setq p1 (list 427.13 1707.42) p2 (list 0.00 0.00))
 (command "TEXT" "J" "MR" p1   0.75  0.00 "3027.84")
 (setq p1 (list 427.50 1698.54) p2 (list 428.00 1698.54))
 (command "LINE" p1 p2 "")
 (setq p1 (list 427.13 1698.54) p2 (list 0.00 0.00))
 (command "TEXT" "J" "MR" p1   0.75  0.00 "220.00")
 (setq p1 (list 427.13 1697.42) p2 (list 0.00 0.00))
 (command "TEXT" "J" "MR" p1   0.75  0.00 "3017.84")
 (setq p1 (list 427.50 1688.54) p2 (list 428.00 1688.54))
 (command "LINE" p1 p2 "")
 (setq p1 (list 427.13 1688.54) p2 (list 0.00 0.00))
 (command "TEXT" "J" "MR" p1   0.75  0.00 "230.00")
 (setq p1 (list 427.13 1687.42) p2 (list 0.00 0.00))
 (command "TEXT" "J" "MR" p1   0.75  0.00 "3007.84")
 (setq p1 (list 427.50 1678.54) p2 (list 428.00 1678.54))
 (command "LINE" p1 p2 "")
 (setq p1 (list 427.13 1678.54) p2 (list 0.00 0.00))
 (command "TEXT" "J" "MR" p1   0.75  0.00 "240.00")
 (setq p1 (list 427.13 1677.42) p2 (list 0.00 0.00))
 (command "TEXT" "J" "MR" p1   0.75  0.00 "2997.84")
 (setq p1 (list 427.50 1668.54) p2 (list 428.00 1668.54))
 (command "LINE" p1 p2 "")
 (setq p1 (list 427.13 1668.54) p2 (list 0.00 0.00))
 (command "TEXT" "J" "MR" p1   0.75  0.00 "250.00")
 (setq p1 (list 427.13 1667.42) p2 (list 0.00 0.00))
 (command "TEXT" "J" "MR" p1   0.75  0.00 "2987.84")
 (setq p1 (list 427.50 1658.54) p2 (list 428.00 1658.54))
 (command "LINE" p1 p2 "")
 (setq p1 (list 427.13 1658.54) p2 (list 0.00 0.00))
 (command "TEXT" "J" "MR" p1   0.75  0.00 "260.00")
 (setq p1 (list 427.13 1657.42) p2 (list 0.00 0.00))
 (command "TEXT" "J" "MR" p1   0.75  0.00 "2977.84")
 (setq p1 (list 427.50 1648.54) p2 (list 428.00 1648.54))
 (command "LINE" p1 p2 "")
 (setq p1 (list 427.13 1648.54) p2 (list 0.00 0.00))
 (command "TEXT" "J" "MR" p1   0.75  0.00 "270.00")
 (setq p1 (list 427.13 1647.42) p2 (list 0.00 0.00))
 (command "TEXT" "J" "MR" p1   0.75  0.00 "2967.84")
 (setq p1 (list 427.50 1638.54) p2 (list 428.00 1638.54))
 (command "LINE" p1 p2 "")
 (setq p1 (list 427.13 1638.54) p2 (list 0.00 0.00))
 (command "TEXT" "J" "MR" p1   0.75  0.00 "280.00")
 (setq p1 (list 427.13 1637.42) p2 (list 0.00 0.00))
 (command "TEXT" "J" "MR" p1   0.75  0.00 "2957.84")
 (setq p1 (list 427.50 1628.54) p2 (list 428.00 1628.54))
 (command "LINE" p1 p2 "")
 (setq p1 (list 427.13 1628.54) p2 (list 0.00 0.00))
 (command "TEXT" "J" "MR" p1   0.75  0.00 "290.00")
 (setq p1 (list 427.13 1627.42) p2 (list 0.00 0.00))
 (command "TEXT" "J" "MR" p1   0.75  0.00 "2947.84")
 (setq p1 (list 427.50 1618.54) p2 (list 428.00 1618.54))
 (command "LINE" p1 p2 "")
 (setq p1 (list 427.13 1618.54) p2 (list 0.00 0.00))
 (command "TEXT" "J" "MR" p1   0.75  0.00 "300.00")
 (setq p1 (list 427.13 1617.42) p2 (list 0.00 0.00))
 (command "TEXT" "J" "MR" p1   0.75  0.00 "2937.84")
 (setq p1 (list 427.50 1608.54) p2 (list 428.00 1608.54))
 (command "LINE" p1 p2 "")
 (setq p1 (list 427.13 1608.54) p2 (list 0.00 0.00))
 (command "TEXT" "J" "MR" p1   0.75  0.00 "310.00")
 (setq p1 (list 427.13 1607.42) p2 (list 0.00 0.00))
 (command "TEXT" "J" "MR" p1   0.75  0.00 "2927.84")
 (setq p1 (list 427.50 1598.54) p2 (list 428.00 1598.54))
 (command "LINE" p1 p2 "")
 (setq p1 (list 427.13 1598.54) p2 (list 0.00 0.00))
 (command "TEXT" "J" "MR" p1   0.75  0.00 "320.00")
 (setq p1 (list 427.13 1597.42) p2 (list 0.00 0.00))
 (command "TEXT" "J" "MR" p1   0.75  0.00 "2917.84")
 (setq p1 (list 427.50 1588.54) p2 (list 428.00 1588.54))
 (command "LINE" p1 p2 "")
 (setq p1 (list 427.13 1588.54) p2 (list 0.00 0.00))
 (command "TEXT" "J" "MR" p1   0.75  0.00 "330.00")
 (setq p1 (list 427.13 1587.42) p2 (list 0.00 0.00))
 (command "TEXT" "J" "MR" p1   0.75  0.00 "2907.84")
 (setq p1 (list 427.50 1578.54) p2 (list 428.00 1578.54))
 (command "LINE" p1 p2 "")
 (setq p1 (list 427.13 1578.54) p2 (list 0.00 0.00))
 (command "TEXT" "J" "MR" p1   0.75  0.00 "340.00")
 (setq p1 (list 427.13 1577.42) p2 (list 0.00 0.00))
 (command "TEXT" "J" "MR" p1   0.75  0.00 "2897.84")
 (setq p1 (list 427.50 1568.54) p2 (list 428.00 1568.54))
 (command "LINE" p1 p2 "")
 (setq p1 (list 427.13 1568.54) p2 (list 0.00 0.00))
 (command "TEXT" "J" "MR" p1   0.75  0.00 "350.00")
 (setq p1 (list 427.13 1567.42) p2 (list 0.00 0.00))
 (command "TEXT" "J" "MR" p1   0.75  0.00 "2887.84")
 (setq p1 (list 427.50 1558.54) p2 (list 428.00 1558.54))
 (command "LINE" p1 p2 "")
 (setq p1 (list 427.13 1558.54) p2 (list 0.00 0.00))
 (command "TEXT" "J" "MR" p1   0.75  0.00 "360.00")
 (setq p1 (list 427.13 1557.42) p2 (list 0.00 0.00))
 (command "TEXT" "J" "MR" p1   0.75  0.00 "2877.84")
 (setq p1 (list 427.50 1548.54) p2 (list 428.00 1548.54))
 (command "LINE" p1 p2 "")
 (setq p1 (list 427.13 1548.54) p2 (list 0.00 0.00))
 (command "TEXT" "J" "MR" p1   0.75  0.00 "370.00")
 (setq p1 (list 427.13 1547.42) p2 (list 0.00 0.00))
 (command "TEXT" "J" "MR" p1   0.75  0.00 "2867.84")
 (setq p1 (list 427.50 1538.54) p2 (list 428.00 1538.54))
 (command "LINE" p1 p2 "")
 (setq p1 (list 427.13 1538.54) p2 (list 0.00 0.00))
 (command "TEXT" "J" "MR" p1   0.75  0.00 "380.00")
 (setq p1 (list 427.13 1537.42) p2 (list 0.00 0.00))
 (command "TEXT" "J" "MR" p1   0.75  0.00 "2857.84")
 (setq p1 (list 427.50 1528.54) p2 (list 428.00 1528.54))
 (command "LINE" p1 p2 "")
 (setq p1 (list 427.13 1528.54) p2 (list 0.00 0.00))
 (command "TEXT" "J" "MR" p1   0.75  0.00 "390.00")
 (setq p1 (list 427.13 1527.42) p2 (list 0.00 0.00))
 (command "TEXT" "J" "MR" p1   0.75  0.00 "2847.84")
 (setq p1 (list 427.50 1518.54) p2 (list 428.00 1518.54))
 (command "LINE" p1 p2 "")
 (setq p1 (list 427.13 1518.54) p2 (list 0.00 0.00))
 (command "TEXT" "J" "MR" p1   0.75  0.00 "400.00")
 (setq p1 (list 427.13 1517.42) p2 (list 0.00 0.00))
 (command "TEXT" "J" "MR" p1   0.75  0.00 "2837.84")
 (setq p1 (list 427.50 1508.54) p2 (list 428.00 1508.54))
 (command "LINE" p1 p2 "")
 (setq p1 (list 427.13 1508.54) p2 (list 0.00 0.00))
 (command "TEXT" "J" "MR" p1   0.75  0.00 "410.00")
 (setq p1 (list 427.13 1507.42) p2 (list 0.00 0.00))
 (command "TEXT" "J" "MR" p1   0.75  0.00 "2827.84")
 (setq p1 (list 427.50 1498.54) p2 (list 428.00 1498.54))
 (command "LINE" p1 p2 "")
 (setq p1 (list 427.13 1498.54) p2 (list 0.00 0.00))
 (command "TEXT" "J" "MR" p1   0.75  0.00 "420.00")
 (setq p1 (list 427.13 1497.42) p2 (list 0.00 0.00))
 (command "TEXT" "J" "MR" p1   0.75  0.00 "2817.84")
 (setq p1 (list 427.50 1491.42) p2 (list 428.00 1491.42))
 (command "LINE" p1 p2 "")
 (setq p1 (list 427.13 1491.42) p2 (list 0.00 0.00))
 (command "TEXT" "J" "MR" p1   0.75  0.00 "427.12")
 (setq p1 (list 427.13 1490.30) p2 (list 0.00 0.00))
 (command "TEXT" "J" "MR" p1   0.75  0.00 "2810.72")
 (command "LAYER" "S" "CGBHLHDR" "")
 (setq p1 (list 421.00 1930.04) p2 (list 421.00 1920.04) p3 (list 441.00 1920.04) p4 (list 441.00 1930.04))
 (command "LINE" p1 p2 p3 p4 "c")
 (setq p1 (list 421.50 1928.29) p2 (list 0.00 0.00))
 (command "TEXT" "J" "ML" p1   1.13  0.00 "Hole:")
 (setq p1 (list 421.50 1926.04) p2 (list 0.00 0.00))
 (command "TEXT" "J" "ML" p1   0.83  0.00 "Easting:")
 (setq p1 (list 421.50 1924.29) p2 (list 0.00 0.00))
 (command "TEXT" "J" "ML" p1   0.83  0.00 "Northing:")
 (setq p1 (list 421.50 1922.54) p2 (list 0.00 0.00))
 (command "TEXT" "J" "ML" p1   0.83  0.00 "Collar Elev:")
 (setq p1 (list 421.50 1920.79) p2 (list 0.00 0.00))
 (command "TEXT" "J" "ML" p1   0.83  0.00 "Drill Depth:")
 (setq p1 (list 440.50 1928.29) p2 (list 0.00 0.00))
 (command "TEXT" "J" "MR" p1   1.13  0.00 "XY-31")
 (setq p1 (list 440.50 1926.04) p2 (list 0.00 0.00))
 (command "TEXT" "J" "MR" p1   0.83  0.00 "4047233.13")
 (setq p1 (list 440.50 1924.29) p2 (list 0.00 0.00))
 (command "TEXT" "J" "MR" p1   0.83  0.00 "269707.88")
 (setq p1 (list 440.50 1922.54) p2 (list 0.00 0.00))
 (command "TEXT" "J" "MR" p1   0.83  0.00 "3237.84")
 (setq p1 (list 440.50 1920.79) p2 (list 0.00 0.00))
 (command "TEXT" "J" "MR" p1   0.83  0.00 "438.60")
 (setq p1 (list 431.00 1920.04) p2 (list 431.00 1918.54))
 (command "LINE" p1 p2 "")
 (command "LAYER" "S" "CGBMAIN" "")
 (setq p1 (list 535.00 1807.74) p2 (list 541.00 1807.74) p3 (list 541.00 1792.74) p4 (list 535.00 1792.74))
 (command "PLINE" p1 p2 p3 p4 "c")
 (command "LINE" p1 p3 "")
 (command "LINE" p2 p4 "")
 (command "COLOR" "BYLAYER")
 (command "LAYER" "S" "CGBLITHCD" "")
 (setq p1 (list 541.00 1800.24) p2 (list 542.35 1800.24))
 (command "LINE" p1 p2 "")
 (setq p1 (list 542.50 1799.87) p2 (list 0.00 0.00))
 (command "TEXT" "J" "ML" p1   0.75  0.00 "001")
 (command "LAYER" "S" "CGBTHK" "")
 (setq p1 (list 547.00 1799.87) p2 (list 0.00 0.00))
 (command "TEXT" "J" "ML" p1   0.75  0.00 "15.00")
 (command "LAYER" "S" "CGBHZID" "")
 (setq p1 (list 551.50 1799.87) p2 (list 0.00 0.00))
 (command "TEXT" "J" "ML" p1   0.75  0.00 "")
 (setq p1 (list 553.75 1799.87) p2 (list 0.00 0.00))
 (command "TEXT" "J" "ML" p1   0.75  0.00 "9990")
 (command "LAYER" "S" "CGBLITHTXT" "")
 (setq p1 (list 557.50 1799.87) p2 (list 0.00 0.00))
 (command "TEXT" "J" "ML" p1   0.75  0.00 "CASING")
 (command "LAYER" "S" "CGBCMNT" "")
 (setq p1 (list 577.75 1799.87) p2 (list 0.00 0.00))
 (command "TEXT" "J" "ML" p1   0.75  0.00 "")
 (command "LAYER" "S" "CGBMAIN" "")
 (setq p1 (list 535.00 1792.74) p2 (list 541.00 1792.74) p3 (list 541.00 1777.74) p4 (list 535.00 1777.74))
 (command "PLINE" p1 p2 p3 p4 "c")
 (command "HATCH" "ZIGZAG" 4.00 0.00 "L" "")
 (command "COLOR" "BYLAYER")
 (command "LAYER" "S" "CGBLITHCD" "")
 (setq p1 (list 541.00 1785.24) p2 (list 542.35 1785.24))
 (command "LINE" p1 p2 "")
 (setq p1 (list 542.50 1784.87) p2 (list 0.00 0.00))
 (command "TEXT" "J" "ML" p1   0.75  0.00 "541")
 (command "LAYER" "S" "CGBTHK" "")
 (setq p1 (list 547.00 1784.87) p2 (list 0.00 0.00))
 (command "TEXT" "J" "ML" p1   0.75  0.00 "15.00")
 (command "LAYER" "S" "CGBHZID" "")
 (setq p1 (list 551.50 1784.87) p2 (list 0.00 0.00))
 (command "TEXT" "J" "ML" p1   0.75  0.00 "")
 (setq p1 (list 553.75 1784.87) p2 (list 0.00 0.00))
 (command "TEXT" "J" "ML" p1   0.75  0.00 "9990")
 (command "LAYER" "S" "CGBLITHTXT" "")
 (setq p1 (list 557.50 1784.87) p2 (list 0.00 0.00))
 (command "TEXT" "J" "ML" p1   0.75  0.00 "GRY CROSSBED SS")
 (command "LAYER" "S" "CGBCMNT" "")
 (setq p1 (list 577.75 1784.87) p2 (list 0.00 0.00))
 (command "TEXT" "J" "ML" p1   0.75  0.00 "CASING")
 (command "LAYER" "S" "CGBMAIN" "")
 (setq p1 (list 535.00 1777.74) p2 (list 541.00 1777.74) p3 (list 541.00 1773.43) p4 (list 535.00 1773.43))
 (command "PLINE" p1 p2 p3 p4 "c")
 (command "HATCH" "ZIGZAG" 4.00 0.00 "L" "")
 (command "COLOR" "BYLAYER")
 (command "LAYER" "S" "CGBLITHCD" "")
 (setq p1 (list 541.00 1775.59) p2 (list 542.35 1775.59))
 (command "LINE" p1 p2 "")
 (setq p1 (list 542.50 1775.21) p2 (list 0.00 0.00))
 (command "TEXT" "J" "ML" p1   0.75  0.00 "541")
 (command "LAYER" "S" "CGBTHK" "")
 (setq p1 (list 547.00 1775.21) p2 (list 0.00 0.00))
 (command "TEXT" "J" "ML" p1   0.75  0.00 "4.31")
 (command "LAYER" "S" "CGBHZID" "")
 (setq p1 (list 551.50 1775.21) p2 (list 0.00 0.00))
 (command "TEXT" "J" "ML" p1   0.75  0.00 "")
 (setq p1 (list 553.75 1775.21) p2 (list 0.00 0.00))
 (command "TEXT" "J" "ML" p1   0.75  0.00 "9990")
 (command "LAYER" "S" "CGBLITHTXT" "")
 (setq p1 (list 557.50 1775.21) p2 (list 0.00 0.00))
 (command "TEXT" "J" "ML" p1   0.75  0.00 "GRY CROSSBED SS")
 (command "LAYER" "S" "CGBCMNT" "")
 (setq p1 (list 577.75 1775.21) p2 (list 0.00 0.00))
 (command "TEXT" "J" "ML" p1   0.75  0.00 "FRACS,WTHRD")
 (command "LAYER" "S" "CGBMAIN" "")
 (setq p1 (list 535.00 1773.43) p2 (list 541.00 1773.43) p3 (list 541.00 1764.84) p4 (list 535.00 1764.84))
 (command "PLINE" p1 p2 p3 p4 "c")
 (command "HATCH" "ZIGZAG" 4.00 0.00 "L" "")
 (command "COLOR" "BYLAYER")
 (command "LAYER" "S" "CGBLITHCD" "")
 (setq p1 (list 541.00 1769.14) p2 (list 542.35 1769.14))
 (command "LINE" p1 p2 "")
 (setq p1 (list 542.50 1768.76) p2 (list 0.00 0.00))
 (command "TEXT" "J" "ML" p1   0.75  0.00 "541")
 (command "LAYER" "S" "CGBTHK" "")
 (setq p1 (list 547.00 1768.76) p2 (list 0.00 0.00))
 (command "TEXT" "J" "ML" p1   0.75  0.00 "8.59")
 (command "LAYER" "S" "CGBHZID" "")
 (setq p1 (list 551.50 1768.76) p2 (list 0.00 0.00))
 (command "TEXT" "J" "ML" p1   0.75  0.00 "")
 (setq p1 (list 553.75 1768.76) p2 (list 0.00 0.00))
 (command "TEXT" "J" "ML" p1   0.75  0.00 "9990")
 (command "LAYER" "S" "CGBLITHTXT" "")
 (setq p1 (list 557.50 1768.76) p2 (list 0.00 0.00))
 (command "TEXT" "J" "ML" p1   0.75  0.00 "GRY CROSSBED SS")
 (command "LAYER" "S" "CGBCMNT" "")
 (setq p1 (list 577.75 1768.76) p2 (list 0.00 0.00))
 (command "TEXT" "J" "ML" p1   0.75  0.00 "AS ABOVE")
 (command "LAYER" "S" "CGBMAIN" "")
 (setq p1 (list 535.00 1764.84) p2 (list 541.00 1764.84) p3 (list 541.00 1762.24) p4 (list 535.00 1762.24))
 (command "PLINE" p1 p2 p3 p4 "c")
 (command "HATCH" "ZIGZAG" 0.25 0.00 "L" "")
 (command "COLOR" "BYLAYER")
 (command "LAYER" "S" "CGBLITHCD" "")
 (setq p1 (list 541.00 1763.54) p2 (list 542.35 1763.54))
 (command "LINE" p1 p2 "")
 (setq p1 (list 542.50 1763.17) p2 (list 0.00 0.00))
 (command "TEXT" "J" "ML" p1   0.75  0.00 "127")
 (command "LAYER" "S" "CGBTHK" "")
 (setq p1 (list 547.00 1763.17) p2 (list 0.00 0.00))
 (command "TEXT" "J" "ML" p1   0.75  0.00 "2.60")
 (command "LAYER" "S" "CGBHZID" "")
 (setq p1 (list 551.50 1763.17) p2 (list 0.00 0.00))
 (command "TEXT" "J" "ML" p1   0.75  0.00 "")
 (setq p1 (list 553.75 1763.17) p2 (list 0.00 0.00))
 (command "TEXT" "J" "ML" p1   0.75  0.00 "9990")
 (command "LAYER" "S" "CGBLITHTXT" "")
 (setq p1 (list 557.50 1763.17) p2 (list 0.00 0.00))
 (command "TEXT" "J" "ML" p1   0.75  0.00 "DRK GRY FIRECLAY")
 (command "LAYER" "S" "CGBCMNT" "")
 (setq p1 (list 577.75 1763.17) p2 (list 0.00 0.00))
 (command "TEXT" "J" "ML" p1   0.75  0.00 "SLC, GRY-BRWN")
 (command "LAYER" "S" "CGBMAIN" "")
 (setq p1 (list 535.00 1762.24) p2 (list 541.00 1762.24) p3 (list 541.00 1756.93) p4 (list 535.00 1756.93))
 (command "PLINE" p1 p2 p3 p4 "c")
 (command "HATCH" "ZIGZAG" 0.25 0.00 "L" "")
 (command "COLOR" "BYLAYER")
 (command "LAYER" "S" "CGBLITHCD" "")
 (setq p1 (list 541.00 1759.59) p2 (list 542.35 1759.59))
 (command "LINE" p1 p2 "")
 (setq p1 (list 542.50 1759.21) p2 (list 0.00 0.00))
 (command "TEXT" "J" "ML" p1   0.75  0.00 "127")
 (command "LAYER" "S" "CGBTHK" "")
 (setq p1 (list 547.00 1759.21) p2 (list 0.00 0.00))
 (command "TEXT" "J" "ML" p1   0.75  0.00 "5.31")
 (command "LAYER" "S" "CGBHZID" "")
 (setq p1 (list 551.50 1759.21) p2 (list 0.00 0.00))
 (command "TEXT" "J" "ML" p1   0.75  0.00 "")
 (setq p1 (list 553.75 1759.21) p2 (list 0.00 0.00))
 (command "TEXT" "J" "ML" p1   0.75  0.00 "9990")
 (command "LAYER" "S" "CGBLITHTXT" "")
 (setq p1 (list 557.50 1759.21) p2 (list 0.00 0.00))
 (command "TEXT" "J" "ML" p1   0.75  0.00 "DRK GRY FIRECLAY")
 (command "LAYER" "S" "CGBCMNT" "")
 (setq p1 (list 577.75 1759.21) p2 (list 0.00 0.00))
 (command "TEXT" "J" "ML" p1   0.75  0.00 "V SFT")
 (command "LAYER" "S" "CGBMAIN" "")
 (setq p1 (list 535.00 1756.93) p2 (list 541.00 1756.93) p3 (list 541.00 1754.24) p4 (list 535.00 1754.24))
 (command "PLINE" p1 p2 p3 p4 "c")
 (command "HATCH" "ZIGZAG" 3.00 0.00 "L" "")
 (command "COLOR" "BYLAYER")
 (command "LAYER" "S" "CGBLITHCD" "")
 (setq p1 (list 541.00 1755.59) p2 (list 542.35 1755.59))
 (command "LINE" p1 p2 "")
 (setq p1 (list 542.50 1755.21) p2 (list 0.00 0.00))
 (command "TEXT" "J" "ML" p1   0.75  0.00 "154")
 (command "LAYER" "S" "CGBTHK" "")
 (setq p1 (list 547.00 1755.21) p2 (list 0.00 0.00))
 (command "TEXT" "J" "ML" p1   0.75  0.00 "2.69")
 (command "LAYER" "S" "CGBHZID" "")
 (setq p1 (list 551.50 1755.21) p2 (list 0.00 0.00))
 (command "TEXT" "J" "ML" p1   0.75  0.00 "")
 (setq p1 (list 553.75 1755.21) p2 (list 0.00 0.00))
 (command "TEXT" "J" "ML" p1   0.75  0.00 "9990")
 (command "LAYER" "S" "CGBLITHTXT" "")
 (setq p1 (list 557.50 1755.21) p2 (list 0.00 0.00))
 (command "TEXT" "J" "ML" p1   0.75  0.00 "RED+GRN SH")
 (command "LAYER" "S" "CGBCMNT" "")
 (setq p1 (list 577.75 1755.21) p2 (list 0.00 0.00))
 (command "TEXT" "J" "ML" p1   0.75  0.00 "BRKN,SLX")
 (command "LAYER" "S" "CGBMAIN" "")
 (setq p1 (list 535.00 1754.24) p2 (list 541.00 1754.24) p3 (list 541.00 1754.18) p4 (list 535.00 1754.18))
 (command "PLINE" p1 p2 p3 p4 "c")
 (command "HATCH" "ZIGZAG" 4.00 0.00 "L" "")
 (command "COLOR" "BYLAYER")
 (command "LAYER" "S" "CGBLITHCD" "")
 (setq p1 (list 541.00 1754.21) p2 (list 542.35 1754.21))
 (command "LINE" p1 p2 "")
 (setq p1 (list 542.50 1753.84) p2 (list 0.00 0.00))
 (command "TEXT" "J" "ML" p1   0.75  0.00 "123")
 (command "LAYER" "S" "CGBTHK" "")
 (setq p1 (list 547.00 1753.84) p2 (list 0.00 0.00))
 (command "TEXT" "J" "ML" p1   0.75  0.00 "0.06")
 (command "LAYER" "S" "CGBHZID" "")
 (setq p1 (list 551.50 1753.84) p2 (list 0.00 0.00))
 (command "TEXT" "J" "ML" p1   0.75  0.00 "")
 (setq p1 (list 553.75 1753.84) p2 (list 0.00 0.00))
 (command "TEXT" "J" "ML" p1   0.75  0.00 "9990")
 (command "LAYER" "S" "CGBLITHTXT" "")
 (setq p1 (list 557.50 1753.84) p2 (list 0.00 0.00))
 (command "TEXT" "J" "ML" p1   0.75  0.00 "DRK GRY SH W/COAL STKS")
 (command "LAYER" "S" "CGBCMNT" "")
 (setq p1 (list 577.75 1753.84) p2 (list 0.00 0.00))
 (command "TEXT" "J" "ML" p1   0.75  0.00 "SLX")
 (command "LAYER" "S" "CGBMAIN" "")
 (setq p1 (list 535.00 1754.18) p2 (list 541.00 1754.18) p3 (list 541.00 1753.50) p4 (list 535.00 1753.50))
 (command "PLINE" p1 p2 p3 p4 "c")
 (command "HATCH" "ZIGZAG" 0.25 0.00 "L" "")
 (command "COLOR" "BYLAYER")
 (command "LAYER" "S" "CGBLITHCD" "")
 (setq p1 (list 541.00 1753.84) p2 (list 542.35 1752.59))
 (command "LINE" p1 p2 "")
 (setq p1 (list 542.50 1752.22) p2 (list 0.00 0.00))
 (command "TEXT" "J" "ML" p1   0.75  0.00 "127")
 (command "LAYER" "S" "CGBTHK" "")
 (setq p1 (list 547.00 1752.22) p2 (list 0.00 0.00))
 (command "TEXT" "J" "ML" p1   0.75  0.00 "0.68")
 (command "LAYER" "S" "CGBHZID" "")
 (setq p1 (list 551.50 1752.22) p2 (list 0.00 0.00))
 (command "TEXT" "J" "ML" p1   0.75  0.00 "")
 (setq p1 (list 553.75 1752.22) p2 (list 0.00 0.00))
 (command "TEXT" "J" "ML" p1   0.75  0.00 "9990")
 (command "LAYER" "S" "CGBLITHTXT" "")
 (setq p1 (list 557.50 1752.22) p2 (list 0.00 0.00))
 (command "TEXT" "J" "ML" p1   0.75  0.00 "DRK GRY FIRECLAY")
 (command "LAYER" "S" "CGBCMNT" "")
 (setq p1 (list 577.75 1752.22) p2 (list 0.00 0.00))
 (command "TEXT" "J" "ML" p1   0.75  0.00 "SFT")
 (command "LAYER" "S" "CGBMAIN" "")
 (setq p1 (list 535.00 1753.50) p2 (list 541.00 1753.50) p3 (list 541.00 1752.34) p4 (list 535.00 1752.34))
 (command "PLINE" p1 p2 p3 p4 "c")
 (command "HATCH" "ZIGZAG" 10.00 45.00 "L" "")
 (command "COLOR" "BYLAYER")
 (command "LAYER" "S" "CGBLITHCD" "")
 (setq p1 (list 541.00 1752.92) p2 (list 542.35 1751.34))
 (command "LINE" p1 p2 "")
 (setq p1 (list 542.50 1750.97) p2 (list 0.00 0.00))
 (command "TEXT" "J" "ML" p1   0.75  0.00 "094")
 (command "LAYER" "S" "CGBTHK" "")
 (setq p1 (list 547.00 1750.97) p2 (list 0.00 0.00))
 (command "TEXT" "J" "ML" p1   0.75  0.00 "1.16")
 (command "LAYER" "S" "CGBHZID" "")
 (setq p1 (list 551.50 1750.97) p2 (list 0.00 0.00))
 (command "TEXT" "J" "ML" p1   0.75  0.00 "")
 (setq p1 (list 553.75 1750.97) p2 (list 0.00 0.00))
 (command "TEXT" "J" "ML" p1   0.75  0.00 "9990")
 (command "LAYER" "S" "CGBLITHTXT" "")
 (setq p1 (list 557.50 1750.97) p2 (list 0.00 0.00))
 (command "TEXT" "J" "ML" p1   0.75  0.00 "MASS FLINT CLAY")
 (command "LAYER" "S" "CGBCMNT" "")
 (setq p1 (list 577.75 1750.97) p2 (list 0.00 0.00))
 (command "TEXT" "J" "ML" p1   0.75  0.00 "")
 (command "LAYER" "S" "CGBMAIN" "")
 (setq p1 (list 535.00 1752.34) p2 (list 541.00 1752.34) p3 (list 541.00 1752.03) p4 (list 535.00 1752.03))
 (command "PLINE" p1 p2 p3 p4 "c")
 (command "HATCH" "ZIGZAG" 4.00 0.00 "L" "")
 (command "COLOR" "BYLAYER")
 (command "LAYER" "S" "CGBLITHCD" "")
 (setq p1 (list 541.00 1752.19) p2 (list 542.35 1750.09))
 (command "LINE" p1 p2 "")
 (setq p1 (list 542.50 1749.72) p2 (list 0.00 0.00))
 (command "TEXT" "J" "ML" p1   0.75  0.00 "123")
 (command "LAYER" "S" "CGBTHK" "")
 (setq p1 (list 547.00 1749.72) p2 (list 0.00 0.00))
 (command "TEXT" "J" "ML" p1   0.75  0.00 "0.31")
 (command "LAYER" "S" "CGBHZID" "")
 (setq p1 (list 551.50 1749.72) p2 (list 0.00 0.00))
 (command "TEXT" "J" "ML" p1   0.75  0.00 "")
 (setq p1 (list 553.75 1749.72) p2 (list 0.00 0.00))
 (command "TEXT" "J" "ML" p1   0.75  0.00 "9990")
 (command "LAYER" "S" "CGBLITHTXT" "")
 (setq p1 (list 557.50 1749.72) p2 (list 0.00 0.00))
 (command "TEXT" "J" "ML" p1   0.75  0.00 "DRK GRY SH W/COAL STKS")
 (command "LAYER" "S" "CGBCMNT" "")
 (setq p1 (list 577.75 1749.72) p2 (list 0.00 0.00))
 (command "TEXT" "J" "ML" p1   0.75  0.00 "CARB")
 (command "LAYER" "S" "CGBMAIN" "")
 (setq p1 (list 535.00 1752.03) p2 (list 541.00 1752.03) p3 (list 541.00 1750.53) p4 (list 535.00 1750.53))
 (command "PLINE" p1 p2 p3 p4 "c")
 (command "HATCH" "ZIGZAG" 4.00 0.00 "L" "")
 (command "COLOR" "BYLAYER")
 (command "LAYER" "S" "CGBLITHCD" "")
 (setq p1 (list 541.00 1751.28) p2 (list 542.35 1748.84))
 (command "LINE" p1 p2 "")
 (setq p1 (list 542.50 1748.47) p2 (list 0.00 0.00))
 (command "TEXT" "J" "ML" p1   0.75  0.00 "125")
 (command "LAYER" "S" "CGBTHK" "")
 (setq p1 (list 547.00 1748.47) p2 (list 0.00 0.00))
 (command "TEXT" "J" "ML" p1   0.75  0.00 "1.50")
 (command "LAYER" "S" "CGBHZID" "")
 (setq p1 (list 551.50 1748.47) p2 (list 0.00 0.00))
 (command "TEXT" "J" "ML" p1   0.75  0.00 "")
 (setq p1 (list 553.75 1748.47) p2 (list 0.00 0.00))
 (command "TEXT" "J" "ML" p1   0.75  0.00 "9990")
 (command "LAYER" "S" "CGBLITHTXT" "")
 (setq p1 (list 557.50 1748.47) p2 (list 0.00 0.00))
 (command "TEXT" "J" "ML" p1   0.75  0.00 "DRK GRY CHRND SH")
 (command "LAYER" "S" "CGBCMNT" "")
 (setq p1 (list 577.75 1748.47) p2 (list 0.00 0.00))
 (command "TEXT" "J" "ML" p1   0.75  0.00 "SLX")
 (command "LAYER" "S" "CGBMAIN" "")
 (setq p1 (list 535.00 1750.53) p2 (list 541.00 1750.53) p3 (list 541.00 1749.74) p4 (list 535.00 1749.74))
 (command "PLINE" p1 p2 p3 p4 "c")
 (command "HATCH" "ZIGZAG" 5.00 0.00 "L" "")
 (command "COLOR" "BYLAYER")
 (command "LAYER" "S" "CGBLITHCD" "")
 (setq p1 (list 541.00 1750.14) p2 (list 542.35 1747.59))
 (command "LINE" p1 p2 "")
 (setq p1 (list 542.50 1747.22) p2 (list 0.00 0.00))
 (command "TEXT" "J" "ML" p1   0.75  0.00 "224")
 (command "LAYER" "S" "CGBTHK" "")
 (setq p1 (list 547.00 1747.22) p2 (list 0.00 0.00))
 (command "TEXT" "J" "ML" p1   0.75  0.00 "0.79")
 (command "LAYER" "S" "CGBHZID" "")
 (setq p1 (list 551.50 1747.22) p2 (list 0.00 0.00))
 (command "TEXT" "J" "ML" p1   0.75  0.00 "")
 (setq p1 (list 553.75 1747.22) p2 (list 0.00 0.00))
 (command "TEXT" "J" "ML" p1   0.75  0.00 "9990")
 (command "LAYER" "S" "CGBLITHTXT" "")
 (setq p1 (list 557.50 1747.22) p2 (list 0.00 0.00))
 (command "TEXT" "J" "ML" p1   0.75  0.00 "DRK GRY SH W/LS NODS")
 (command "LAYER" "S" "CGBCMNT" "")
 (setq p1 (list 577.75 1747.22) p2 (list 0.00 0.00))
 (command "TEXT" "J" "ML" p1   0.75  0.00 "")
 (command "LAYER" "S" "CGBMAIN" "")
 (setq p1 (list 535.00 1749.74) p2 (list 541.00 1749.74) p3 (list 541.00 1749.26) p4 (list 535.00 1749.26))
 (command "PLINE" p1 p2 p3 p4 "c")
 (command "HATCH" "ZIGZAG" 0.50 0.00 "L" "")
 (command "COLOR" "BYLAYER")
 (command "LAYER" "S" "CGBLITHCD" "")
 (setq p1 (list 541.00 1749.50) p2 (list 542.35 1746.34))
 (command "LINE" p1 p2 "")
 (setq p1 (list 542.50 1745.97) p2 (list 0.00 0.00))
 (command "TEXT" "J" "ML" p1   0.75  0.00 "804")
 (command "LAYER" "S" "CGBTHK" "")
 (setq p1 (list 547.00 1745.97) p2 (list 0.00 0.00))
 (command "TEXT" "J" "ML" p1   0.75  0.00 "0.48")
 (command "LAYER" "S" "CGBHZID" "")
 (setq p1 (list 551.50 1745.97) p2 (list 0.00 0.00))
 (command "TEXT" "J" "ML" p1   0.75  0.00 "")
 (setq p1 (list 553.75 1745.97) p2 (list 0.00 0.00))
 (command "TEXT" "J" "ML" p1   0.75  0.00 "9990")
 (command "LAYER" "S" "CGBLITHTXT" "")
 (setq p1 (list 557.50 1745.97) p2 (list 0.00 0.00))
 (command "TEXT" "J" "ML" p1   0.75  0.00 "MASS FN GRND SHLY LS")
 (command "LAYER" "S" "CGBCMNT" "")
 (setq p1 (list 577.75 1745.97) p2 (list 0.00 0.00))
 (command "TEXT" "J" "ML" p1   0.75  0.00 "")
 (command "LAYER" "S" "CGBMAIN" "")
 (setq p1 (list 535.00 1749.26) p2 (list 541.00 1749.26) p3 (list 541.00 1748.20) p4 (list 535.00 1748.20))
 (command "PLINE" p1 p2 p3 p4 "c")
 (command "HATCH" "ZIGZAG" 10.00 45.00 "L" "")
 (command "COLOR" "BYLAYER")
 (command "LAYER" "S" "CGBLITHCD" "")
 (setq p1 (list 541.00 1748.73) p2 (list 542.35 1745.09))
 (command "LINE" p1 p2 "")
 (setq p1 (list 542.50 1744.72) p2 (list 0.00 0.00))
 (command "TEXT" "J" "ML" p1   0.75  0.00 "094")
 (command "LAYER" "S" "CGBTHK" "")
 (setq p1 (list 547.00 1744.72) p2 (list 0.00 0.00))
 (command "TEXT" "J" "ML" p1   0.75  0.00 "1.06")
 (command "LAYER" "S" "CGBHZID" "")
 (setq p1 (list 551.50 1744.72) p2 (list 0.00 0.00))
 (command "TEXT" "J" "ML" p1   0.75  0.00 "")
 (setq p1 (list 553.75 1744.72) p2 (list 0.00 0.00))
 (command "TEXT" "J" "ML" p1   0.75  0.00 "9990")
 (command "LAYER" "S" "CGBLITHTXT" "")
 (setq p1 (list 557.50 1744.72) p2 (list 0.00 0.00))
 (command "TEXT" "J" "ML" p1   0.75  0.00 "MASS FLINT CLAY")
 (command "LAYER" "S" "CGBCMNT" "")
 (setq p1 (list 577.75 1744.72) p2 (list 0.00 0.00))
 (command "TEXT" "J" "ML" p1   0.75  0.00 "")
 (command "LAYER" "S" "CGBMAIN" "")
 (setq p1 (list 535.00 1748.20) p2 (list 541.00 1748.20) p3 (list 541.00 1747.81) p4 (list 535.00 1747.81))
 (command "PLINE" p1 p2 p3 p4 "c")
 (command "HATCH" "ZIGZAG" 0.50 0.00 "L" "")
 (command "COLOR" "BYLAYER")
 (command "LAYER" "S" "CGBLITHCD" "")
 (setq p1 (list 541.00 1748.01) p2 (list 542.35 1743.84))
 (command "LINE" p1 p2 "")
 (setq p1 (list 542.50 1743.47) p2 (list 0.00 0.00))
 (command "TEXT" "J" "ML" p1   0.75  0.00 "804")
 (command "LAYER" "S" "CGBTHK" "")
 (setq p1 (list 547.00 1743.47) p2 (list 0.00 0.00))
 (command "TEXT" "J" "ML" p1   0.75  0.00 "0.39")
 (command "LAYER" "S" "CGBHZID" "")
 (setq p1 (list 551.50 1743.47) p2 (list 0.00 0.00))
 (command "TEXT" "J" "ML" p1   0.75  0.00 "")
 (setq p1 (list 553.75 1743.47) p2 (list 0.00 0.00))
 (command "TEXT" "J" "ML" p1   0.75  0.00 "9990")
 (command "LAYER" "S" "CGBLITHTXT" "")
 (setq p1 (list 557.50 1743.47) p2 (list 0.00 0.00))
 (command "TEXT" "J" "ML" p1   0.75  0.00 "MASS FN GRND SHLY LS")
 (command "LAYER" "S" "CGBCMNT" "")
 (setq p1 (list 577.75 1743.47) p2 (list 0.00 0.00))
 (command "TEXT" "J" "ML" p1   0.75  0.00 "")
 (command "LAYER" "S" "CGBMAIN" "")
 (setq p1 (list 535.00 1747.81) p2 (list 541.00 1747.81) p3 (list 541.00 1747.29) p4 (list 535.00 1747.29))
 (command "PLINE" p1 p2 p3 p4 "c")
 (command "HATCH" "ZIGZAG" 10.00 45.00 "L" "")
 (command "COLOR" "BYLAYER")
 (command "LAYER" "S" "CGBLITHCD" "")
 (setq p1 (list 541.00 1747.55) p2 (list 542.35 1742.59))
 (command "LINE" p1 p2 "")
 (setq p1 (list 542.50 1742.22) p2 (list 0.00 0.00))
 (command "TEXT" "J" "ML" p1   0.75  0.00 "094")
 (command "LAYER" "S" "CGBTHK" "")
 (setq p1 (list 547.00 1742.22) p2 (list 0.00 0.00))
 (command "TEXT" "J" "ML" p1   0.75  0.00 "0.52")
 (command "LAYER" "S" "CGBHZID" "")
 (setq p1 (list 551.50 1742.22) p2 (list 0.00 0.00))
 (command "TEXT" "J" "ML" p1   0.75  0.00 "")
 (setq p1 (list 553.75 1742.22) p2 (list 0.00 0.00))
 (command "TEXT" "J" "ML" p1   0.75  0.00 "9990")
 (command "LAYER" "S" "CGBLITHTXT" "")
 (setq p1 (list 557.50 1742.22) p2 (list 0.00 0.00))
 (command "TEXT" "J" "ML" p1   0.75  0.00 "MASS FLINT CLAY")
 (command "LAYER" "S" "CGBCMNT" "")
 (setq p1 (list 577.75 1742.22) p2 (list 0.00 0.00))
 (command "TEXT" "J" "ML" p1   0.75  0.00 "")
 (command "LAYER" "S" "CGBMAIN" "")
 (setq p1 (list 535.00 1747.29) p2 (list 541.00 1747.29) p3 (list 541.00 1747.20) p4 (list 535.00 1747.20))
 (command "PLINE" p1 p2 p3 p4 "c")
 (command "HATCH" "ZIGZAG" 4.00 0.00 "L" "")
 (command "COLOR" "BYLAYER")
 (command "LAYER" "S" "CGBLITHCD" "")
 (setq p1 (list 541.00 1747.25) p2 (list 542.35 1741.34))
 (command "LINE" p1 p2 "")
 (setq p1 (list 542.50 1740.97) p2 (list 0.00 0.00))
 (command "TEXT" "J" "ML" p1   0.75  0.00 "123")
 (command "LAYER" "S" "CGBTHK" "")
 (setq p1 (list 547.00 1740.97) p2 (list 0.00 0.00))
 (command "TEXT" "J" "ML" p1   0.75  0.00 "0.09")
 (command "LAYER" "S" "CGBHZID" "")
 (setq p1 (list 551.50 1740.97) p2 (list 0.00 0.00))
 (command "TEXT" "J" "ML" p1   0.75  0.00 "")
 (setq p1 (list 553.75 1740.97) p2 (list 0.00 0.00))
 (command "TEXT" "J" "ML" p1   0.75  0.00 "9990")
 (command "LAYER" "S" "CGBLITHTXT" "")
 (setq p1 (list 557.50 1740.97) p2 (list 0.00 0.00))
 (command "TEXT" "J" "ML" p1   0.75  0.00 "DRK GRY SH W/COAL STKS")
 (command "LAYER" "S" "CGBCMNT" "")
 (setq p1 (list 577.75 1740.97) p2 (list 0.00 0.00))
 (command "TEXT" "J" "ML" p1   0.75  0.00 "")
 (command "LAYER" "S" "CGBMAIN" "")
 (setq p1 (list 535.00 1747.20) p2 (list 541.00 1747.20) p3 (list 541.00 1746.74) p4 (list 535.00 1746.74))
 (command "PLINE" p1 p2 p3 p4 "c")
 (command "HATCH" "ZIGZAG" 5.00 0.00 "L" "")
 (command "COLOR" "BYLAYER")
 (command "LAYER" "S" "CGBLITHCD" "")
 (setq p1 (list 541.00 1746.97) p2 (list 542.35 1740.09))
 (command "LINE" p1 p2 "")
 (setq p1 (list 542.50 1739.72) p2 (list 0.00 0.00))
 (command "TEXT" "J" "ML" p1   0.75  0.00 "224")
 (command "LAYER" "S" "CGBTHK" "")
 (setq p1 (list 547.00 1739.72) p2 (list 0.00 0.00))
 (command "TEXT" "J" "ML" p1   0.75  0.00 "0.46")
 (command "LAYER" "S" "CGBHZID" "")
 (setq p1 (list 551.50 1739.72) p2 (list 0.00 0.00))
 (command "TEXT" "J" "ML" p1   0.75  0.00 "")
 (setq p1 (list 553.75 1739.72) p2 (list 0.00 0.00))
 (command "TEXT" "J" "ML" p1   0.75  0.00 "9990")
 (command "LAYER" "S" "CGBLITHTXT" "")
 (setq p1 (list 557.50 1739.72) p2 (list 0.00 0.00))
 (command "TEXT" "J" "ML" p1   0.75  0.00 "DRK GRY SH W/LS NODS")
 (command "LAYER" "S" "CGBCMNT" "")
 (setq p1 (list 577.75 1739.72) p2 (list 0.00 0.00))
 (command "TEXT" "J" "ML" p1   0.75  0.00 "")
 (command "LAYER" "S" "CGBMAIN" "")
 (setq p1 (list 535.00 1746.74) p2 (list 541.00 1746.74) p3 (list 541.00 1739.88) p4 (list 535.00 1739.88))
 (command "PLINE" p1 p2 p3 p4 "c")
 (command "HATCH" "ZIGZAG" 4.00 0.00 "L" "")
 (command "COLOR" "BYLAYER")
 (command "LAYER" "S" "CGBLITHCD" "")
 (setq p1 (list 541.00 1743.31) p2 (list 542.35 1738.84))
 (command "LINE" p1 p2 "")
 (setq p1 (list 542.50 1738.47) p2 (list 0.00 0.00))
 (command "TEXT" "J" "ML" p1   0.75  0.00 "424")
 (command "LAYER" "S" "CGBTHK" "")
 (setq p1 (list 547.00 1738.47) p2 (list 0.00 0.00))
 (command "TEXT" "J" "ML" p1   0.75  0.00 "6.86")
 (command "LAYER" "S" "CGBHZID" "")
 (setq p1 (list 551.50 1738.47) p2 (list 0.00 0.00))
 (command "TEXT" "J" "ML" p1   0.75  0.00 "")
 (setq p1 (list 553.75 1738.47) p2 (list 0.00 0.00))
 (command "TEXT" "J" "ML" p1   0.75  0.00 "9990")
 (command "LAYER" "S" "CGBLITHTXT" "")
 (setq p1 (list 557.50 1738.47) p2 (list 0.00 0.00))
 (command "TEXT" "J" "ML" p1   0.75  0.00 "DRK GRY SDY SH W/LS NODS")
 (command "LAYER" "S" "CGBCMNT" "")
 (setq p1 (list 577.75 1738.47) p2 (list 0.00 0.00))
 (command "TEXT" "J" "ML" p1   0.75  0.00 "CALC VEINS")
 (command "LAYER" "S" "CGBMAIN" "")
 (setq p1 (list 535.00 1739.88) p2 (list 541.00 1739.88) p3 (list 541.00 1739.52) p4 (list 535.00 1739.52))
 (command "PLINE" p1 p2 p3 p4 "c")
 (command "HATCH" "ZIGZAG" 5.00 0.00 "L" "")
 (command "COLOR" "BYLAYER")
 (command "LAYER" "S" "CGBLITHCD" "")
 (setq p1 (list 541.00 1739.70) p2 (list 542.35 1737.59))
 (command "LINE" p1 p2 "")
 (setq p1 (list 542.50 1737.22) p2 (list 0.00 0.00))
 (command "TEXT" "J" "ML" p1   0.75  0.00 "074")
 (command "LAYER" "S" "CGBTHK" "")
 (setq p1 (list 547.00 1737.22) p2 (list 0.00 0.00))
 (command "TEXT" "J" "ML" p1   0.75  0.00 "0.36")
 (command "LAYER" "S" "CGBHZID" "")
 (setq p1 (list 551.50 1737.22) p2 (list 0.00 0.00))
 (command "TEXT" "J" "ML" p1   0.75  0.00 "")
 (setq p1 (list 553.75 1737.22) p2 (list 0.00 0.00))
 (command "TEXT" "J" "ML" p1   0.75  0.00 "9990")
 (command "LAYER" "S" "CGBLITHTXT" "")
 (setq p1 (list 557.50 1737.22) p2 (list 0.00 0.00))
 (command "TEXT" "J" "ML" p1   0.75  0.00 "MASS IRNSTN")
 (command "LAYER" "S" "CGBCMNT" "")
 (setq p1 (list 577.75 1737.22) p2 (list 0.00 0.00))
 (command "TEXT" "J" "ML" p1   0.75  0.00 "SLC")
 (command "LAYER" "S" "CGBMAIN" "")
 (setq p1 (list 535.00 1739.52) p2 (list 541.00 1739.52) p3 (list 541.00 1738.22) p4 (list 535.00 1738.22))
 (command "PLINE" p1 p2 p3 p4 "c")
 (command "HATCH" "ZIGZAG" 4.00 0.00 "L" "")
 (command "COLOR" "BYLAYER")
 (command "LAYER" "S" "CGBLITHCD" "")
 (setq p1 (list 541.00 1738.87) p2 (list 542.35 1736.34))
 (command "LINE" p1 p2 "")
 (setq p1 (list 542.50 1735.97) p2 (list 0.00 0.00))
 (command "TEXT" "J" "ML" p1   0.75  0.00 "124")
 (command "LAYER" "S" "CGBTHK" "")
 (setq p1 (list 547.00 1735.97) p2 (list 0.00 0.00))
 (command "TEXT" "J" "ML" p1   0.75  0.00 "1.30")
 (command "LAYER" "S" "CGBHZID" "")
 (setq p1 (list 551.50 1735.97) p2 (list 0.00 0.00))
 (command "TEXT" "J" "ML" p1   0.75  0.00 "")
 (setq p1 (list 553.75 1735.97) p2 (list 0.00 0.00))
 (command "TEXT" "J" "ML" p1   0.75  0.00 "9990")
 (command "LAYER" "S" "CGBLITHTXT" "")
 (setq p1 (list 557.50 1735.97) p2 (list 0.00 0.00))
 (command "TEXT" "J" "ML" p1   0.75  0.00 "DRK GRY SH")
 (command "LAYER" "S" "CGBCMNT" "")
 (setq p1 (list 577.75 1735.97) p2 (list 0.00 0.00))
 (command "TEXT" "J" "ML" p1   0.75  0.00 "")
 (command "LAYER" "S" "CGBMAIN" "")
 (setq p1 (list 535.00 1738.22) p2 (list 541.00 1738.22) p3 (list 541.00 1737.52) p4 (list 535.00 1737.52))
 (command "PLINE" p1 p2 p3 p4 "c")
 (command "HATCH" "ZIGZAG" 2.50 90.00 "L" "")
 (command "COLOR" "BYLAYER")
 (command "LAYER" "S" "CGBLITHCD" "")
 (setq p1 (list 541.00 1737.87) p2 (list 542.35 1735.09))
 (command "LINE" p1 p2 "")
 (setq p1 (list 542.50 1734.72) p2 (list 0.00 0.00))
 (command "TEXT" "J" "ML" p1   0.75  0.00 "324")
 (command "LAYER" "S" "CGBTHK" "")
 (setq p1 (list 547.00 1734.72) p2 (list 0.00 0.00))
 (command "TEXT" "J" "ML" p1   0.75  0.00 "0.70")
 (command "LAYER" "S" "CGBHZID" "")
 (setq p1 (list 551.50 1734.72) p2 (list 0.00 0.00))
 (command "TEXT" "J" "ML" p1   0.75  0.00 "")
 (setq p1 (list 553.75 1734.72) p2 (list 0.00 0.00))
 (command "TEXT" "J" "ML" p1   0.75  0.00 "9990")
 (command "LAYER" "S" "CGBLITHTXT" "")
 (setq p1 (list 557.50 1734.72) p2 (list 0.00 0.00))
 (command "TEXT" "J" "ML" p1   0.75  0.00 "DRK GRY MASS SDY SH")
 (command "LAYER" "S" "CGBCMNT" "")
 (setq p1 (list 577.75 1734.72) p2 (list 0.00 0.00))
 (command "TEXT" "J" "ML" p1   0.75  0.00 "CRSN DWN")
 (command "LAYER" "S" "CGBMAIN" "")
 (setq p1 (list 535.00 1737.52) p2 (list 541.00 1737.52) p3 (list 541.00 1737.34) p4 (list 535.00 1737.34))
 (command "PLINE" p1 p2 p3 p4 "c")
 (command "HATCH" "ZIGZAG" 4.00 0.00 "L" "")
 (command "COLOR" "BYLAYER")
 (command "LAYER" "S" "CGBLITHCD" "")
 (setq p1 (list 541.00 1737.43) p2 (list 542.35 1733.84))
 (command "LINE" p1 p2 "")
 (setq p1 (list 542.50 1733.47) p2 (list 0.00 0.00))
 (command "TEXT" "J" "ML" p1   0.75  0.00 "543")
 (command "LAYER" "S" "CGBTHK" "")
 (setq p1 (list 547.00 1733.47) p2 (list 0.00 0.00))
 (command "TEXT" "J" "ML" p1   0.75  0.00 "0.18")
 (command "LAYER" "S" "CGBHZID" "")
 (setq p1 (list 551.50 1733.47) p2 (list 0.00 0.00))
 (command "TEXT" "J" "ML" p1   0.75  0.00 "")
 (setq p1 (list 553.75 1733.47) p2 (list 0.00 0.00))
 (command "TEXT" "J" "ML" p1   0.75  0.00 "9990")
 (command "LAYER" "S" "CGBLITHTXT" "")
 (setq p1 (list 557.50 1733.47) p2 (list 0.00 0.00))
 (command "TEXT" "J" "ML" p1   0.75  0.00 "GRY SS W/SH STKS")
 (command "LAYER" "S" "CGBCMNT" "")
 (setq p1 (list 577.75 1733.47) p2 (list 0.00 0.00))
 (command "TEXT" "J" "ML" p1   0.75  0.00 "")
 (command "LAYER" "S" "CGBMAIN" "")
 (setq p1 (list 535.00 1737.34) p2 (list 541.00 1737.34) p3 (list 541.00 1734.79) p4 (list 535.00 1734.79))
 (command "PLINE" p1 p2 p3 p4 "c")
 (command "HATCH" "ZIGZAG" 5.00 0.00 "L" "")
 (command "COLOR" "BYLAYER")
 (command "LAYER" "S" "CGBLITHCD" "")
 (setq p1 (list 541.00 1736.07) p2 (list 542.35 1732.59))
 (command "LINE" p1 p2 "")
 (setq p1 (list 542.50 1732.22) p2 (list 0.00 0.00))
 (command "TEXT" "J" "ML" p1   0.75  0.00 "224")
 (command "LAYER" "S" "CGBTHK" "")
 (setq p1 (list 547.00 1732.22) p2 (list 0.00 0.00))
 (command "TEXT" "J" "ML" p1   0.75  0.00 "2.55")
 (command "LAYER" "S" "CGBHZID" "")
 (setq p1 (list 551.50 1732.22) p2 (list 0.00 0.00))
 (command "TEXT" "J" "ML" p1   0.75  0.00 "")
 (setq p1 (list 553.75 1732.22) p2 (list 0.00 0.00))
 (command "TEXT" "J" "ML" p1   0.75  0.00 "9990")
 (command "LAYER" "S" "CGBLITHTXT" "")
 (setq p1 (list 557.50 1732.22) p2 (list 0.00 0.00))
 (command "TEXT" "J" "ML" p1   0.75  0.00 "DRK GRY SH W/LS NODS")
 (command "LAYER" "S" "CGBCMNT" "")
 (setq p1 (list 577.75 1732.22) p2 (list 0.00 0.00))
 (command "TEXT" "J" "ML" p1   0.75  0.00 "IRST, SLC")
 (command "LAYER" "S" "CGBMAIN" "")
 (setq p1 (list 535.00 1734.79) p2 (list 541.00 1734.79) p3 (list 541.00 1733.93) p4 (list 535.00 1733.93))
 (command "PLINE" p1 p2 p3 p4 "c")
 (command "HATCH" "ZIGZAG" 4.00 22.50 "L" "")
 (command "COLOR" "BYLAYER")
 (command "LAYER" "S" "CGBLITHCD" "")
 (setq p1 (list 541.00 1734.36) p2 (list 542.35 1731.34))
 (command "LINE" p1 p2 "")
 (setq p1 (list 542.50 1730.97) p2 (list 0.00 0.00))
 (command "TEXT" "J" "ML" p1   0.75  0.00 "114")
 (command "LAYER" "S" "CGBTHK" "")
 (setq p1 (list 547.00 1730.97) p2 (list 0.00 0.00))
 (command "TEXT" "J" "ML" p1   0.75  0.00 "0.86")
 (command "LAYER" "S" "CGBHZID" "")
 (setq p1 (list 551.50 1730.97) p2 (list 0.00 0.00))
 (command "TEXT" "J" "ML" p1   0.75  0.00 "")
 (setq p1 (list 553.75 1730.97) p2 (list 0.00 0.00))
 (command "TEXT" "J" "ML" p1   0.75  0.00 "9990")
 (command "LAYER" "S" "CGBLITHTXT" "")
 (setq p1 (list 557.50 1730.97) p2 (list 0.00 0.00))
 (command "TEXT" "J" "ML" p1   0.75  0.00 "BLK SH")
 (command "LAYER" "S" "CGBCMNT" "")
 (setq p1 (list 577.75 1730.97) p2 (list 0.00 0.00))
 (command "TEXT" "J" "ML" p1   0.75  0.00 "GB")
 (command "LAYER" "S" "CGBMAIN" "")
 (setq p1 (list 535.00 1733.93) p2 (list 541.00 1733.93) p3 (list 541.00 1732.57) p4 (list 535.00 1732.57))
 (command "PLINE" p1 p2 p3 p4 "c")
 (command "HATCH" "ZIGZAG" 4.00 0.00 "L" "")
 (command "COLOR" "BYLAYER")
 (command "LAYER" "S" "CGBLITHCD" "")
 (setq p1 (list 541.00 1733.25) p2 (list 542.35 1730.09))
 (command "LINE" p1 p2 "")
 (setq p1 (list 542.50 1729.72) p2 (list 0.00 0.00))
 (command "TEXT" "J" "ML" p1   0.75  0.00 "124")
 (command "LAYER" "S" "CGBTHK" "")
 (setq p1 (list 547.00 1729.72) p2 (list 0.00 0.00))
 (command "TEXT" "J" "ML" p1   0.75  0.00 "1.36")
 (command "LAYER" "S" "CGBHZID" "")
 (setq p1 (list 551.50 1729.72) p2 (list 0.00 0.00))
 (command "TEXT" "J" "ML" p1   0.75  0.00 "")
 (setq p1 (list 553.75 1729.72) p2 (list 0.00 0.00))
 (command "TEXT" "J" "ML" p1   0.75  0.00 "9990")
 (command "LAYER" "S" "CGBLITHTXT" "")
 (setq p1 (list 557.50 1729.72) p2 (list 0.00 0.00))
 (command "TEXT" "J" "ML" p1   0.75  0.00 "DRK GRY SH")
 (command "LAYER" "S" "CGBCMNT" "")
 (setq p1 (list 577.75 1729.72) p2 (list 0.00 0.00))
 (command "TEXT" "J" "ML" p1   0.75  0.00 "")
 (command "LAYER" "S" "CGBMAIN" "")
 (setq p1 (list 535.00 1732.57) p2 (list 541.00 1732.57) p3 (list 541.00 1731.74) p4 (list 535.00 1731.74))
 (command "PLINE" p1 p2 p3 p4 "c")
 (command "HATCH" "ZIGZAG" 5.00 0.00 "L" "")
 (command "COLOR" "BYLAYER")
 (command "LAYER" "S" "CGBLITHCD" "")
 (setq p1 (list 541.00 1732.16) p2 (list 542.35 1728.84))
 (command "LINE" p1 p2 "")
 (setq p1 (list 542.50 1728.47) p2 (list 0.00 0.00))
 (command "TEXT" "J" "ML" p1   0.75  0.00 "224")
 (command "LAYER" "S" "CGBTHK" "")
 (setq p1 (list 547.00 1728.47) p2 (list 0.00 0.00))
 (command "TEXT" "J" "ML" p1   0.75  0.00 "0.83")
 (command "LAYER" "S" "CGBHZID" "")
 (setq p1 (list 551.50 1728.47) p2 (list 0.00 0.00))
 (command "TEXT" "J" "ML" p1   0.75  0.00 "")
 (setq p1 (list 553.75 1728.47) p2 (list 0.00 0.00))
 (command "TEXT" "J" "ML" p1   0.75  0.00 "9990")
 (command "LAYER" "S" "CGBLITHTXT" "")
 (setq p1 (list 557.50 1728.47) p2 (list 0.00 0.00))
 (command "TEXT" "J" "ML" p1   0.75  0.00 "DRK GRY SH W/LS NODS")
 (command "LAYER" "S" "CGBCMNT" "")
 (setq p1 (list 577.75 1728.47) p2 (list 0.00 0.00))
 (command "TEXT" "J" "ML" p1   0.75  0.00 "")
 (command "LAYER" "S" "CGBMAIN" "")
 (setq p1 (list 535.00 1731.74) p2 (list 541.00 1731.74) p3 (list 541.00 1731.52) p4 (list 535.00 1731.52))
 (command "PLINE" p1 p2 p3 p4 "c")
 (command "HATCH" "ZIGZAG" 5.00 0.00 "L" "")
 (command "COLOR" "BYLAYER")
 (command "LAYER" "S" "CGBLITHCD" "")
 (setq p1 (list 541.00 1731.63) p2 (list 542.35 1727.59))
 (command "LINE" p1 p2 "")
 (setq p1 (list 542.50 1727.22) p2 (list 0.00 0.00))
 (command "TEXT" "J" "ML" p1   0.75  0.00 "224")
 (command "LAYER" "S" "CGBTHK" "")
 (setq p1 (list 547.00 1727.22) p2 (list 0.00 0.00))
 (command "TEXT" "J" "ML" p1   0.75  0.00 "0.22")
 (command "LAYER" "S" "CGBHZID" "")
 (setq p1 (list 551.50 1727.22) p2 (list 0.00 0.00))
 (command "TEXT" "J" "ML" p1   0.75  0.00 "")
 (setq p1 (list 553.75 1727.22) p2 (list 0.00 0.00))
 (command "TEXT" "J" "ML" p1   0.75  0.00 "9990")
 (command "LAYER" "S" "CGBLITHTXT" "")
 (setq p1 (list 557.50 1727.22) p2 (list 0.00 0.00))
 (command "TEXT" "J" "ML" p1   0.75  0.00 "DRK GRY SH W/LS NODS")
 (command "LAYER" "S" "CGBCMNT" "")
 (setq p1 (list 577.75 1727.22) p2 (list 0.00 0.00))
 (command "TEXT" "J" "ML" p1   0.75  0.00 "")
 (command "LAYER" "S" "CGBMAIN" "")
 (setq p1 (list 535.00 1731.52) p2 (list 541.00 1731.52) p3 (list 541.00 1725.63) p4 (list 535.00 1725.63))
 (command "PLINE" p1 p2 p3 p4 "c")
 (command "HATCH" "ZIGZAG" 0.50 0.00 "L" "")
 (command "COLOR" "BYLAYER")
 (command "LAYER" "S" "CGBLITHCD" "")
 (setq p1 (list 541.00 1728.58) p2 (list 542.35 1726.34))
 (command "LINE" p1 p2 "")
 (setq p1 (list 542.50 1725.97) p2 (list 0.00 0.00))
 (command "TEXT" "J" "ML" p1   0.75  0.00 "323")
 (command "LAYER" "S" "CGBTHK" "")
 (setq p1 (list 547.00 1725.97) p2 (list 0.00 0.00))
 (command "TEXT" "J" "ML" p1   0.75  0.00 "5.89")
 (command "LAYER" "S" "CGBHZID" "")
 (setq p1 (list 551.50 1725.97) p2 (list 0.00 0.00))
 (command "TEXT" "J" "ML" p1   0.75  0.00 "")
 (setq p1 (list 553.75 1725.97) p2 (list 0.00 0.00))
 (command "TEXT" "J" "ML" p1   0.75  0.00 "9990")
 (command "LAYER" "S" "CGBLITHTXT" "")
 (setq p1 (list 557.50 1725.97) p2 (list 0.00 0.00))
 (command "TEXT" "J" "ML" p1   0.75  0.00 "DRK GRY SH W/SS STKS")
 (command "LAYER" "S" "CGBCMNT" "")
 (setq p1 (list 577.75 1725.97) p2 (list 0.00 0.00))
 (command "TEXT" "J" "ML" p1   0.75  0.00 "")
 (command "LAYER" "S" "CGBMAIN" "")
 (setq p1 (list 535.00 1725.63) p2 (list 541.00 1725.63) p3 (list 541.00 1725.38) p4 (list 535.00 1725.38))
 (command "PLINE" p1 p2 p3 p4 "c")
 (command "HATCH" "ZIGZAG" 4.00 0.00 "L" "")
 (command "COLOR" "BYLAYER")
 (command "LAYER" "S" "CGBLITHCD" "")
 (setq p1 (list 541.00 1725.51) p2 (list 542.35 1725.09))
 (command "LINE" p1 p2 "")
 (setq p1 (list 542.50 1724.72) p2 (list 0.00 0.00))
 (command "TEXT" "J" "ML" p1   0.75  0.00 "543")
 (command "LAYER" "S" "CGBTHK" "")
 (setq p1 (list 547.00 1724.72) p2 (list 0.00 0.00))
 (command "TEXT" "J" "ML" p1   0.75  0.00 "0.25")
 (command "LAYER" "S" "CGBHZID" "")
 (setq p1 (list 551.50 1724.72) p2 (list 0.00 0.00))
 (command "TEXT" "J" "ML" p1   0.75  0.00 "")
 (setq p1 (list 553.75 1724.72) p2 (list 0.00 0.00))
 (command "TEXT" "J" "ML" p1   0.75  0.00 "9990")
 (command "LAYER" "S" "CGBLITHTXT" "")
 (setq p1 (list 557.50 1724.72) p2 (list 0.00 0.00))
 (command "TEXT" "J" "ML" p1   0.75  0.00 "GRY SS W/SH STKS")
 (command "LAYER" "S" "CGBCMNT" "")
 (setq p1 (list 577.75 1724.72) p2 (list 0.00 0.00))
 (command "TEXT" "J" "ML" p1   0.75  0.00 "GB")
 (command "LAYER" "S" "CGBMAIN" "")
 (setq p1 (list 535.00 1725.38) p2 (list 541.00 1725.38) p3 (list 541.00 1724.93) p4 (list 535.00 1724.93))
 (command "PLINE" p1 p2 p3 p4 "c")
 (command "HATCH" "ZIGZAG" 2.00 45.00 "L" "")
 (command "COLOR" "BYLAYER")
 (command "LAYER" "S" "CGBLITHCD" "")
 (setq p1 (list 541.00 1725.16) p2 (list 542.35 1723.84))
 (command "LINE" p1 p2 "")
 (setq p1 (list 542.50 1723.47) p2 (list 0.00 0.00))
 (command "TEXT" "J" "ML" p1   0.75  0.00 "313")
 (command "LAYER" "S" "CGBTHK" "")
 (setq p1 (list 547.00 1723.47) p2 (list 0.00 0.00))
 (command "TEXT" "J" "ML" p1   0.75  0.00 "0.45")
 (command "LAYER" "S" "CGBHZID" "")
 (setq p1 (list 551.50 1723.47) p2 (list 0.00 0.00))
 (command "TEXT" "J" "ML" p1   0.75  0.00 "")
 (setq p1 (list 553.75 1723.47) p2 (list 0.00 0.00))
 (command "TEXT" "J" "ML" p1   0.75  0.00 "9990")
 (command "LAYER" "S" "CGBLITHTXT" "")
 (setq p1 (list 557.50 1723.47) p2 (list 0.00 0.00))
 (command "TEXT" "J" "ML" p1   0.75  0.00 "BLK SH W/SS STKS")
 (command "LAYER" "S" "CGBCMNT" "")
 (setq p1 (list 577.75 1723.47) p2 (list 0.00 0.00))
 (command "TEXT" "J" "ML" p1   0.75  0.00 "")
 (command "LAYER" "S" "CGBMAIN" "")
 (setq p1 (list 535.00 1724.93) p2 (list 541.00 1724.93) p3 (list 541.00 1722.87) p4 (list 535.00 1722.87))
 (command "PLINE" p1 p2 p3 p4 "c")
 (command "HATCH" "ZIGZAG" 4.00 22.50 "L" "")
 (command "COLOR" "BYLAYER")
 (command "LAYER" "S" "CGBLITHCD" "")
 (setq p1 (list 541.00 1723.90) p2 (list 542.35 1722.59))
 (command "LINE" p1 p2 "")
 (setq p1 (list 542.50 1722.22) p2 (list 0.00 0.00))
 (command "TEXT" "J" "ML" p1   0.75  0.00 "114")
 (command "LAYER" "S" "CGBTHK" "")
 (setq p1 (list 547.00 1722.22) p2 (list 0.00 0.00))
 (command "TEXT" "J" "ML" p1   0.75  0.00 "2.06")
 (command "LAYER" "S" "CGBHZID" "")
 (setq p1 (list 551.50 1722.22) p2 (list 0.00 0.00))
 (command "TEXT" "J" "ML" p1   0.75  0.00 "")
 (setq p1 (list 553.75 1722.22) p2 (list 0.00 0.00))
 (command "TEXT" "J" "ML" p1   0.75  0.00 "9990")
 (command "LAYER" "S" "CGBLITHTXT" "")
 (setq p1 (list 557.50 1722.22) p2 (list 0.00 0.00))
 (command "TEXT" "J" "ML" p1   0.75  0.00 "BLK SH")
 (command "LAYER" "S" "CGBCMNT" "")
 (setq p1 (list 577.75 1722.22) p2 (list 0.00 0.00))
 (command "TEXT" "J" "ML" p1   0.75  0.00 "")
 (command "LAYER" "S" "CGBMAIN" "")
 (setq p1 (list 535.00 1722.87) p2 (list 541.00 1722.87) p3 (list 541.00 1722.18) p4 (list 535.00 1722.18))
 (command "PLINE" p1 p2 p3 p4 "c")
 (command "HATCH" "ZIGZAG" 5.00 0.00 "L" "")
 (command "COLOR" "BYLAYER")
 (command "LAYER" "S" "CGBLITHCD" "")
 (setq p1 (list 541.00 1722.53) p2 (list 542.35 1721.34))
 (command "LINE" p1 p2 "")
 (setq p1 (list 542.50 1720.97) p2 (list 0.00 0.00))
 (command "TEXT" "J" "ML" p1   0.75  0.00 "039")
 (command "LAYER" "S" "CGBTHK" "")
 (setq p1 (list 547.00 1720.97) p2 (list 0.00 0.00))
 (command "TEXT" "J" "ML" p1   0.75  0.00 "0.69")
 (command "LAYER" "S" "CGBHZID" "")
 (setq p1 (list 551.50 1720.97) p2 (list 0.00 0.00))
 (command "TEXT" "J" "ML" p1   0.75  0.00 "")
 (setq p1 (list 553.75 1720.97) p2 (list 0.00 0.00))
 (command "TEXT" "J" "ML" p1   0.75  0.00 "9990")
 (command "LAYER" "S" "CGBLITHTXT" "")
 (setq p1 (list 557.50 1720.97) p2 (list 0.00 0.00))
 (command "TEXT" "J" "ML" p1   0.75  0.00 "BONE W/PYRITE STKS")
 (command "LAYER" "S" "CGBCMNT" "")
 (setq p1 (list 577.75 1720.97) p2 (list 0.00 0.00))
 (command "TEXT" "J" "ML" p1   0.75  0.00 "")
 (command "LAYER" "S" "CGBMAIN" "")
 (setq p1 (list 535.00 1722.18) p2 (list 541.00 1722.18) p3 (list 541.00 1721.68) p4 (list 535.00 1721.68))
 (command "PLINE" p1 p2 p3 p4 "c")
 (command "HATCH" "ZIGZAG" 0.80 0.00 "L" "")
 (command "COLOR" "BYLAYER")
 (command "LAYER" "S" "CGBLITHCD" "")
 (setq p1 (list 541.00 1721.93) p2 (list 542.35 1720.09))
 (command "LINE" p1 p2 "")
 (setq p1 (list 542.50 1719.72) p2 (list 0.00 0.00))
 (command "TEXT" "J" "ML" p1   0.75  0.00 "029")
 (command "LAYER" "S" "CGBTHK" "")
 (setq p1 (list 547.00 1719.72) p2 (list 0.00 0.00))
 (command "TEXT" "J" "ML" p1   0.75  0.00 "0.50")
 (command "LAYER" "S" "CGBHZID" "")
 (setq p1 (list 551.50 1719.72) p2 (list 0.00 0.00))
 (command "TEXT" "J" "ML" p1   0.75  0.00 "")
 (setq p1 (list 553.75 1719.72) p2 (list 0.00 0.00))
 (command "TEXT" "J" "ML" p1   0.75  0.00 "8000")
 (command "LAYER" "S" "CGBLITHTXT" "")
 (setq p1 (list 557.50 1719.72) p2 (list 0.00 0.00))
 (command "TEXT" "J" "ML" p1   0.75  0.00 "COAL W/PYRITE STKS")
 (command "LAYER" "S" "CGBCMNT" "")
 (setq p1 (list 577.75 1719.72) p2 (list 0.00 0.00))
 (command "TEXT" "J" "ML" p1   0.75  0.00 "")
 (command "LAYER" "S" "CGBMAIN" "")
 (setq p1 (list 535.00 1721.68) p2 (list 541.00 1721.68) p3 (list 541.00 1721.33) p4 (list 535.00 1721.33))
 (command "PLINE" p1 p2 p3 p4 "c")
 (command "HATCH" "ZIGZAG" 0.40 45.00 "L" "")
 (command "COLOR" "BYLAYER")
 (command "LAYER" "S" "CGBLITHCD" "")
 (setq p1 (list 541.00 1721.51) p2 (list 542.35 1718.84))
 (command "LINE" p1 p2 "")
 (setq p1 (list 542.50 1718.47) p2 (list 0.00 0.00))
 (command "TEXT" "J" "ML" p1   0.75  0.00 "024")
 (command "LAYER" "S" "CGBTHK" "")
 (setq p1 (list 547.00 1718.47) p2 (list 0.00 0.00))
 (command "TEXT" "J" "ML" p1   0.75  0.00 "0.35")
 (command "LAYER" "S" "CGBHZID" "")
 (setq p1 (list 551.50 1718.47) p2 (list 0.00 0.00))
 (command "TEXT" "J" "ML" p1   0.75  0.00 "")
 (setq p1 (list 553.75 1718.47) p2 (list 0.00 0.00))
 (command "TEXT" "J" "ML" p1   0.75  0.00 "8000")
 (command "LAYER" "S" "CGBLITHTXT" "")
 (setq p1 (list 557.50 1718.47) p2 (list 0.00 0.00))
 (command "TEXT" "J" "ML" p1   0.75  0.00 "DULL OR CANNEL COAL")
 (command "LAYER" "S" "CGBCMNT" "")
 (setq p1 (list 577.75 1718.47) p2 (list 0.00 0.00))
 (command "TEXT" "J" "ML" p1   0.75  0.00 "PYRT")
 (command "LAYER" "S" "CGBMAIN" "")
 (setq p1 (list 535.00 1721.33) p2 (list 541.00 1721.33) p3 (list 541.00 1720.84) p4 (list 535.00 1720.84))
 (command "PLINE" p1 p2 p3 p4 "c")
 (command "HATCH" "ZIGZAG" 0.80 0.00 "L" "")
 (command "COLOR" "BYLAYER")
 (command "LAYER" "S" "CGBLITHCD" "")
 (setq p1 (list 541.00 1721.09) p2 (list 542.35 1717.59))
 (command "LINE" p1 p2 "")
 (setq p1 (list 542.50 1717.22) p2 (list 0.00 0.00))
 (command "TEXT" "J" "ML" p1   0.75  0.00 "029")
 (command "LAYER" "S" "CGBTHK" "")
 (setq p1 (list 547.00 1717.22) p2 (list 0.00 0.00))
 (command "TEXT" "J" "ML" p1   0.75  0.00 "0.49")
 (command "LAYER" "S" "CGBHZID" "")
 (setq p1 (list 551.50 1717.22) p2 (list 0.00 0.00))
 (command "TEXT" "J" "ML" p1   0.75  0.00 "")
 (setq p1 (list 553.75 1717.22) p2 (list 0.00 0.00))
 (command "TEXT" "J" "ML" p1   0.75  0.00 "8000")
 (command "LAYER" "S" "CGBLITHTXT" "")
 (setq p1 (list 557.50 1717.22) p2 (list 0.00 0.00))
 (command "TEXT" "J" "ML" p1   0.75  0.00 "COAL W/PYRITE STKS")
 (command "LAYER" "S" "CGBCMNT" "")
 (setq p1 (list 577.75 1717.22) p2 (list 0.00 0.00))
 (command "TEXT" "J" "ML" p1   0.75  0.00 "VIT W/PYRT")
 (command "LAYER" "S" "CGBMAIN" "")
 (setq p1 (list 535.00 1720.84) p2 (list 541.00 1720.84) p3 (list 541.00 1719.75) p4 (list 535.00 1719.75))
 (command "PLINE" p1 p2 p3 p4 "c")
 (command "COLOR" "BLUE")
 (command "SOLID" p1 p2 p4 p3 "")
 (command "COLOR" "BYLAYER")
 (command "LAYER" "S" "CGBLITHCD" "")
 (setq p1 (list 541.00 1720.30) p2 (list 542.35 1716.34))
 (command "LINE" p1 p2 "")
 (setq p1 (list 542.50 1715.97) p2 (list 0.00 0.00))
 (command "TEXT" "J" "ML" p1   0.75  0.00 "021")
 (command "LAYER" "S" "CGBTHK" "")
 (setq p1 (list 547.00 1715.97) p2 (list 0.00 0.00))
 (command "TEXT" "J" "ML" p1   0.75  0.00 "1.09")
 (command "LAYER" "S" "CGBHZID" "")
 (setq p1 (list 551.50 1715.97) p2 (list 0.00 0.00))
 (command "TEXT" "J" "ML" p1   0.75  0.00 "")
 (setq p1 (list 553.75 1715.97) p2 (list 0.00 0.00))
 (command "TEXT" "J" "ML" p1   0.75  0.00 "8000")
 (command "LAYER" "S" "CGBLITHTXT" "")
 (setq p1 (list 557.50 1715.97) p2 (list 0.00 0.00))
 (command "TEXT" "J" "ML" p1   0.75  0.00 "COMMON BANDED COAL")
 (command "LAYER" "S" "CGBCMNT" "")
 (setq p1 (list 577.75 1715.97) p2 (list 0.00 0.00))
 (command "TEXT" "J" "ML" p1   0.75  0.00 "BRKN VIT")
 (command "LAYER" "S" "CGBMAIN" "")
 (setq p1 (list 535.00 1719.75) p2 (list 541.00 1719.75) p3 (list 541.00 1717.32) p4 (list 535.00 1717.32))
 (command "PLINE" p1 p2 p3 p4 "c")
 (command "HATCH" "ZIGZAG" 0.25 0.00 "L" "")
 (command "COLOR" "BYLAYER")
 (command "LAYER" "S" "CGBLITHCD" "")
 (setq p1 (list 541.00 1718.54) p2 (list 542.35 1715.09))
 (command "LINE" p1 p2 "")
 (setq p1 (list 542.50 1714.72) p2 (list 0.00 0.00))
 (command "TEXT" "J" "ML" p1   0.75  0.00 "127")
 (command "LAYER" "S" "CGBTHK" "")
 (setq p1 (list 547.00 1714.72) p2 (list 0.00 0.00))
 (command "TEXT" "J" "ML" p1   0.75  0.00 "2.43")
 (command "LAYER" "S" "CGBHZID" "")
 (setq p1 (list 551.50 1714.72) p2 (list 0.00 0.00))
 (command "TEXT" "J" "ML" p1   0.75  0.00 "")
 (setq p1 (list 553.75 1714.72) p2 (list 0.00 0.00))
 (command "TEXT" "J" "ML" p1   0.75  0.00 "7951")
 (command "LAYER" "S" "CGBLITHTXT" "")
 (setq p1 (list 557.50 1714.72) p2 (list 0.00 0.00))
 (command "TEXT" "J" "ML" p1   0.75  0.00 "DRK GRY FIRECLAY")
 (command "LAYER" "S" "CGBCMNT" "")
 (setq p1 (list 577.75 1714.72) p2 (list 0.00 0.00))
 (command "TEXT" "J" "ML" p1   0.75  0.00 "GB")
 (command "LAYER" "S" "CGBMAIN" "")
 (setq p1 (list 535.00 1717.32) p2 (list 541.00 1717.32) p3 (list 541.00 1716.74) p4 (list 535.00 1716.74))
 (command "PLINE" p1 p2 p3 p4 "c")
 (command "HATCH" "ZIGZAG" 2.50 90.00 "L" "")
 (command "COLOR" "BYLAYER")
 (command "LAYER" "S" "CGBLITHCD" "")
 (setq p1 (list 541.00 1717.03) p2 (list 542.35 1713.84))
 (command "LINE" p1 p2 "")
 (setq p1 (list 542.50 1713.47) p2 (list 0.00 0.00))
 (command "TEXT" "J" "ML" p1   0.75  0.00 "324")
 (command "LAYER" "S" "CGBTHK" "")
 (setq p1 (list 547.00 1713.47) p2 (list 0.00 0.00))
 (command "TEXT" "J" "ML" p1   0.75  0.00 "0.58")
 (command "LAYER" "S" "CGBHZID" "")
 (setq p1 (list 551.50 1713.47) p2 (list 0.00 0.00))
 (command "TEXT" "J" "ML" p1   0.75  0.00 "")
 (setq p1 (list 553.75 1713.47) p2 (list 0.00 0.00))
 (command "TEXT" "J" "ML" p1   0.75  0.00 "7951")
 (command "LAYER" "S" "CGBLITHTXT" "")
 (setq p1 (list 557.50 1713.47) p2 (list 0.00 0.00))
 (command "TEXT" "J" "ML" p1   0.75  0.00 "DRK GRY MASS SDY SH")
 (command "LAYER" "S" "CGBCMNT" "")
 (setq p1 (list 577.75 1713.47) p2 (list 0.00 0.00))
 (command "TEXT" "J" "ML" p1   0.75  0.00 "")
 (command "LAYER" "S" "CGBMAIN" "")
 (setq p1 (list 535.00 1716.74) p2 (list 541.00 1716.74) p3 (list 541.00 1715.61) p4 (list 535.00 1715.61))
 (command "PLINE" p1 p2 p3 p4 "c")
 (command "HATCH" "ZIGZAG" 2.50 90.00 "L" "")
 (command "COLOR" "BYLAYER")
 (command "LAYER" "S" "CGBLITHCD" "")
 (setq p1 (list 541.00 1716.18) p2 (list 542.35 1712.59))
 (command "LINE" p1 p2 "")
 (setq p1 (list 542.50 1712.22) p2 (list 0.00 0.00))
 (command "TEXT" "J" "ML" p1   0.75  0.00 "324")
 (command "LAYER" "S" "CGBTHK" "")
 (setq p1 (list 547.00 1712.22) p2 (list 0.00 0.00))
 (command "TEXT" "J" "ML" p1   0.75  0.00 "1.13")
 (command "LAYER" "S" "CGBHZID" "")
 (setq p1 (list 551.50 1712.22) p2 (list 0.00 0.00))
 (command "TEXT" "J" "ML" p1   0.75  0.00 "")
 (setq p1 (list 553.75 1712.22) p2 (list 0.00 0.00))
 (command "TEXT" "J" "ML" p1   0.75  0.00 "7951")
 (command "LAYER" "S" "CGBLITHTXT" "")
 (setq p1 (list 557.50 1712.22) p2 (list 0.00 0.00))
 (command "TEXT" "J" "ML" p1   0.75  0.00 "DRK GRY MASS SDY SH")
 (command "LAYER" "S" "CGBCMNT" "")
 (setq p1 (list 577.75 1712.22) p2 (list 0.00 0.00))
 (command "TEXT" "J" "ML" p1   0.75  0.00 "")
 (command "LAYER" "S" "CGBMAIN" "")
 (setq p1 (list 535.00 1715.61) p2 (list 541.00 1715.61) p3 (list 541.00 1714.74) p4 (list 535.00 1714.74))
 (command "PLINE" p1 p2 p3 p4 "c")
 (command "HATCH" "ZIGZAG" 4.00 0.00 "L" "")
 (command "COLOR" "BYLAYER")
 (command "LAYER" "S" "CGBLITHCD" "")
 (setq p1 (list 541.00 1715.18) p2 (list 542.35 1711.34))
 (command "LINE" p1 p2 "")
 (setq p1 (list 542.50 1710.97) p2 (list 0.00 0.00))
 (command "TEXT" "J" "ML" p1   0.75  0.00 "125")
 (command "LAYER" "S" "CGBTHK" "")
 (setq p1 (list 547.00 1710.97) p2 (list 0.00 0.00))
 (command "TEXT" "J" "ML" p1   0.75  0.00 "0.87")
 (command "LAYER" "S" "CGBHZID" "")
 (setq p1 (list 551.50 1710.97) p2 (list 0.00 0.00))
 (command "TEXT" "J" "ML" p1   0.75  0.00 "")
 (setq p1 (list 553.75 1710.97) p2 (list 0.00 0.00))
 (command "TEXT" "J" "ML" p1   0.75  0.00 "7951")
 (command "LAYER" "S" "CGBLITHTXT" "")
 (setq p1 (list 557.50 1710.97) p2 (list 0.00 0.00))
 (command "TEXT" "J" "ML" p1   0.75  0.00 "DRK GRY CHRND SH")
 (command "LAYER" "S" "CGBCMNT" "")
 (setq p1 (list 577.75 1710.97) p2 (list 0.00 0.00))
 (command "TEXT" "J" "ML" p1   0.75  0.00 "V SFT, SLC")
 (command "LAYER" "S" "CGBMAIN" "")
 (setq p1 (list 535.00 1714.74) p2 (list 541.00 1714.74) p3 (list 541.00 1711.83) p4 (list 535.00 1711.83))
 (command "PLINE" p1 p2 p3 p4 "c")
 (command "HATCH" "ZIGZAG" 2.50 90.00 "L" "")
 (command "COLOR" "BYLAYER")
 (command "LAYER" "S" "CGBLITHCD" "")
 (setq p1 (list 541.00 1713.29) p2 (list 542.35 1710.09))
 (command "LINE" p1 p2 "")
 (setq p1 (list 542.50 1709.72) p2 (list 0.00 0.00))
 (command "TEXT" "J" "ML" p1   0.75  0.00 "324")
 (command "LAYER" "S" "CGBTHK" "")
 (setq p1 (list 547.00 1709.72) p2 (list 0.00 0.00))
 (command "TEXT" "J" "ML" p1   0.75  0.00 "2.91")
 (command "LAYER" "S" "CGBHZID" "")
 (setq p1 (list 551.50 1709.72) p2 (list 0.00 0.00))
 (command "TEXT" "J" "ML" p1   0.75  0.00 "")
 (setq p1 (list 553.75 1709.72) p2 (list 0.00 0.00))
 (command "TEXT" "J" "ML" p1   0.75  0.00 "7951")
 (command "LAYER" "S" "CGBLITHTXT" "")
 (setq p1 (list 557.50 1709.72) p2 (list 0.00 0.00))
 (command "TEXT" "J" "ML" p1   0.75  0.00 "DRK GRY MASS SDY SH")
 (command "LAYER" "S" "CGBCMNT" "")
 (setq p1 (list 577.75 1709.72) p2 (list 0.00 0.00))
 (command "TEXT" "J" "ML" p1   0.75  0.00 "")
 (command "LAYER" "S" "CGBMAIN" "")
 (setq p1 (list 535.00 1711.83) p2 (list 541.00 1711.83) p3 (list 541.00 1711.45) p4 (list 535.00 1711.45))
 (command "PLINE" p1 p2 p3 p4 "c")
 (command "HATCH" "ZIGZAG" 5.00 0.00 "L" "")
 (command "COLOR" "BYLAYER")
 (command "LAYER" "S" "CGBLITHCD" "")
 (setq p1 (list 541.00 1711.64) p2 (list 542.35 1708.84))
 (command "LINE" p1 p2 "")
 (setq p1 (list 542.50 1708.47) p2 (list 0.00 0.00))
 (command "TEXT" "J" "ML" p1   0.75  0.00 "074")
 (command "LAYER" "S" "CGBTHK" "")
 (setq p1 (list 547.00 1708.47) p2 (list 0.00 0.00))
 (command "TEXT" "J" "ML" p1   0.75  0.00 "0.38")
 (command "LAYER" "S" "CGBHZID" "")
 (setq p1 (list 551.50 1708.47) p2 (list 0.00 0.00))
 (command "TEXT" "J" "ML" p1   0.75  0.00 "")
 (setq p1 (list 553.75 1708.47) p2 (list 0.00 0.00))
 (command "TEXT" "J" "ML" p1   0.75  0.00 "7951")
 (command "LAYER" "S" "CGBLITHTXT" "")
 (setq p1 (list 557.50 1708.47) p2 (list 0.00 0.00))
 (command "TEXT" "J" "ML" p1   0.75  0.00 "MASS IRNSTN")
 (command "LAYER" "S" "CGBCMNT" "")
 (setq p1 (list 577.75 1708.47) p2 (list 0.00 0.00))
 (command "TEXT" "J" "ML" p1   0.75  0.00 "")
 (command "LAYER" "S" "CGBMAIN" "")
 (setq p1 (list 535.00 1711.45) p2 (list 541.00 1711.45) p3 (list 541.00 1709.60) p4 (list 535.00 1709.60))
 (command "PLINE" p1 p2 p3 p4 "c")
 (command "HATCH" "ZIGZAG" 4.00 0.00 "L" "")
 (command "COLOR" "BYLAYER")
 (command "LAYER" "S" "CGBLITHCD" "")
 (setq p1 (list 541.00 1710.53) p2 (list 542.35 1707.59))
 (command "LINE" p1 p2 "")
 (setq p1 (list 542.50 1707.22) p2 (list 0.00 0.00))
 (command "TEXT" "J" "ML" p1   0.75  0.00 "374")
 (command "LAYER" "S" "CGBTHK" "")
 (setq p1 (list 547.00 1707.22) p2 (list 0.00 0.00))
 (command "TEXT" "J" "ML" p1   0.75  0.00 "1.85")
 (command "LAYER" "S" "CGBHZID" "")
 (setq p1 (list 551.50 1707.22) p2 (list 0.00 0.00))
 (command "TEXT" "J" "ML" p1   0.75  0.00 "")
 (setq p1 (list 553.75 1707.22) p2 (list 0.00 0.00))
 (command "TEXT" "J" "ML" p1   0.75  0.00 "7951")
 (command "LAYER" "S" "CGBLITHTXT" "")
 (setq p1 (list 557.50 1707.22) p2 (list 0.00 0.00))
 (command "TEXT" "J" "ML" p1   0.75  0.00 "GRY/GRN SDY SH")
 (command "LAYER" "S" "CGBCMNT" "")
 (setq p1 (list 577.75 1707.22) p2 (list 0.00 0.00))
 (command "TEXT" "J" "ML" p1   0.75  0.00 "SLC")
 (command "LAYER" "S" "CGBMAIN" "")
 (setq p1 (list 535.00 1709.60) p2 (list 541.00 1709.60) p3 (list 541.00 1708.64) p4 (list 535.00 1708.64))
 (command "PLINE" p1 p2 p3 p4 "c")
 (command "HATCH" "ZIGZAG" 4.00 0.00 "L" "")
 (command "COLOR" "BYLAYER")
 (command "LAYER" "S" "CGBLITHCD" "")
 (setq p1 (list 541.00 1709.12) p2 (list 542.35 1706.34))
 (command "LINE" p1 p2 "")
 (setq p1 (list 542.50 1705.97) p2 (list 0.00 0.00))
 (command "TEXT" "J" "ML" p1   0.75  0.00 "547")
 (command "LAYER" "S" "CGBTHK" "")
 (setq p1 (list 547.00 1705.97) p2 (list 0.00 0.00))
 (command "TEXT" "J" "ML" p1   0.75  0.00 "0.96")
 (command "LAYER" "S" "CGBHZID" "")
 (setq p1 (list 551.50 1705.97) p2 (list 0.00 0.00))
 (command "TEXT" "J" "ML" p1   0.75  0.00 "")
 (setq p1 (list 553.75 1705.97) p2 (list 0.00 0.00))
 (command "TEXT" "J" "ML" p1   0.75  0.00 "7951")
 (command "LAYER" "S" "CGBLITHTXT" "")
 (setq p1 (list 557.50 1705.97) p2 (list 0.00 0.00))
 (command "TEXT" "J" "ML" p1   0.75  0.00 "GRY ROOTED SS")
 (command "LAYER" "S" "CGBCMNT" "")
 (setq p1 (list 577.75 1705.97) p2 (list 0.00 0.00))
 (command "TEXT" "J" "ML" p1   0.75  0.00 "DRK")
 (command "LAYER" "S" "CGBMAIN" "")
 (setq p1 (list 535.00 1708.64) p2 (list 541.00 1708.64) p3 (list 541.00 1707.68) p4 (list 535.00 1707.68))
 (command "PLINE" p1 p2 p3 p4 "c")
 (command "HATCH" "ZIGZAG" 4.00 0.00 "L" "")
 (command "COLOR" "BYLAYER")
 (command "LAYER" "S" "CGBLITHCD" "")
 (setq p1 (list 541.00 1708.16) p2 (list 542.35 1705.09))
 (command "LINE" p1 p2 "")
 (setq p1 (list 542.50 1704.72) p2 (list 0.00 0.00))
 (command "TEXT" "J" "ML" p1   0.75  0.00 "544")
 (command "LAYER" "S" "CGBTHK" "")
 (setq p1 (list 547.00 1704.72) p2 (list 0.00 0.00))
 (command "TEXT" "J" "ML" p1   0.75  0.00 "0.96")
 (command "LAYER" "S" "CGBHZID" "")
 (setq p1 (list 551.50 1704.72) p2 (list 0.00 0.00))
 (command "TEXT" "J" "ML" p1   0.75  0.00 "")
 (setq p1 (list 553.75 1704.72) p2 (list 0.00 0.00))
 (command "TEXT" "J" "ML" p1   0.75  0.00 "7951")
 (command "LAYER" "S" "CGBLITHTXT" "")
 (setq p1 (list 557.50 1704.72) p2 (list 0.00 0.00))
 (command "TEXT" "J" "ML" p1   0.75  0.00 "GRY MASS SS")
 (command "LAYER" "S" "CGBCMNT" "")
 (setq p1 (list 577.75 1704.72) p2 (list 0.00 0.00))
 (command "TEXT" "J" "ML" p1   0.75  0.00 "")
 (command "LAYER" "S" "CGBMAIN" "")
 (setq p1 (list 535.00 1707.68) p2 (list 541.00 1707.68) p3 (list 541.00 1706.22) p4 (list 535.00 1706.22))
 (command "PLINE" p1 p2 p3 p4 "c")
 (command "HATCH" "ZIGZAG" 4.00 22.50 "L" "")
 (command "COLOR" "BYLAYER")
 (command "LAYER" "S" "CGBLITHCD" "")
 (setq p1 (list 541.00 1706.95) p2 (list 542.35 1703.84))
 (command "LINE" p1 p2 "")
 (setq p1 (list 542.50 1703.47) p2 (list 0.00 0.00))
 (command "TEXT" "J" "ML" p1   0.75  0.00 "135")
 (command "LAYER" "S" "CGBTHK" "")
 (setq p1 (list 547.00 1703.47) p2 (list 0.00 0.00))
 (command "TEXT" "J" "ML" p1   0.75  0.00 "1.46")
 (command "LAYER" "S" "CGBHZID" "")
 (setq p1 (list 551.50 1703.47) p2 (list 0.00 0.00))
 (command "TEXT" "J" "ML" p1   0.75  0.00 "")
 (setq p1 (list 553.75 1703.47) p2 (list 0.00 0.00))
 (command "TEXT" "J" "ML" p1   0.75  0.00 "7951")
 (command "LAYER" "S" "CGBLITHTXT" "")
 (setq p1 (list 557.50 1703.47) p2 (list 0.00 0.00))
 (command "TEXT" "J" "ML" p1   0.75  0.00 "LT GRY CHRND SH")
 (command "LAYER" "S" "CGBCMNT" "")
 (setq p1 (list 577.75 1703.47) p2 (list 0.00 0.00))
 (command "TEXT" "J" "ML" p1   0.75  0.00 "V SFT")
 (command "LAYER" "S" "CGBMAIN" "")
 (setq p1 (list 535.00 1706.22) p2 (list 541.00 1706.22) p3 (list 541.00 1704.04) p4 (list 535.00 1704.04))
 (command "PLINE" p1 p2 p3 p4 "c")
 (command "HATCH" "ZIGZAG" 4.00 0.00 "L" "")
 (command "COLOR" "BYLAYER")
 (command "LAYER" "S" "CGBLITHCD" "")
 (setq p1 (list 541.00 1705.13) p2 (list 542.35 1702.59))
 (command "LINE" p1 p2 "")
 (setq p1 (list 542.50 1702.22) p2 (list 0.00 0.00))
 (command "TEXT" "J" "ML" p1   0.75  0.00 "374")
 (command "LAYER" "S" "CGBTHK" "")
 (setq p1 (list 547.00 1702.22) p2 (list 0.00 0.00))
 (command "TEXT" "J" "ML" p1   0.75  0.00 "2.18")
 (command "LAYER" "S" "CGBHZID" "")
 (setq p1 (list 551.50 1702.22) p2 (list 0.00 0.00))
 (command "TEXT" "J" "ML" p1   0.75  0.00 "")
 (setq p1 (list 553.75 1702.22) p2 (list 0.00 0.00))
 (command "TEXT" "J" "ML" p1   0.75  0.00 "7951")
 (command "LAYER" "S" "CGBLITHTXT" "")
 (setq p1 (list 557.50 1702.22) p2 (list 0.00 0.00))
 (command "TEXT" "J" "ML" p1   0.75  0.00 "GRY/GRN SDY SH")
 (command "LAYER" "S" "CGBCMNT" "")
 (setq p1 (list 577.75 1702.22) p2 (list 0.00 0.00))
 (command "TEXT" "J" "ML" p1   0.75  0.00 "BRKN,FRAC")
 (command "LAYER" "S" "CGBMAIN" "")
 (setq p1 (list 535.00 1704.04) p2 (list 541.00 1704.04) p3 (list 541.00 1703.02) p4 (list 535.00 1703.02))
 (command "PLINE" p1 p2 p3 p4 "c")
 (command "HATCH" "ZIGZAG" 5.00 0.00 "L" "")
 (command "COLOR" "BYLAYER")
 (command "LAYER" "S" "CGBLITHCD" "")
 (setq p1 (list 541.00 1703.53) p2 (list 542.35 1701.34))
 (command "LINE" p1 p2 "")
 (setq p1 (list 542.50 1700.97) p2 (list 0.00 0.00))
 (command "TEXT" "J" "ML" p1   0.75  0.00 "174")
 (command "LAYER" "S" "CGBTHK" "")
 (setq p1 (list 547.00 1700.97) p2 (list 0.00 0.00))
 (command "TEXT" "J" "ML" p1   0.75  0.00 "1.02")
 (command "LAYER" "S" "CGBHZID" "")
 (setq p1 (list 551.50 1700.97) p2 (list 0.00 0.00))
 (command "TEXT" "J" "ML" p1   0.75  0.00 "")
 (setq p1 (list 553.75 1700.97) p2 (list 0.00 0.00))
 (command "TEXT" "J" "ML" p1   0.75  0.00 "7951")
 (command "LAYER" "S" "CGBLITHTXT" "")
 (setq p1 (list 557.50 1700.97) p2 (list 0.00 0.00))
 (command "TEXT" "J" "ML" p1   0.75  0.00 "GRY/GRN SH")
 (command "LAYER" "S" "CGBCMNT" "")
 (setq p1 (list 577.75 1700.97) p2 (list 0.00 0.00))
 (command "TEXT" "J" "ML" p1   0.75  0.00 "")
 (command "LAYER" "S" "CGBMAIN" "")
 (setq p1 (list 535.00 1703.02) p2 (list 541.00 1703.02) p3 (list 541.00 1701.90) p4 (list 535.00 1701.90))
 (command "PLINE" p1 p2 p3 p4 "c")
 (command "HATCH" "ZIGZAG" 4.00 0.00 "L" "")
 (command "COLOR" "BYLAYER")
 (command "LAYER" "S" "CGBLITHCD" "")
 (setq p1 (list 541.00 1702.46) p2 (list 542.35 1700.09))
 (command "LINE" p1 p2 "")
 (setq p1 (list 542.50 1699.72) p2 (list 0.00 0.00))
 (command "TEXT" "J" "ML" p1   0.75  0.00 "123")
 (command "LAYER" "S" "CGBTHK" "")
 (setq p1 (list 547.00 1699.72) p2 (list 0.00 0.00))
 (command "TEXT" "J" "ML" p1   0.75  0.00 "1.12")
 (command "LAYER" "S" "CGBHZID" "")
 (setq p1 (list 551.50 1699.72) p2 (list 0.00 0.00))
 (command "TEXT" "J" "ML" p1   0.75  0.00 "")
 (setq p1 (list 553.75 1699.72) p2 (list 0.00 0.00))
 (command "TEXT" "J" "ML" p1   0.75  0.00 "7951")
 (command "LAYER" "S" "CGBLITHTXT" "")
 (setq p1 (list 557.50 1699.72) p2 (list 0.00 0.00))
 (command "TEXT" "J" "ML" p1   0.75  0.00 "DRK GRY SH W/COAL STKS")
 (command "LAYER" "S" "CGBCMNT" "")
 (setq p1 (list 577.75 1699.72) p2 (list 0.00 0.00))
 (command "TEXT" "J" "ML" p1   0.75  0.00 "")
 (command "LAYER" "S" "CGBMAIN" "")
 (setq p1 (list 535.00 1701.90) p2 (list 541.00 1701.90) p3 (list 541.00 1701.66) p4 (list 535.00 1701.66))
 (command "PLINE" p1 p2 p3 p4 "c")
 (command "HATCH" "ZIGZAG" 0.25 0.00 "L" "")
 (command "COLOR" "BYLAYER")
 (command "LAYER" "S" "CGBLITHCD" "")
 (setq p1 (list 541.00 1701.78) p2 (list 542.35 1698.84))
 (command "LINE" p1 p2 "")
 (setq p1 (list 542.50 1698.47) p2 (list 0.00 0.00))
 (command "TEXT" "J" "ML" p1   0.75  0.00 "127")
 (command "LAYER" "S" "CGBTHK" "")
 (setq p1 (list 547.00 1698.47) p2 (list 0.00 0.00))
 (command "TEXT" "J" "ML" p1   0.75  0.00 "0.24")
 (command "LAYER" "S" "CGBHZID" "")
 (setq p1 (list 551.50 1698.47) p2 (list 0.00 0.00))
 (command "TEXT" "J" "ML" p1   0.75  0.00 "")
 (setq p1 (list 553.75 1698.47) p2 (list 0.00 0.00))
 (command "TEXT" "J" "ML" p1   0.75  0.00 "7951")
 (command "LAYER" "S" "CGBLITHTXT" "")
 (setq p1 (list 557.50 1698.47) p2 (list 0.00 0.00))
 (command "TEXT" "J" "ML" p1   0.75  0.00 "DRK GRY FIRECLAY")
 (command "LAYER" "S" "CGBCMNT" "")
 (setq p1 (list 577.75 1698.47) p2 (list 0.00 0.00))
 (command "TEXT" "J" "ML" p1   0.75  0.00 "")
 (command "LAYER" "S" "CGBMAIN" "")
 (setq p1 (list 535.00 1701.66) p2 (list 541.00 1701.66) p3 (list 541.00 1701.53) p4 (list 535.00 1701.53))
 (command "PLINE" p1 p2 p3 p4 "c")
 (command "HATCH" "ZIGZAG" 0.25 0.00 "L" "")
 (command "COLOR" "BYLAYER")
 (command "LAYER" "S" "CGBLITHCD" "")
 (setq p1 (list 541.00 1701.60) p2 (list 542.35 1697.59))
 (command "LINE" p1 p2 "")
 (setq p1 (list 542.50 1697.22) p2 (list 0.00 0.00))
 (command "TEXT" "J" "ML" p1   0.75  0.00 "327")
 (command "LAYER" "S" "CGBTHK" "")
 (setq p1 (list 547.00 1697.22) p2 (list 0.00 0.00))
 (command "TEXT" "J" "ML" p1   0.75  0.00 "0.13")
 (command "LAYER" "S" "CGBHZID" "")
 (setq p1 (list 551.50 1697.22) p2 (list 0.00 0.00))
 (command "TEXT" "J" "ML" p1   0.75  0.00 "")
 (setq p1 (list 553.75 1697.22) p2 (list 0.00 0.00))
 (command "TEXT" "J" "ML" p1   0.75  0.00 "7951")
 (command "LAYER" "S" "CGBLITHTXT" "")
 (setq p1 (list 557.50 1697.22) p2 (list 0.00 0.00))
 (command "TEXT" "J" "ML" p1   0.75  0.00 "DRK GRY SDY FIRECLAY")
 (command "LAYER" "S" "CGBCMNT" "")
 (setq p1 (list 577.75 1697.22) p2 (list 0.00 0.00))
 (command "TEXT" "J" "ML" p1   0.75  0.00 "")
 (command "LAYER" "S" "CGBMAIN" "")
 (setq p1 (list 535.00 1701.53) p2 (list 541.00 1701.53) p3 (list 541.00 1698.63) p4 (list 535.00 1698.63))
 (command "PLINE" p1 p2 p3 p4 "c")
 (command "HATCH" "ZIGZAG" 4.00 0.00 "L" "")
 (command "COLOR" "BYLAYER")
 (command "LAYER" "S" "CGBLITHCD" "")
 (setq p1 (list 541.00 1700.08) p2 (list 542.35 1696.34))
 (command "LINE" p1 p2 "")
 (setq p1 (list 542.50 1695.97) p2 (list 0.00 0.00))
 (command "TEXT" "J" "ML" p1   0.75  0.00 "424")
 (command "LAYER" "S" "CGBTHK" "")
 (setq p1 (list 547.00 1695.97) p2 (list 0.00 0.00))
 (command "TEXT" "J" "ML" p1   0.75  0.00 "2.90")
 (command "LAYER" "S" "CGBHZID" "")
 (setq p1 (list 551.50 1695.97) p2 (list 0.00 0.00))
 (command "TEXT" "J" "ML" p1   0.75  0.00 "")
 (setq p1 (list 553.75 1695.97) p2 (list 0.00 0.00))
 (command "TEXT" "J" "ML" p1   0.75  0.00 "7951")
 (command "LAYER" "S" "CGBLITHTXT" "")
 (setq p1 (list 557.50 1695.97) p2 (list 0.00 0.00))
 (command "TEXT" "J" "ML" p1   0.75  0.00 "DRK GRY SDY SH W/LS NODS")
 (command "LAYER" "S" "CGBCMNT" "")
 (setq p1 (list 577.75 1695.97) p2 (list 0.00 0.00))
 (command "TEXT" "J" "ML" p1   0.75  0.00 "CALC VEINS")
 (command "LAYER" "S" "CGBMAIN" "")
 (setq p1 (list 535.00 1698.63) p2 (list 541.00 1698.63) p3 (list 541.00 1694.08) p4 (list 535.00 1694.08))
 (command "PLINE" p1 p2 p3 p4 "c")
 (command "HATCH" "ZIGZAG" 5.00 0.00 "L" "")
 (command "COLOR" "BYLAYER")
 (command "LAYER" "S" "CGBLITHCD" "")
 (setq p1 (list 541.00 1696.36) p2 (list 542.35 1695.09))
 (command "LINE" p1 p2 "")
 (setq p1 (list 542.50 1694.72) p2 (list 0.00 0.00))
 (command "TEXT" "J" "ML" p1   0.75  0.00 "224")
 (command "LAYER" "S" "CGBTHK" "")
 (setq p1 (list 547.00 1694.72) p2 (list 0.00 0.00))
 (command "TEXT" "J" "ML" p1   0.75  0.00 "4.55")
 (command "LAYER" "S" "CGBHZID" "")
 (setq p1 (list 551.50 1694.72) p2 (list 0.00 0.00))
 (command "TEXT" "J" "ML" p1   0.75  0.00 "")
 (setq p1 (list 553.75 1694.72) p2 (list 0.00 0.00))
 (command "TEXT" "J" "ML" p1   0.75  0.00 "7951")
 (command "LAYER" "S" "CGBLITHTXT" "")
 (setq p1 (list 557.50 1694.72) p2 (list 0.00 0.00))
 (command "TEXT" "J" "ML" p1   0.75  0.00 "DRK GRY SH W/LS NODS")
 (command "LAYER" "S" "CGBCMNT" "")
 (setq p1 (list 577.75 1694.72) p2 (list 0.00 0.00))
 (command "TEXT" "J" "ML" p1   0.75  0.00 "")
 (command "LAYER" "S" "CGBMAIN" "")
 (setq p1 (list 535.00 1694.08) p2 (list 541.00 1694.08) p3 (list 541.00 1691.74) p4 (list 535.00 1691.74))
 (command "PLINE" p1 p2 p3 p4 "c")
 (command "HATCH" "ZIGZAG" 4.00 0.00 "L" "")
 (command "COLOR" "BYLAYER")
 (command "LAYER" "S" "CGBLITHCD" "")
 (setq p1 (list 541.00 1692.91) p2 (list 542.35 1692.91))
 (command "LINE" p1 p2 "")
 (setq p1 (list 542.50 1692.54) p2 (list 0.00 0.00))
 (command "TEXT" "J" "ML" p1   0.75  0.00 "124")
 (command "LAYER" "S" "CGBTHK" "")
 (setq p1 (list 547.00 1692.54) p2 (list 0.00 0.00))
 (command "TEXT" "J" "ML" p1   0.75  0.00 "2.34")
 (command "LAYER" "S" "CGBHZID" "")
 (setq p1 (list 551.50 1692.54) p2 (list 0.00 0.00))
 (command "TEXT" "J" "ML" p1   0.75  0.00 "")
 (setq p1 (list 553.75 1692.54) p2 (list 0.00 0.00))
 (command "TEXT" "J" "ML" p1   0.75  0.00 "7951")
 (command "LAYER" "S" "CGBLITHTXT" "")
 (setq p1 (list 557.50 1692.54) p2 (list 0.00 0.00))
 (command "TEXT" "J" "ML" p1   0.75  0.00 "DRK GRY SH")
 (command "LAYER" "S" "CGBCMNT" "")
 (setq p1 (list 577.75 1692.54) p2 (list 0.00 0.00))
 (command "TEXT" "J" "ML" p1   0.75  0.00 "")
 (command "LAYER" "S" "CGBMAIN" "")
 (setq p1 (list 535.00 1691.74) p2 (list 541.00 1691.74) p3 (list 541.00 1691.29) p4 (list 535.00 1691.29))
 (command "PLINE" p1 p2 p3 p4 "c")
 (command "HATCH" "ZIGZAG" 4.00 0.00 "L" "")
 (command "COLOR" "BYLAYER")
 (command "LAYER" "S" "CGBLITHCD" "")
 (setq p1 (list 541.00 1691.52) p2 (list 542.35 1691.52))
 (command "LINE" p1 p2 "")
 (setq p1 (list 542.50 1691.14) p2 (list 0.00 0.00))
 (command "TEXT" "J" "ML" p1   0.75  0.00 "124")
 (command "LAYER" "S" "CGBTHK" "")
 (setq p1 (list 547.00 1691.14) p2 (list 0.00 0.00))
 (command "TEXT" "J" "ML" p1   0.75  0.00 "0.45")
 (command "LAYER" "S" "CGBHZID" "")
 (setq p1 (list 551.50 1691.14) p2 (list 0.00 0.00))
 (command "TEXT" "J" "ML" p1   0.75  0.00 "")
 (setq p1 (list 553.75 1691.14) p2 (list 0.00 0.00))
 (command "TEXT" "J" "ML" p1   0.75  0.00 "7951")
 (command "LAYER" "S" "CGBLITHTXT" "")
 (setq p1 (list 557.50 1691.14) p2 (list 0.00 0.00))
 (command "TEXT" "J" "ML" p1   0.75  0.00 "DRK GRY SH")
 (command "LAYER" "S" "CGBCMNT" "")
 (setq p1 (list 577.75 1691.14) p2 (list 0.00 0.00))
 (command "TEXT" "J" "ML" p1   0.75  0.00 "PLNT FOS")
 (command "LAYER" "S" "CGBMAIN" "")
 (setq p1 (list 535.00 1691.29) p2 (list 541.00 1691.29) p3 (list 541.00 1688.44) p4 (list 535.00 1688.44))
 (command "PLINE" p1 p2 p3 p4 "c")
 (command "HATCH" "ZIGZAG" 5.00 0.00 "L" "")
 (command "COLOR" "BYLAYER")
 (command "LAYER" "S" "CGBLITHCD" "")
 (setq p1 (list 541.00 1689.87) p2 (list 542.35 1689.87))
 (command "LINE" p1 p2 "")
 (setq p1 (list 542.50 1689.49) p2 (list 0.00 0.00))
 (command "TEXT" "J" "ML" p1   0.75  0.00 "274")
 (command "LAYER" "S" "CGBTHK" "")
 (setq p1 (list 547.00 1689.49) p2 (list 0.00 0.00))
 (command "TEXT" "J" "ML" p1   0.75  0.00 "2.85")
 (command "LAYER" "S" "CGBHZID" "")
 (setq p1 (list 551.50 1689.49) p2 (list 0.00 0.00))
 (command "TEXT" "J" "ML" p1   0.75  0.00 "")
 (setq p1 (list 553.75 1689.49) p2 (list 0.00 0.00))
 (command "TEXT" "J" "ML" p1   0.75  0.00 "7951")
 (command "LAYER" "S" "CGBLITHTXT" "")
 (setq p1 (list 557.50 1689.49) p2 (list 0.00 0.00))
 (command "TEXT" "J" "ML" p1   0.75  0.00 "GRY/GRN SH W/LS NODS")
 (command "LAYER" "S" "CGBCMNT" "")
 (setq p1 (list 577.75 1689.49) p2 (list 0.00 0.00))
 (command "TEXT" "J" "ML" p1   0.75  0.00 "")
 (command "LAYER" "S" "CGBMAIN" "")
 (setq p1 (list 535.00 1688.44) p2 (list 541.00 1688.44) p3 (list 541.00 1687.59) p4 (list 535.00 1687.59))
 (command "PLINE" p1 p2 p3 p4 "c")
 (command "HATCH" "ZIGZAG" 4.00 0.00 "L" "")
 (command "COLOR" "BYLAYER")
 (command "LAYER" "S" "CGBLITHCD" "")
 (setq p1 (list 541.00 1688.02) p2 (list 542.35 1688.02))
 (command "LINE" p1 p2 "")
 (setq p1 (list 542.50 1687.64) p2 (list 0.00 0.00))
 (command "TEXT" "J" "ML" p1   0.75  0.00 "124")
 (command "LAYER" "S" "CGBTHK" "")
 (setq p1 (list 547.00 1687.64) p2 (list 0.00 0.00))
 (command "TEXT" "J" "ML" p1   0.75  0.00 "0.85")
 (command "LAYER" "S" "CGBHZID" "")
 (setq p1 (list 551.50 1687.64) p2 (list 0.00 0.00))
 (command "TEXT" "J" "ML" p1   0.75  0.00 "")
 (setq p1 (list 553.75 1687.64) p2 (list 0.00 0.00))
 (command "TEXT" "J" "ML" p1   0.75  0.00 "7951")
 (command "LAYER" "S" "CGBLITHTXT" "")
 (setq p1 (list 557.50 1687.64) p2 (list 0.00 0.00))
 (command "TEXT" "J" "ML" p1   0.75  0.00 "DRK GRY SH")
 (command "LAYER" "S" "CGBCMNT" "")
 (setq p1 (list 577.75 1687.64) p2 (list 0.00 0.00))
 (command "TEXT" "J" "ML" p1   0.75  0.00 "V SFT,BRKN SL")
 (command "LAYER" "S" "CGBMAIN" "")
 (setq p1 (list 535.00 1687.59) p2 (list 541.00 1687.59) p3 (list 541.00 1687.51) p4 (list 535.00 1687.51))
 (command "PLINE" p1 p2 p3 p4 "c")
 (command "HATCH" "ZIGZAG" 4.00 0.00 "L" "")
 (command "COLOR" "BYLAYER")
 (command "LAYER" "S" "CGBLITHCD" "")
 (setq p1 (list 541.00 1687.55) p2 (list 542.35 1686.30))
 (command "LINE" p1 p2 "")
 (setq p1 (list 542.50 1685.93) p2 (list 0.00 0.00))
 (command "TEXT" "J" "ML" p1   0.75  0.00 "123")
 (command "LAYER" "S" "CGBTHK" "")
 (setq p1 (list 547.00 1685.93) p2 (list 0.00 0.00))
 (command "TEXT" "J" "ML" p1   0.75  0.00 "0.08")
 (command "LAYER" "S" "CGBHZID" "")
 (setq p1 (list 551.50 1685.93) p2 (list 0.00 0.00))
 (command "TEXT" "J" "ML" p1   0.75  0.00 "")
 (setq p1 (list 553.75 1685.93) p2 (list 0.00 0.00))
 (command "TEXT" "J" "ML" p1   0.75  0.00 "7951")
 (command "LAYER" "S" "CGBLITHTXT" "")
 (setq p1 (list 557.50 1685.93) p2 (list 0.00 0.00))
 (command "TEXT" "J" "ML" p1   0.75  0.00 "DRK GRY SH W/COAL STKS")
 (command "LAYER" "S" "CGBCMNT" "")
 (setq p1 (list 577.75 1685.93) p2 (list 0.00 0.00))
 (command "TEXT" "J" "ML" p1   0.75  0.00 "")
 (command "LAYER" "S" "CGBMAIN" "")
 (setq p1 (list 535.00 1687.51) p2 (list 541.00 1687.51) p3 (list 541.00 1686.59) p4 (list 535.00 1686.59))
 (command "PLINE" p1 p2 p3 p4 "c")
 (command "HATCH" "ZIGZAG" 4.00 0.00 "L" "")
 (command "COLOR" "BYLAYER")
 (command "LAYER" "S" "CGBLITHCD" "")
 (setq p1 (list 541.00 1687.05) p2 (list 542.35 1685.05))
 (command "LINE" p1 p2 "")
 (setq p1 (list 542.50 1684.68) p2 (list 0.00 0.00))
 (command "TEXT" "J" "ML" p1   0.75  0.00 "125")
 (command "LAYER" "S" "CGBTHK" "")
 (setq p1 (list 547.00 1684.68) p2 (list 0.00 0.00))
 (command "TEXT" "J" "ML" p1   0.75  0.00 "0.92")
 (command "LAYER" "S" "CGBHZID" "")
 (setq p1 (list 551.50 1684.68) p2 (list 0.00 0.00))
 (command "TEXT" "J" "ML" p1   0.75  0.00 "")
 (setq p1 (list 553.75 1684.68) p2 (list 0.00 0.00))
 (command "TEXT" "J" "ML" p1   0.75  0.00 "7951")
 (command "LAYER" "S" "CGBLITHTXT" "")
 (setq p1 (list 557.50 1684.68) p2 (list 0.00 0.00))
 (command "TEXT" "J" "ML" p1   0.75  0.00 "DRK GRY CHRND SH")
 (command "LAYER" "S" "CGBCMNT" "")
 (setq p1 (list 577.75 1684.68) p2 (list 0.00 0.00))
 (command "TEXT" "J" "ML" p1   0.75  0.00 "DRK,CRMB")
 (command "LAYER" "S" "CGBMAIN" "")
 (setq p1 (list 535.00 1686.59) p2 (list 541.00 1686.59) p3 (list 541.00 1685.62) p4 (list 535.00 1685.62))
 (command "PLINE" p1 p2 p3 p4 "c")
 (command "HATCH" "ZIGZAG" 0.25 0.00 "L" "")
 (command "COLOR" "BYLAYER")
 (command "LAYER" "S" "CGBLITHCD" "")
 (setq p1 (list 541.00 1686.11) p2 (list 542.35 1683.80))
 (command "LINE" p1 p2 "")
 (setq p1 (list 542.50 1683.43) p2 (list 0.00 0.00))
 (command "TEXT" "J" "ML" p1   0.75  0.00 "177")
 (command "LAYER" "S" "CGBTHK" "")
 (setq p1 (list 547.00 1683.43) p2 (list 0.00 0.00))
 (command "TEXT" "J" "ML" p1   0.75  0.00 "0.97")
 (command "LAYER" "S" "CGBHZID" "")
 (setq p1 (list 551.50 1683.43) p2 (list 0.00 0.00))
 (command "TEXT" "J" "ML" p1   0.75  0.00 "")
 (setq p1 (list 553.75 1683.43) p2 (list 0.00 0.00))
 (command "TEXT" "J" "ML" p1   0.75  0.00 "7951")
 (command "LAYER" "S" "CGBLITHTXT" "")
 (setq p1 (list 557.50 1683.43) p2 (list 0.00 0.00))
 (command "TEXT" "J" "ML" p1   0.75  0.00 "GRY/GRN FIRECLAY")
 (command "LAYER" "S" "CGBCMNT" "")
 (setq p1 (list 577.75 1683.43) p2 (list 0.00 0.00))
 (command "TEXT" "J" "ML" p1   0.75  0.00 "BRKN,SLX")
 (command "LAYER" "S" "CGBMAIN" "")
 (setq p1 (list 535.00 1685.62) p2 (list 541.00 1685.62) p3 (list 541.00 1684.09) p4 (list 535.00 1684.09))
 (command "PLINE" p1 p2 p3 p4 "c")
 (command "HATCH" "ZIGZAG" 5.00 0.00 "L" "")
 (command "COLOR" "BYLAYER")
 (command "LAYER" "S" "CGBLITHCD" "")
 (setq p1 (list 541.00 1684.86) p2 (list 542.35 1682.55))
 (command "LINE" p1 p2 "")
 (setq p1 (list 542.50 1682.18) p2 (list 0.00 0.00))
 (command "TEXT" "J" "ML" p1   0.75  0.00 "224")
 (command "LAYER" "S" "CGBTHK" "")
 (setq p1 (list 547.00 1682.18) p2 (list 0.00 0.00))
 (command "TEXT" "J" "ML" p1   0.75  0.00 "1.53")
 (command "LAYER" "S" "CGBHZID" "")
 (setq p1 (list 551.50 1682.18) p2 (list 0.00 0.00))
 (command "TEXT" "J" "ML" p1   0.75  0.00 "")
 (setq p1 (list 553.75 1682.18) p2 (list 0.00 0.00))
 (command "TEXT" "J" "ML" p1   0.75  0.00 "7951")
 (command "LAYER" "S" "CGBLITHTXT" "")
 (setq p1 (list 557.50 1682.18) p2 (list 0.00 0.00))
 (command "TEXT" "J" "ML" p1   0.75  0.00 "DRK GRY SH W/LS NODS")
 (command "LAYER" "S" "CGBCMNT" "")
 (setq p1 (list 577.75 1682.18) p2 (list 0.00 0.00))
 (command "TEXT" "J" "ML" p1   0.75  0.00 "")
 (command "LAYER" "S" "CGBMAIN" "")
 (setq p1 (list 535.00 1684.09) p2 (list 541.00 1684.09) p3 (list 541.00 1682.94) p4 (list 535.00 1682.94))
 (command "PLINE" p1 p2 p3 p4 "c")
 (command "HATCH" "ZIGZAG" 0.50 0.00 "L" "")
 (command "COLOR" "BYLAYER")
 (command "LAYER" "S" "CGBLITHCD" "")
 (setq p1 (list 541.00 1683.52) p2 (list 542.35 1681.30))
 (command "LINE" p1 p2 "")
 (setq p1 (list 542.50 1680.93) p2 (list 0.00 0.00))
 (command "TEXT" "J" "ML" p1   0.75  0.00 "804")
 (command "LAYER" "S" "CGBTHK" "")
 (setq p1 (list 547.00 1680.93) p2 (list 0.00 0.00))
 (command "TEXT" "J" "ML" p1   0.75  0.00 "1.15")
 (command "LAYER" "S" "CGBHZID" "")
 (setq p1 (list 551.50 1680.93) p2 (list 0.00 0.00))
 (command "TEXT" "J" "ML" p1   0.75  0.00 "")
 (setq p1 (list 553.75 1680.93) p2 (list 0.00 0.00))
 (command "TEXT" "J" "ML" p1   0.75  0.00 "7951")
 (command "LAYER" "S" "CGBLITHTXT" "")
 (setq p1 (list 557.50 1680.93) p2 (list 0.00 0.00))
 (command "TEXT" "J" "ML" p1   0.75  0.00 "MASS FN GRND SHLY LS")
 (command "LAYER" "S" "CGBCMNT" "")
 (setq p1 (list 577.75 1680.93) p2 (list 0.00 0.00))
 (command "TEXT" "J" "ML" p1   0.75  0.00 "BRWN")
 (command "LAYER" "S" "CGBMAIN" "")
 (setq p1 (list 535.00 1682.94) p2 (list 541.00 1682.94) p3 (list 541.00 1681.99) p4 (list 535.00 1681.99))
 (command "PLINE" p1 p2 p3 p4 "c")
 (command "HATCH" "ZIGZAG" 4.00 0.00 "L" "")
 (command "COLOR" "BYLAYER")
 (command "LAYER" "S" "CGBLITHCD" "")
 (setq p1 (list 541.00 1682.47) p2 (list 542.35 1680.05))
 (command "LINE" p1 p2 "")
 (setq p1 (list 542.50 1679.68) p2 (list 0.00 0.00))
 (command "TEXT" "J" "ML" p1   0.75  0.00 "424")
 (command "LAYER" "S" "CGBTHK" "")
 (setq p1 (list 547.00 1679.68) p2 (list 0.00 0.00))
 (command "TEXT" "J" "ML" p1   0.75  0.00 "0.95")
 (command "LAYER" "S" "CGBHZID" "")
 (setq p1 (list 551.50 1679.68) p2 (list 0.00 0.00))
 (command "TEXT" "J" "ML" p1   0.75  0.00 "")
 (setq p1 (list 553.75 1679.68) p2 (list 0.00 0.00))
 (command "TEXT" "J" "ML" p1   0.75  0.00 "7951")
 (command "LAYER" "S" "CGBLITHTXT" "")
 (setq p1 (list 557.50 1679.68) p2 (list 0.00 0.00))
 (command "TEXT" "J" "ML" p1   0.75  0.00 "DRK GRY SDY SH W/LS NODS")
 (command "LAYER" "S" "CGBCMNT" "")
 (setq p1 (list 577.75 1679.68) p2 (list 0.00 0.00))
 (command "TEXT" "J" "ML" p1   0.75  0.00 "")
 (command "LAYER" "S" "CGBMAIN" "")
 (setq p1 (list 535.00 1681.99) p2 (list 541.00 1681.99) p3 (list 541.00 1681.65) p4 (list 535.00 1681.65))
 (command "PLINE" p1 p2 p3 p4 "c")
 (command "HATCH" "ZIGZAG" 0.50 0.00 "L" "")
 (command "COLOR" "BYLAYER")
 (command "LAYER" "S" "CGBLITHCD" "")
 (setq p1 (list 541.00 1681.82) p2 (list 542.35 1678.80))
 (command "LINE" p1 p2 "")
 (setq p1 (list 542.50 1678.43) p2 (list 0.00 0.00))
 (command "TEXT" "J" "ML" p1   0.75  0.00 "804")
 (command "LAYER" "S" "CGBTHK" "")
 (setq p1 (list 547.00 1678.43) p2 (list 0.00 0.00))
 (command "TEXT" "J" "ML" p1   0.75  0.00 "0.34")
 (command "LAYER" "S" "CGBHZID" "")
 (setq p1 (list 551.50 1678.43) p2 (list 0.00 0.00))
 (command "TEXT" "J" "ML" p1   0.75  0.00 "")
 (setq p1 (list 553.75 1678.43) p2 (list 0.00 0.00))
 (command "TEXT" "J" "ML" p1   0.75  0.00 "7951")
 (command "LAYER" "S" "CGBLITHTXT" "")
 (setq p1 (list 557.50 1678.43) p2 (list 0.00 0.00))
 (command "TEXT" "J" "ML" p1   0.75  0.00 "MASS FN GRND SHLY LS")
 (command "LAYER" "S" "CGBCMNT" "")
 (setq p1 (list 577.75 1678.43) p2 (list 0.00 0.00))
 (command "TEXT" "J" "ML" p1   0.75  0.00 "SLC")
 (command "LAYER" "S" "CGBMAIN" "")
 (setq p1 (list 535.00 1681.65) p2 (list 541.00 1681.65) p3 (list 541.00 1676.74) p4 (list 535.00 1676.74))
 (command "PLINE" p1 p2 p3 p4 "c")
 (command "HATCH" "ZIGZAG" 3.00 0.00 "L" "")
 (command "COLOR" "BYLAYER")
 (command "LAYER" "S" "CGBLITHCD" "")
 (setq p1 (list 541.00 1679.20) p2 (list 542.35 1677.55))
 (command "LINE" p1 p2 "")
 (setq p1 (list 542.50 1677.18) p2 (list 0.00 0.00))
 (command "TEXT" "J" "ML" p1   0.75  0.00 "157")
 (command "LAYER" "S" "CGBTHK" "")
 (setq p1 (list 547.00 1677.18) p2 (list 0.00 0.00))
 (command "TEXT" "J" "ML" p1   0.75  0.00 "4.91")
 (command "LAYER" "S" "CGBHZID" "")
 (setq p1 (list 551.50 1677.18) p2 (list 0.00 0.00))
 (command "TEXT" "J" "ML" p1   0.75  0.00 "")
 (setq p1 (list 553.75 1677.18) p2 (list 0.00 0.00))
 (command "TEXT" "J" "ML" p1   0.75  0.00 "7951")
 (command "LAYER" "S" "CGBLITHTXT" "")
 (setq p1 (list 557.50 1677.18) p2 (list 0.00 0.00))
 (command "TEXT" "J" "ML" p1   0.75  0.00 "RED+GRN CLYSTN")
 (command "LAYER" "S" "CGBCMNT" "")
 (setq p1 (list 577.75 1677.18) p2 (list 0.00 0.00))
 (command "TEXT" "J" "ML" p1   0.75  0.00 "SLX,BRKN")
 (command "LAYER" "S" "CGBMAIN" "")
 (setq p1 (list 535.00 1676.74) p2 (list 541.00 1676.74) p3 (list 541.00 1676.33) p4 (list 535.00 1676.33))
 (command "PLINE" p1 p2 p3 p4 "c")
 (command "HATCH" "ZIGZAG" 0.50 0.00 "L" "")
 (command "COLOR" "BYLAYER")
 (command "LAYER" "S" "CGBLITHCD" "")
 (setq p1 (list 541.00 1676.54) p2 (list 542.35 1676.30))
 (command "LINE" p1 p2 "")
 (setq p1 (list 542.50 1675.93) p2 (list 0.00 0.00))
 (command "TEXT" "J" "ML" p1   0.75  0.00 "804")
 (command "LAYER" "S" "CGBTHK" "")
 (setq p1 (list 547.00 1675.93) p2 (list 0.00 0.00))
 (command "TEXT" "J" "ML" p1   0.75  0.00 "0.41")
 (command "LAYER" "S" "CGBHZID" "")
 (setq p1 (list 551.50 1675.93) p2 (list 0.00 0.00))
 (command "TEXT" "J" "ML" p1   0.75  0.00 "")
 (setq p1 (list 553.75 1675.93) p2 (list 0.00 0.00))
 (command "TEXT" "J" "ML" p1   0.75  0.00 "7951")
 (command "LAYER" "S" "CGBLITHTXT" "")
 (setq p1 (list 557.50 1675.93) p2 (list 0.00 0.00))
 (command "TEXT" "J" "ML" p1   0.75  0.00 "MASS FN GRND SHLY LS")
 (command "LAYER" "S" "CGBCMNT" "")
 (setq p1 (list 577.75 1675.93) p2 (list 0.00 0.00))
 (command "TEXT" "J" "ML" p1   0.75  0.00 "GREEN")
 (command "LAYER" "S" "CGBMAIN" "")
 (setq p1 (list 535.00 1676.33) p2 (list 541.00 1676.33) p3 (list 541.00 1675.83) p4 (list 535.00 1675.83))
 (command "PLINE" p1 p2 p3 p4 "c")
 (command "HATCH" "ZIGZAG" 5.00 0.00 "L" "")
 (command "COLOR" "BYLAYER")
 (command "LAYER" "S" "CGBLITHCD" "")
 (setq p1 (list 541.00 1676.08) p2 (list 542.35 1675.05))
 (command "LINE" p1 p2 "")
 (setq p1 (list 542.50 1674.68) p2 (list 0.00 0.00))
 (command "TEXT" "J" "ML" p1   0.75  0.00 "144")
 (command "LAYER" "S" "CGBTHK" "")
 (setq p1 (list 547.00 1674.68) p2 (list 0.00 0.00))
 (command "TEXT" "J" "ML" p1   0.75  0.00 "0.50")
 (command "LAYER" "S" "CGBHZID" "")
 (setq p1 (list 551.50 1674.68) p2 (list 0.00 0.00))
 (command "TEXT" "J" "ML" p1   0.75  0.00 "")
 (setq p1 (list 553.75 1674.68) p2 (list 0.00 0.00))
 (command "TEXT" "J" "ML" p1   0.75  0.00 "7951")
 (command "LAYER" "S" "CGBLITHTXT" "")
 (setq p1 (list 557.50 1674.68) p2 (list 0.00 0.00))
 (command "TEXT" "J" "ML" p1   0.75  0.00 "GRN SH")
 (command "LAYER" "S" "CGBCMNT" "")
 (setq p1 (list 577.75 1674.68) p2 (list 0.00 0.00))
 (command "TEXT" "J" "ML" p1   0.75  0.00 "SLX")
 (command "LAYER" "S" "CGBMAIN" "")
 (setq p1 (list 535.00 1675.83) p2 (list 541.00 1675.83) p3 (list 541.00 1675.22) p4 (list 535.00 1675.22))
 (command "PLINE" p1 p2 p3 p4 "c")
 (command "HATCH" "ZIGZAG" 0.50 0.00 "L" "")
 (command "COLOR" "BYLAYER")
 (command "LAYER" "S" "CGBLITHCD" "")
 (setq p1 (list 541.00 1675.53) p2 (list 542.35 1673.80))
 (command "LINE" p1 p2 "")
 (setq p1 (list 542.50 1673.43) p2 (list 0.00 0.00))
 (command "TEXT" "J" "ML" p1   0.75  0.00 "804")
 (command "LAYER" "S" "CGBTHK" "")
 (setq p1 (list 547.00 1673.43) p2 (list 0.00 0.00))
 (command "TEXT" "J" "ML" p1   0.75  0.00 "0.61")
 (command "LAYER" "S" "CGBHZID" "")
 (setq p1 (list 551.50 1673.43) p2 (list 0.00 0.00))
 (command "TEXT" "J" "ML" p1   0.75  0.00 "")
 (setq p1 (list 553.75 1673.43) p2 (list 0.00 0.00))
 (command "TEXT" "J" "ML" p1   0.75  0.00 "7951")
 (command "LAYER" "S" "CGBLITHTXT" "")
 (setq p1 (list 557.50 1673.43) p2 (list 0.00 0.00))
 (command "TEXT" "J" "ML" p1   0.75  0.00 "MASS FN GRND SHLY LS")
 (command "LAYER" "S" "CGBCMNT" "")
 (setq p1 (list 577.75 1673.43) p2 (list 0.00 0.00))
 (command "TEXT" "J" "ML" p1   0.75  0.00 "")
 (command "LAYER" "S" "CGBMAIN" "")
 (setq p1 (list 535.00 1675.22) p2 (list 541.00 1675.22) p3 (list 541.00 1673.62) p4 (list 535.00 1673.62))
 (command "PLINE" p1 p2 p3 p4 "c")
 (command "HATCH" "ZIGZAG" 4.00 0.00 "L" "")
 (command "COLOR" "BYLAYER")
 (command "LAYER" "S" "CGBLITHCD" "")
 (setq p1 (list 541.00 1674.42) p2 (list 542.35 1672.55))
 (command "LINE" p1 p2 "")
 (setq p1 (list 542.50 1672.18) p2 (list 0.00 0.00))
 (command "TEXT" "J" "ML" p1   0.75  0.00 "444")
 (command "LAYER" "S" "CGBTHK" "")
 (setq p1 (list 547.00 1672.18) p2 (list 0.00 0.00))
 (command "TEXT" "J" "ML" p1   0.75  0.00 "1.60")
 (command "LAYER" "S" "CGBHZID" "")
 (setq p1 (list 551.50 1672.18) p2 (list 0.00 0.00))
 (command "TEXT" "J" "ML" p1   0.75  0.00 "")
 (setq p1 (list 553.75 1672.18) p2 (list 0.00 0.00))
 (command "TEXT" "J" "ML" p1   0.75  0.00 "7951")
 (command "LAYER" "S" "CGBLITHTXT" "")
 (setq p1 (list 557.50 1672.18) p2 (list 0.00 0.00))
 (command "TEXT" "J" "ML" p1   0.75  0.00 "GRN SDY SH W/LS NODS")
 (command "LAYER" "S" "CGBCMNT" "")
 (setq p1 (list 577.75 1672.18) p2 (list 0.00 0.00))
 (command "TEXT" "J" "ML" p1   0.75  0.00 "")
 (command "LAYER" "S" "CGBMAIN" "")
 (setq p1 (list 535.00 1673.62) p2 (list 541.00 1673.62) p3 (list 541.00 1671.74) p4 (list 535.00 1671.74))
 (command "PLINE" p1 p2 p3 p4 "c")
 (command "HATCH" "ZIGZAG" 5.00 0.00 "L" "")
 (command "COLOR" "BYLAYER")
 (command "LAYER" "S" "CGBLITHCD" "")
 (setq p1 (list 541.00 1672.68) p2 (list 542.35 1671.30))
 (command "LINE" p1 p2 "")
 (setq p1 (list 542.50 1670.93) p2 (list 0.00 0.00))
 (command "TEXT" "J" "ML" p1   0.75  0.00 "274")
 (command "LAYER" "S" "CGBTHK" "")
 (setq p1 (list 547.00 1670.93) p2 (list 0.00 0.00))
 (command "TEXT" "J" "ML" p1   0.75  0.00 "1.88")
 (command "LAYER" "S" "CGBHZID" "")
 (setq p1 (list 551.50 1670.93) p2 (list 0.00 0.00))
 (command "TEXT" "J" "ML" p1   0.75  0.00 "")
 (setq p1 (list 553.75 1670.93) p2 (list 0.00 0.00))
 (command "TEXT" "J" "ML" p1   0.75  0.00 "7951")
 (command "LAYER" "S" "CGBLITHTXT" "")
 (setq p1 (list 557.50 1670.93) p2 (list 0.00 0.00))
 (command "TEXT" "J" "ML" p1   0.75  0.00 "GRY/GRN SH W/LS NODS")
 (command "LAYER" "S" "CGBCMNT" "")
 (setq p1 (list 577.75 1670.93) p2 (list 0.00 0.00))
 (command "TEXT" "J" "ML" p1   0.75  0.00 "SLX,GB")
 (command "LAYER" "S" "CGBMAIN" "")
 (setq p1 (list 535.00 1671.74) p2 (list 541.00 1671.74) p3 (list 541.00 1669.79) p4 (list 535.00 1669.79))
 (command "PLINE" p1 p2 p3 p4 "c")
 (command "HATCH" "ZIGZAG" 2.50 90.00 "L" "")
 (command "COLOR" "BYLAYER")
 (command "LAYER" "S" "CGBLITHCD" "")
 (setq p1 (list 541.00 1670.77) p2 (list 542.35 1670.05))
 (command "LINE" p1 p2 "")
 (setq p1 (list 542.50 1669.68) p2 (list 0.00 0.00))
 (command "TEXT" "J" "ML" p1   0.75  0.00 "324")
 (command "LAYER" "S" "CGBTHK" "")
 (setq p1 (list 547.00 1669.68) p2 (list 0.00 0.00))
 (command "TEXT" "J" "ML" p1   0.75  0.00 "1.95")
 (command "LAYER" "S" "CGBHZID" "")
 (setq p1 (list 551.50 1669.68) p2 (list 0.00 0.00))
 (command "TEXT" "J" "ML" p1   0.75  0.00 "")
 (setq p1 (list 553.75 1669.68) p2 (list 0.00 0.00))
 (command "TEXT" "J" "ML" p1   0.75  0.00 "7951")
 (command "LAYER" "S" "CGBLITHTXT" "")
 (setq p1 (list 557.50 1669.68) p2 (list 0.00 0.00))
 (command "TEXT" "J" "ML" p1   0.75  0.00 "DRK GRY MASS SDY SH")
 (command "LAYER" "S" "CGBCMNT" "")
 (setq p1 (list 577.75 1669.68) p2 (list 0.00 0.00))
 (command "TEXT" "J" "ML" p1   0.75  0.00 "CALC")
 (command "LAYER" "S" "CGBMAIN" "")
 (setq p1 (list 535.00 1669.79) p2 (list 541.00 1669.79) p3 (list 541.00 1666.29) p4 (list 535.00 1666.29))
 (command "PLINE" p1 p2 p3 p4 "c")
 (command "HATCH" "ZIGZAG" 4.00 0.00 "L" "")
 (command "COLOR" "BYLAYER")
 (command "LAYER" "S" "CGBLITHCD" "")
 (setq p1 (list 541.00 1668.04) p2 (list 542.35 1668.04))
 (command "LINE" p1 p2 "")
 (setq p1 (list 542.50 1667.67) p2 (list 0.00 0.00))
 (command "TEXT" "J" "ML" p1   0.75  0.00 "543")
 (command "LAYER" "S" "CGBTHK" "")
 (setq p1 (list 547.00 1667.67) p2 (list 0.00 0.00))
 (command "TEXT" "J" "ML" p1   0.75  0.00 "3.50")
 (command "LAYER" "S" "CGBHZID" "")
 (setq p1 (list 551.50 1667.67) p2 (list 0.00 0.00))
 (command "TEXT" "J" "ML" p1   0.75  0.00 "")
 (setq p1 (list 553.75 1667.67) p2 (list 0.00 0.00))
 (command "TEXT" "J" "ML" p1   0.75  0.00 "7951")
 (command "LAYER" "S" "CGBLITHTXT" "")
 (setq p1 (list 557.50 1667.67) p2 (list 0.00 0.00))
 (command "TEXT" "J" "ML" p1   0.75  0.00 "GRY SS W/SH STKS")
 (command "LAYER" "S" "CGBCMNT" "")
 (setq p1 (list 577.75 1667.67) p2 (list 0.00 0.00))
 (command "TEXT" "J" "ML" p1   0.75  0.00 "")
 (command "LAYER" "S" "CGBMAIN" "")
 (setq p1 (list 535.00 1666.29) p2 (list 541.00 1666.29) p3 (list 541.00 1666.11) p4 (list 535.00 1666.11))
 (command "PLINE" p1 p2 p3 p4 "c")
 (command "HATCH" "ZIGZAG" 0.25 0.00 "L" "")
 (command "COLOR" "BYLAYER")
 (command "LAYER" "S" "CGBLITHCD" "")
 (setq p1 (list 541.00 1666.20) p2 (list 542.35 1666.20))
 (command "LINE" p1 p2 "")
 (setq p1 (list 542.50 1665.83) p2 (list 0.00 0.00))
 (command "TEXT" "J" "ML" p1   0.75  0.00 "742")
 (command "LAYER" "S" "CGBTHK" "")
 (setq p1 (list 547.00 1665.83) p2 (list 0.00 0.00))
 (command "TEXT" "J" "ML" p1   0.75  0.00 "0.18")
 (command "LAYER" "S" "CGBHZID" "")
 (setq p1 (list 551.50 1665.83) p2 (list 0.00 0.00))
 (command "TEXT" "J" "ML" p1   0.75  0.00 "")
 (setq p1 (list 553.75 1665.83) p2 (list 0.00 0.00))
 (command "TEXT" "J" "ML" p1   0.75  0.00 "7951")
 (command "LAYER" "S" "CGBLITHTXT" "")
 (setq p1 (list 557.50 1665.83) p2 (list 0.00 0.00))
 (command "TEXT" "J" "ML" p1   0.75  0.00 "GRY SH PEB CGL")
 (command "LAYER" "S" "CGBCMNT" "")
 (setq p1 (list 577.75 1665.83) p2 (list 0.00 0.00))
 (command "TEXT" "J" "ML" p1   0.75  0.00 "")
 (command "LAYER" "S" "CGBMAIN" "")
 (setq p1 (list 535.00 1666.11) p2 (list 541.00 1666.11) p3 (list 541.00 1665.68) p4 (list 535.00 1665.68))
 (command "PLINE" p1 p2 p3 p4 "c")
 (command "HATCH" "ZIGZAG" 4.00 0.00 "L" "")
 (command "COLOR" "BYLAYER")
 (command "LAYER" "S" "CGBLITHCD" "")
 (setq p1 (list 541.00 1665.90) p2 (list 542.35 1664.65))
 (command "LINE" p1 p2 "")
 (setq p1 (list 542.50 1664.27) p2 (list 0.00 0.00))
 (command "TEXT" "J" "ML" p1   0.75  0.00 "543")
 (command "LAYER" "S" "CGBTHK" "")
 (setq p1 (list 547.00 1664.27) p2 (list 0.00 0.00))
 (command "TEXT" "J" "ML" p1   0.75  0.00 "0.43")
 (command "LAYER" "S" "CGBHZID" "")
 (setq p1 (list 551.50 1664.27) p2 (list 0.00 0.00))
 (command "TEXT" "J" "ML" p1   0.75  0.00 "")
 (setq p1 (list 553.75 1664.27) p2 (list 0.00 0.00))
 (command "TEXT" "J" "ML" p1   0.75  0.00 "7951")
 (command "LAYER" "S" "CGBLITHTXT" "")
 (setq p1 (list 557.50 1664.27) p2 (list 0.00 0.00))
 (command "TEXT" "J" "ML" p1   0.75  0.00 "GRY SS W/SH STKS")
 (command "LAYER" "S" "CGBCMNT" "")
 (setq p1 (list 577.75 1664.27) p2 (list 0.00 0.00))
 (command "TEXT" "J" "ML" p1   0.75  0.00 "SLC")
 (command "LAYER" "S" "CGBMAIN" "")
 (setq p1 (list 535.00 1665.68) p2 (list 541.00 1665.68) p3 (list 541.00 1665.04) p4 (list 535.00 1665.04))
 (command "PLINE" p1 p2 p3 p4 "c")
 (command "HATCH" "ZIGZAG" 5.00 0.00 "L" "")
 (command "COLOR" "BYLAYER")
 (command "LAYER" "S" "CGBLITHCD" "")
 (setq p1 (list 541.00 1665.36) p2 (list 542.35 1663.40))
 (command "LINE" p1 p2 "")
 (setq p1 (list 542.50 1663.02) p2 (list 0.00 0.00))
 (command "TEXT" "J" "ML" p1   0.75  0.00 "137")
 (command "LAYER" "S" "CGBTHK" "")
 (setq p1 (list 547.00 1663.02) p2 (list 0.00 0.00))
 (command "TEXT" "J" "ML" p1   0.75  0.00 "0.64")
 (command "LAYER" "S" "CGBHZID" "")
 (setq p1 (list 551.50 1663.02) p2 (list 0.00 0.00))
 (command "TEXT" "J" "ML" p1   0.75  0.00 "")
 (setq p1 (list 553.75 1663.02) p2 (list 0.00 0.00))
 (command "TEXT" "J" "ML" p1   0.75  0.00 "7951")
 (command "LAYER" "S" "CGBLITHTXT" "")
 (setq p1 (list 557.50 1663.02) p2 (list 0.00 0.00))
 (command "TEXT" "J" "ML" p1   0.75  0.00 "LT GRY GRN FIRECLAY")
 (command "LAYER" "S" "CGBCMNT" "")
 (setq p1 (list 577.75 1663.02) p2 (list 0.00 0.00))
 (command "TEXT" "J" "ML" p1   0.75  0.00 "")
 (command "LAYER" "S" "CGBMAIN" "")
 (setq p1 (list 535.00 1665.04) p2 (list 541.00 1665.04) p3 (list 541.00 1663.76) p4 (list 535.00 1663.76))
 (command "PLINE" p1 p2 p3 p4 "c")
 (command "HATCH" "ZIGZAG" 0.25 0.00 "L" "")
 (command "COLOR" "BYLAYER")
 (command "LAYER" "S" "CGBLITHCD" "")
 (setq p1 (list 541.00 1664.40) p2 (list 542.35 1662.15))
 (command "LINE" p1 p2 "")
 (setq p1 (list 542.50 1661.77) p2 (list 0.00 0.00))
 (command "TEXT" "J" "ML" p1   0.75  0.00 "127")
 (command "LAYER" "S" "CGBTHK" "")
 (setq p1 (list 547.00 1661.77) p2 (list 0.00 0.00))
 (command "TEXT" "J" "ML" p1   0.75  0.00 "1.28")
 (command "LAYER" "S" "CGBHZID" "")
 (setq p1 (list 551.50 1661.77) p2 (list 0.00 0.00))
 (command "TEXT" "J" "ML" p1   0.75  0.00 "")
 (setq p1 (list 553.75 1661.77) p2 (list 0.00 0.00))
 (command "TEXT" "J" "ML" p1   0.75  0.00 "7951")
 (command "LAYER" "S" "CGBLITHTXT" "")
 (setq p1 (list 557.50 1661.77) p2 (list 0.00 0.00))
 (command "TEXT" "J" "ML" p1   0.75  0.00 "DRK GRY FIRECLAY")
 (command "LAYER" "S" "CGBCMNT" "")
 (setq p1 (list 577.75 1661.77) p2 (list 0.00 0.00))
 (command "TEXT" "J" "ML" p1   0.75  0.00 "DRK")
 (command "LAYER" "S" "CGBMAIN" "")
 (setq p1 (list 535.00 1663.76) p2 (list 541.00 1663.76) p3 (list 541.00 1663.46) p4 (list 535.00 1663.46))
 (command "PLINE" p1 p2 p3 p4 "c")
 (command "HATCH" "ZIGZAG" 4.00 0.00 "L" "")
 (command "COLOR" "BYLAYER")
 (command "LAYER" "S" "CGBLITHCD" "")
 (setq p1 (list 541.00 1663.61) p2 (list 542.35 1660.90))
 (command "LINE" p1 p2 "")
 (setq p1 (list 542.50 1660.52) p2 (list 0.00 0.00))
 (command "TEXT" "J" "ML" p1   0.75  0.00 "424")
 (command "LAYER" "S" "CGBTHK" "")
 (setq p1 (list 547.00 1660.52) p2 (list 0.00 0.00))
 (command "TEXT" "J" "ML" p1   0.75  0.00 "0.30")
 (command "LAYER" "S" "CGBHZID" "")
 (setq p1 (list 551.50 1660.52) p2 (list 0.00 0.00))
 (command "TEXT" "J" "ML" p1   0.75  0.00 "")
 (setq p1 (list 553.75 1660.52) p2 (list 0.00 0.00))
 (command "TEXT" "J" "ML" p1   0.75  0.00 "7951")
 (command "LAYER" "S" "CGBLITHTXT" "")
 (setq p1 (list 557.50 1660.52) p2 (list 0.00 0.00))
 (command "TEXT" "J" "ML" p1   0.75  0.00 "DRK GRY SDY SH W/LS NODS")
 (command "LAYER" "S" "CGBCMNT" "")
 (setq p1 (list 577.75 1660.52) p2 (list 0.00 0.00))
 (command "TEXT" "J" "ML" p1   0.75  0.00 "")
 (command "LAYER" "S" "CGBMAIN" "")
 (setq p1 (list 535.00 1663.46) p2 (list 541.00 1663.46) p3 (list 541.00 1662.64) p4 (list 535.00 1662.64))
 (command "PLINE" p1 p2 p3 p4 "c")
 (command "HATCH" "ZIGZAG" 4.00 0.00 "L" "")
 (command "COLOR" "BYLAYER")
 (command "LAYER" "S" "CGBLITHCD" "")
 (setq p1 (list 541.00 1663.05) p2 (list 542.35 1659.65))
 (command "LINE" p1 p2 "")
 (setq p1 (list 542.50 1659.27) p2 (list 0.00 0.00))
 (command "TEXT" "J" "ML" p1   0.75  0.00 "124")
 (command "LAYER" "S" "CGBTHK" "")
 (setq p1 (list 547.00 1659.27) p2 (list 0.00 0.00))
 (command "TEXT" "J" "ML" p1   0.75  0.00 "0.82")
 (command "LAYER" "S" "CGBHZID" "")
 (setq p1 (list 551.50 1659.27) p2 (list 0.00 0.00))
 (command "TEXT" "J" "ML" p1   0.75  0.00 "")
 (setq p1 (list 553.75 1659.27) p2 (list 0.00 0.00))
 (command "TEXT" "J" "ML" p1   0.75  0.00 "7951")
 (command "LAYER" "S" "CGBLITHTXT" "")
 (setq p1 (list 557.50 1659.27) p2 (list 0.00 0.00))
 (command "TEXT" "J" "ML" p1   0.75  0.00 "DRK GRY SH")
 (command "LAYER" "S" "CGBCMNT" "")
 (setq p1 (list 577.75 1659.27) p2 (list 0.00 0.00))
 (command "TEXT" "J" "ML" p1   0.75  0.00 "")
 (command "LAYER" "S" "CGBMAIN" "")
 (setq p1 (list 535.00 1662.64) p2 (list 541.00 1662.64) p3 (list 541.00 1661.98) p4 (list 535.00 1661.98))
 (command "PLINE" p1 p2 p3 p4 "c")
 (command "HATCH" "ZIGZAG" 4.00 0.00 "L" "")
 (command "COLOR" "BYLAYER")
 (command "LAYER" "S" "CGBLITHCD" "")
 (setq p1 (list 541.00 1662.31) p2 (list 542.35 1658.40))
 (command "LINE" p1 p2 "")
 (setq p1 (list 542.50 1658.02) p2 (list 0.00 0.00))
 (command "TEXT" "J" "ML" p1   0.75  0.00 "124")
 (command "LAYER" "S" "CGBTHK" "")
 (setq p1 (list 547.00 1658.02) p2 (list 0.00 0.00))
 (command "TEXT" "J" "ML" p1   0.75  0.00 "0.66")
 (command "LAYER" "S" "CGBHZID" "")
 (setq p1 (list 551.50 1658.02) p2 (list 0.00 0.00))
 (command "TEXT" "J" "ML" p1   0.75  0.00 "")
 (setq p1 (list 553.75 1658.02) p2 (list 0.00 0.00))
 (command "TEXT" "J" "ML" p1   0.75  0.00 "7951")
 (command "LAYER" "S" "CGBLITHTXT" "")
 (setq p1 (list 557.50 1658.02) p2 (list 0.00 0.00))
 (command "TEXT" "J" "ML" p1   0.75  0.00 "DRK GRY SH")
 (command "LAYER" "S" "CGBCMNT" "")
 (setq p1 (list 577.75 1658.02) p2 (list 0.00 0.00))
 (command "TEXT" "J" "ML" p1   0.75  0.00 "")
 (command "LAYER" "S" "CGBMAIN" "")
 (setq p1 (list 535.00 1661.98) p2 (list 541.00 1661.98) p3 (list 541.00 1659.46) p4 (list 535.00 1659.46))
 (command "PLINE" p1 p2 p3 p4 "c")
 (command "HATCH" "ZIGZAG" 3.00 0.00 "L" "")
 (command "COLOR" "BYLAYER")
 (command "LAYER" "S" "CGBLITHCD" "")
 (setq p1 (list 541.00 1660.72) p2 (list 542.35 1657.15))
 (command "LINE" p1 p2 "")
 (setq p1 (list 542.50 1656.77) p2 (list 0.00 0.00))
 (command "TEXT" "J" "ML" p1   0.75  0.00 "154")
 (command "LAYER" "S" "CGBTHK" "")
 (setq p1 (list 547.00 1656.77) p2 (list 0.00 0.00))
 (command "TEXT" "J" "ML" p1   0.75  0.00 "2.52")
 (command "LAYER" "S" "CGBHZID" "")
 (setq p1 (list 551.50 1656.77) p2 (list 0.00 0.00))
 (command "TEXT" "J" "ML" p1   0.75  0.00 "")
 (setq p1 (list 553.75 1656.77) p2 (list 0.00 0.00))
 (command "TEXT" "J" "ML" p1   0.75  0.00 "7951")
 (command "LAYER" "S" "CGBLITHTXT" "")
 (setq p1 (list 557.50 1656.77) p2 (list 0.00 0.00))
 (command "TEXT" "J" "ML" p1   0.75  0.00 "RED+GRN SH")
 (command "LAYER" "S" "CGBCMNT" "")
 (setq p1 (list 577.75 1656.77) p2 (list 0.00 0.00))
 (command "TEXT" "J" "ML" p1   0.75  0.00 "YELLOW, SLX")
 (command "LAYER" "S" "CGBMAIN" "")
 (setq p1 (list 535.00 1659.46) p2 (list 541.00 1659.46) p3 (list 541.00 1656.54) p4 (list 535.00 1656.54))
 (command "PLINE" p1 p2 p3 p4 "c")
 (command "HATCH" "ZIGZAG" 5.00 0.00 "L" "")
 (command "COLOR" "BYLAYER")
 (command "LAYER" "S" "CGBLITHCD" "")
 (setq p1 (list 541.00 1658.00) p2 (list 542.35 1655.90))
 (command "LINE" p1 p2 "")
 (setq p1 (list 542.50 1655.52) p2 (list 0.00 0.00))
 (command "TEXT" "J" "ML" p1   0.75  0.00 "274")
 (command "LAYER" "S" "CGBTHK" "")
 (setq p1 (list 547.00 1655.52) p2 (list 0.00 0.00))
 (command "TEXT" "J" "ML" p1   0.75  0.00 "2.92")
 (command "LAYER" "S" "CGBHZID" "")
 (setq p1 (list 551.50 1655.52) p2 (list 0.00 0.00))
 (command "TEXT" "J" "ML" p1   0.75  0.00 "")
 (setq p1 (list 553.75 1655.52) p2 (list 0.00 0.00))
 (command "TEXT" "J" "ML" p1   0.75  0.00 "7951")
 (command "LAYER" "S" "CGBLITHTXT" "")
 (setq p1 (list 557.50 1655.52) p2 (list 0.00 0.00))
 (command "TEXT" "J" "ML" p1   0.75  0.00 "GRY/GRN SH W/LS NODS")
 (command "LAYER" "S" "CGBCMNT" "")
 (setq p1 (list 577.75 1655.52) p2 (list 0.00 0.00))
 (command "TEXT" "J" "ML" p1   0.75  0.00 "YELLOW")
 (command "LAYER" "S" "CGBMAIN" "")
 (setq p1 (list 535.00 1656.54) p2 (list 541.00 1656.54) p3 (list 541.00 1654.84) p4 (list 535.00 1654.84))
 (command "PLINE" p1 p2 p3 p4 "c")
 (command "HATCH" "ZIGZAG" 5.00 0.00 "L" "")
 (command "COLOR" "BYLAYER")
 (command "LAYER" "S" "CGBLITHCD" "")
 (setq p1 (list 541.00 1655.69) p2 (list 542.35 1654.65))
 (command "LINE" p1 p2 "")
 (setq p1 (list 542.50 1654.27) p2 (list 0.00 0.00))
 (command "TEXT" "J" "ML" p1   0.75  0.00 "274")
 (command "LAYER" "S" "CGBTHK" "")
 (setq p1 (list 547.00 1654.27) p2 (list 0.00 0.00))
 (command "TEXT" "J" "ML" p1   0.75  0.00 "1.70")
 (command "LAYER" "S" "CGBHZID" "")
 (setq p1 (list 551.50 1654.27) p2 (list 0.00 0.00))
 (command "TEXT" "J" "ML" p1   0.75  0.00 "")
 (setq p1 (list 553.75 1654.27) p2 (list 0.00 0.00))
 (command "TEXT" "J" "ML" p1   0.75  0.00 "7951")
 (command "LAYER" "S" "CGBLITHTXT" "")
 (setq p1 (list 557.50 1654.27) p2 (list 0.00 0.00))
 (command "TEXT" "J" "ML" p1   0.75  0.00 "GRY/GRN SH W/LS NODS")
 (command "LAYER" "S" "CGBCMNT" "")
 (setq p1 (list 577.75 1654.27) p2 (list 0.00 0.00))
 (command "TEXT" "J" "ML" p1   0.75  0.00 "")
 (command "LAYER" "S" "CGBMAIN" "")
 (setq p1 (list 535.00 1654.84) p2 (list 541.00 1654.84) p3 (list 541.00 1653.11) p4 (list 535.00 1653.11))
 (command "PLINE" p1 p2 p3 p4 "c")
 (command "HATCH" "ZIGZAG" 4.00 0.00 "L" "")
 (command "COLOR" "BYLAYER")
 (command "LAYER" "S" "CGBLITHCD" "")
 (setq p1 (list 541.00 1653.98) p2 (list 542.35 1653.40))
 (command "LINE" p1 p2 "")
 (setq p1 (list 542.50 1653.02) p2 (list 0.00 0.00))
 (command "TEXT" "J" "ML" p1   0.75  0.00 "125")
 (command "LAYER" "S" "CGBTHK" "")
 (setq p1 (list 547.00 1653.02) p2 (list 0.00 0.00))
 (command "TEXT" "J" "ML" p1   0.75  0.00 "1.73")
 (command "LAYER" "S" "CGBHZID" "")
 (setq p1 (list 551.50 1653.02) p2 (list 0.00 0.00))
 (command "TEXT" "J" "ML" p1   0.75  0.00 "")
 (setq p1 (list 553.75 1653.02) p2 (list 0.00 0.00))
 (command "TEXT" "J" "ML" p1   0.75  0.00 "7951")
 (command "LAYER" "S" "CGBLITHTXT" "")
 (setq p1 (list 557.50 1653.02) p2 (list 0.00 0.00))
 (command "TEXT" "J" "ML" p1   0.75  0.00 "DRK GRY CHRND SH")
 (command "LAYER" "S" "CGBCMNT" "")
 (setq p1 (list 577.75 1653.02) p2 (list 0.00 0.00))
 (command "TEXT" "J" "ML" p1   0.75  0.00 "CARB,SLC")
 (command "LAYER" "S" "CGBMAIN" "")
 (setq p1 (list 535.00 1653.11) p2 (list 541.00 1653.11) p3 (list 541.00 1651.74) p4 (list 535.00 1651.74))
 (command "PLINE" p1 p2 p3 p4 "c")
 (command "HATCH" "ZIGZAG" 4.00 0.00 "L" "")
 (command "COLOR" "BYLAYER")
 (command "LAYER" "S" "CGBLITHCD" "")
 (setq p1 (list 541.00 1652.43) p2 (list 542.35 1652.15))
 (command "LINE" p1 p2 "")
 (setq p1 (list 542.50 1651.77) p2 (list 0.00 0.00))
 (command "TEXT" "J" "ML" p1   0.75  0.00 "544")
 (command "LAYER" "S" "CGBTHK" "")
 (setq p1 (list 547.00 1651.77) p2 (list 0.00 0.00))
 (command "TEXT" "J" "ML" p1   0.75  0.00 "1.37")
 (command "LAYER" "S" "CGBHZID" "")
 (setq p1 (list 551.50 1651.77) p2 (list 0.00 0.00))
 (command "TEXT" "J" "ML" p1   0.75  0.00 "")
 (setq p1 (list 553.75 1651.77) p2 (list 0.00 0.00))
 (command "TEXT" "J" "ML" p1   0.75  0.00 "7951")
 (command "LAYER" "S" "CGBLITHTXT" "")
 (setq p1 (list 557.50 1651.77) p2 (list 0.00 0.00))
 (command "TEXT" "J" "ML" p1   0.75  0.00 "GRY MASS SS")
 (command "LAYER" "S" "CGBCMNT" "")
 (setq p1 (list 577.75 1651.77) p2 (list 0.00 0.00))
 (command "TEXT" "J" "ML" p1   0.75  0.00 "SLC")
 (command "LAYER" "S" "CGBMAIN" "")
 (setq p1 (list 535.00 1651.74) p2 (list 541.00 1651.74) p3 (list 541.00 1647.51) p4 (list 535.00 1647.51))
 (command "PLINE" p1 p2 p3 p4 "c")
 (command "HATCH" "ZIGZAG" 4.00 0.00 "L" "")
 (command "COLOR" "BYLAYER")
 (command "LAYER" "S" "CGBLITHCD" "")
 (setq p1 (list 541.00 1649.63) p2 (list 542.35 1649.63))
 (command "LINE" p1 p2 "")
 (setq p1 (list 542.50 1649.25) p2 (list 0.00 0.00))
 (command "TEXT" "J" "ML" p1   0.75  0.00 "541")
 (command "LAYER" "S" "CGBTHK" "")
 (setq p1 (list 547.00 1649.25) p2 (list 0.00 0.00))
 (command "TEXT" "J" "ML" p1   0.75  0.00 "4.23")
 (command "LAYER" "S" "CGBHZID" "")
 (setq p1 (list 551.50 1649.25) p2 (list 0.00 0.00))
 (command "TEXT" "J" "ML" p1   0.75  0.00 "")
 (setq p1 (list 553.75 1649.25) p2 (list 0.00 0.00))
 (command "TEXT" "J" "ML" p1   0.75  0.00 "7951")
 (command "LAYER" "S" "CGBLITHTXT" "")
 (setq p1 (list 557.50 1649.25) p2 (list 0.00 0.00))
 (command "TEXT" "J" "ML" p1   0.75  0.00 "GRY CROSSBED SS")
 (command "LAYER" "S" "CGBCMNT" "")
 (setq p1 (list 577.75 1649.25) p2 (list 0.00 0.00))
 (command "TEXT" "J" "ML" p1   0.75  0.00 "ANG SLC")
 (command "LAYER" "S" "CGBMAIN" "")
 (setq p1 (list 535.00 1647.51) p2 (list 541.00 1647.51) p3 (list 541.00 1642.83) p4 (list 535.00 1642.83))
 (command "PLINE" p1 p2 p3 p4 "c")
 (command "HATCH" "ZIGZAG" 2.50 90.00 "L" "")
 (command "COLOR" "BYLAYER")
 (command "LAYER" "S" "CGBLITHCD" "")
 (setq p1 (list 541.00 1645.17) p2 (list 542.35 1645.17))
 (command "LINE" p1 p2 "")
 (setq p1 (list 542.50 1644.80) p2 (list 0.00 0.00))
 (command "TEXT" "J" "ML" p1   0.75  0.00 "324")
 (command "LAYER" "S" "CGBTHK" "")
 (setq p1 (list 547.00 1644.80) p2 (list 0.00 0.00))
 (command "TEXT" "J" "ML" p1   0.75  0.00 "4.68")
 (command "LAYER" "S" "CGBHZID" "")
 (setq p1 (list 551.50 1644.80) p2 (list 0.00 0.00))
 (command "TEXT" "J" "ML" p1   0.75  0.00 "")
 (setq p1 (list 553.75 1644.80) p2 (list 0.00 0.00))
 (command "TEXT" "J" "ML" p1   0.75  0.00 "7951")
 (command "LAYER" "S" "CGBLITHTXT" "")
 (setq p1 (list 557.50 1644.80) p2 (list 0.00 0.00))
 (command "TEXT" "J" "ML" p1   0.75  0.00 "DRK GRY MASS SDY SH")
 (command "LAYER" "S" "CGBCMNT" "")
 (setq p1 (list 577.75 1644.80) p2 (list 0.00 0.00))
 (command "TEXT" "J" "ML" p1   0.75  0.00 "IRST")
 (command "LAYER" "S" "CGBMAIN" "")
 (setq p1 (list 535.00 1642.83) p2 (list 541.00 1642.83) p3 (list 541.00 1638.34) p4 (list 535.00 1638.34))
 (command "PLINE" p1 p2 p3 p4 "c")
 (command "HATCH" "ZIGZAG" 0.25 0.00 "L" "")
 (command "COLOR" "BYLAYER")
 (command "LAYER" "S" "CGBLITHCD" "")
 (setq p1 (list 541.00 1640.59) p2 (list 542.35 1640.59))
 (command "LINE" p1 p2 "")
 (setq p1 (list 542.50 1640.21) p2 (list 0.00 0.00))
 (command "TEXT" "J" "ML" p1   0.75  0.00 "742")
 (command "LAYER" "S" "CGBTHK" "")
 (setq p1 (list 547.00 1640.21) p2 (list 0.00 0.00))
 (command "TEXT" "J" "ML" p1   0.75  0.00 "4.49")
 (command "LAYER" "S" "CGBHZID" "")
 (setq p1 (list 551.50 1640.21) p2 (list 0.00 0.00))
 (command "TEXT" "J" "ML" p1   0.75  0.00 "")
 (setq p1 (list 553.75 1640.21) p2 (list 0.00 0.00))
 (command "TEXT" "J" "ML" p1   0.75  0.00 "7951")
 (command "LAYER" "S" "CGBLITHTXT" "")
 (setq p1 (list 557.50 1640.21) p2 (list 0.00 0.00))
 (command "TEXT" "J" "ML" p1   0.75  0.00 "GRY SH PEB CGL")
 (command "LAYER" "S" "CGBCMNT" "")
 (setq p1 (list 577.75 1640.21) p2 (list 0.00 0.00))
 (command "TEXT" "J" "ML" p1   0.75  0.00 "SH SPAR")
 (command "LAYER" "S" "CGBMAIN" "")
 (setq p1 (list 535.00 1638.34) p2 (list 541.00 1638.34) p3 (list 541.00 1636.74) p4 (list 535.00 1636.74))
 (command "PLINE" p1 p2 p3 p4 "c")
 (command "HATCH" "ZIGZAG" 4.00 0.00 "L" "")
 (command "COLOR" "BYLAYER")
 (command "LAYER" "S" "CGBLITHCD" "")
 (setq p1 (list 541.00 1637.54) p2 (list 542.35 1637.54))
 (command "LINE" p1 p2 "")
 (setq p1 (list 542.50 1637.17) p2 (list 0.00 0.00))
 (command "TEXT" "J" "ML" p1   0.75  0.00 "541")
 (command "LAYER" "S" "CGBTHK" "")
 (setq p1 (list 547.00 1637.17) p2 (list 0.00 0.00))
 (command "TEXT" "J" "ML" p1   0.75  0.00 "1.60")
 (command "LAYER" "S" "CGBHZID" "")
 (setq p1 (list 551.50 1637.17) p2 (list 0.00 0.00))
 (command "TEXT" "J" "ML" p1   0.75  0.00 "")
 (setq p1 (list 553.75 1637.17) p2 (list 0.00 0.00))
 (command "TEXT" "J" "ML" p1   0.75  0.00 "7951")
 (command "LAYER" "S" "CGBLITHTXT" "")
 (setq p1 (list 557.50 1637.17) p2 (list 0.00 0.00))
 (command "TEXT" "J" "ML" p1   0.75  0.00 "GRY CROSSBED SS")
 (command "LAYER" "S" "CGBCMNT" "")
 (setq p1 (list 577.75 1637.17) p2 (list 0.00 0.00))
 (command "TEXT" "J" "ML" p1   0.75  0.00 "")
 (command "LAYER" "S" "CGBMAIN" "")
 (setq p1 (list 535.00 1636.74) p2 (list 541.00 1636.74) p3 (list 541.00 1634.62) p4 (list 535.00 1634.62))
 (command "PLINE" p1 p2 p3 p4 "c")
 (command "HATCH" "ZIGZAG" 4.00 0.00 "L" "")
 (command "COLOR" "BYLAYER")
 (command "LAYER" "S" "CGBLITHCD" "")
 (setq p1 (list 541.00 1635.68) p2 (list 542.35 1635.68))
 (command "LINE" p1 p2 "")
 (setq p1 (list 542.50 1635.31) p2 (list 0.00 0.00))
 (command "TEXT" "J" "ML" p1   0.75  0.00 "541")
 (command "LAYER" "S" "CGBTHK" "")
 (setq p1 (list 547.00 1635.31) p2 (list 0.00 0.00))
 (command "TEXT" "J" "ML" p1   0.75  0.00 "2.12")
 (command "LAYER" "S" "CGBHZID" "")
 (setq p1 (list 551.50 1635.31) p2 (list 0.00 0.00))
 (command "TEXT" "J" "ML" p1   0.75  0.00 "")
 (setq p1 (list 553.75 1635.31) p2 (list 0.00 0.00))
 (command "TEXT" "J" "ML" p1   0.75  0.00 "7951")
 (command "LAYER" "S" "CGBLITHTXT" "")
 (setq p1 (list 557.50 1635.31) p2 (list 0.00 0.00))
 (command "TEXT" "J" "ML" p1   0.75  0.00 "GRY CROSSBED SS")
 (command "LAYER" "S" "CGBCMNT" "")
 (setq p1 (list 577.75 1635.31) p2 (list 0.00 0.00))
 (command "TEXT" "J" "ML" p1   0.75  0.00 "SLC")
 (command "LAYER" "S" "CGBMAIN" "")
 (setq p1 (list 535.00 1634.62) p2 (list 541.00 1634.62) p3 (list 541.00 1629.55) p4 (list 535.00 1629.55))
 (command "PLINE" p1 p2 p3 p4 "c")
 (command "HATCH" "ZIGZAG" 2.50 90.00 "L" "")
 (command "COLOR" "BYLAYER")
 (command "LAYER" "S" "CGBLITHCD" "")
 (setq p1 (list 541.00 1632.09) p2 (list 542.35 1632.09))
 (command "LINE" p1 p2 "")
 (setq p1 (list 542.50 1631.71) p2 (list 0.00 0.00))
 (command "TEXT" "J" "ML" p1   0.75  0.00 "324")
 (command "LAYER" "S" "CGBTHK" "")
 (setq p1 (list 547.00 1631.71) p2 (list 0.00 0.00))
 (command "TEXT" "J" "ML" p1   0.75  0.00 "5.07")
 (command "LAYER" "S" "CGBHZID" "")
 (setq p1 (list 551.50 1631.71) p2 (list 0.00 0.00))
 (command "TEXT" "J" "ML" p1   0.75  0.00 "")
 (setq p1 (list 553.75 1631.71) p2 (list 0.00 0.00))
 (command "TEXT" "J" "ML" p1   0.75  0.00 "7951")
 (command "LAYER" "S" "CGBLITHTXT" "")
 (setq p1 (list 557.50 1631.71) p2 (list 0.00 0.00))
 (command "TEXT" "J" "ML" p1   0.75  0.00 "DRK GRY MASS SDY SH")
 (command "LAYER" "S" "CGBCMNT" "")
 (setq p1 (list 577.75 1631.71) p2 (list 0.00 0.00))
 (command "TEXT" "J" "ML" p1   0.75  0.00 "FNS DWN")
 (command "LAYER" "S" "CGBMAIN" "")
 (setq p1 (list 535.00 1629.55) p2 (list 541.00 1629.55) p3 (list 541.00 1627.08) p4 (list 535.00 1627.08))
 (command "PLINE" p1 p2 p3 p4 "c")
 (command "HATCH" "ZIGZAG" 4.00 0.00 "L" "")
 (command "COLOR" "BYLAYER")
 (command "LAYER" "S" "CGBLITHCD" "")
 (setq p1 (list 541.00 1628.32) p2 (list 542.35 1628.32))
 (command "LINE" p1 p2 "")
 (setq p1 (list 542.50 1627.94) p2 (list 0.00 0.00))
 (command "TEXT" "J" "ML" p1   0.75  0.00 "124")
 (command "LAYER" "S" "CGBTHK" "")
 (setq p1 (list 547.00 1627.94) p2 (list 0.00 0.00))
 (command "TEXT" "J" "ML" p1   0.75  0.00 "2.47")
 (command "LAYER" "S" "CGBHZID" "")
 (setq p1 (list 551.50 1627.94) p2 (list 0.00 0.00))
 (command "TEXT" "J" "ML" p1   0.75  0.00 "")
 (setq p1 (list 553.75 1627.94) p2 (list 0.00 0.00))
 (command "TEXT" "J" "ML" p1   0.75  0.00 "7951")
 (command "LAYER" "S" "CGBLITHTXT" "")
 (setq p1 (list 557.50 1627.94) p2 (list 0.00 0.00))
 (command "TEXT" "J" "ML" p1   0.75  0.00 "DRK GRY SH")
 (command "LAYER" "S" "CGBCMNT" "")
 (setq p1 (list 577.75 1627.94) p2 (list 0.00 0.00))
 (command "TEXT" "J" "ML" p1   0.75  0.00 "GB")
 (command "LAYER" "S" "CGBMAIN" "")
 (setq p1 (list 535.00 1627.08) p2 (list 541.00 1627.08) p3 (list 541.00 1626.60) p4 (list 535.00 1626.60))
 (command "PLINE" p1 p2 p3 p4 "c")
 (command "HATCH" "ZIGZAG" 4.00 22.50 "L" "")
 (command "COLOR" "BYLAYER")
 (command "LAYER" "S" "CGBLITHCD" "")
 (setq p1 (list 541.00 1626.84) p2 (list 542.35 1626.84))
 (command "LINE" p1 p2 "")
 (setq p1 (list 542.50 1626.47) p2 (list 0.00 0.00))
 (command "TEXT" "J" "ML" p1   0.75  0.00 "114")
 (command "LAYER" "S" "CGBTHK" "")
 (setq p1 (list 547.00 1626.47) p2 (list 0.00 0.00))
 (command "TEXT" "J" "ML" p1   0.75  0.00 "0.48")
 (command "LAYER" "S" "CGBHZID" "")
 (setq p1 (list 551.50 1626.47) p2 (list 0.00 0.00))
 (command "TEXT" "J" "ML" p1   0.75  0.00 "")
 (setq p1 (list 553.75 1626.47) p2 (list 0.00 0.00))
 (command "TEXT" "J" "ML" p1   0.75  0.00 "7951")
 (command "LAYER" "S" "CGBLITHTXT" "")
 (setq p1 (list 557.50 1626.47) p2 (list 0.00 0.00))
 (command "TEXT" "J" "ML" p1   0.75  0.00 "BLK SH")
 (command "LAYER" "S" "CGBCMNT" "")
 (setq p1 (list 577.75 1626.47) p2 (list 0.00 0.00))
 (command "TEXT" "J" "ML" p1   0.75  0.00 "")
 (command "LAYER" "S" "CGBMAIN" "")
 (setq p1 (list 535.00 1626.60) p2 (list 541.00 1626.60) p3 (list 541.00 1626.41) p4 (list 535.00 1626.41))
 (command "PLINE" p1 p2 p3 p4 "c")
 (command "HATCH" "ZIGZAG" 0.80 0.00 "L" "")
 (command "COLOR" "BYLAYER")
 (command "LAYER" "S" "CGBLITHCD" "")
 (setq p1 (list 541.00 1626.51) p2 (list 542.35 1625.26))
 (command "LINE" p1 p2 "")
 (setq p1 (list 542.50 1624.88) p2 (list 0.00 0.00))
 (command "TEXT" "J" "ML" p1   0.75  0.00 "029")
 (command "LAYER" "S" "CGBTHK" "")
 (setq p1 (list 547.00 1624.88) p2 (list 0.00 0.00))
 (command "TEXT" "J" "ML" p1   0.75  0.00 "0.19")
 (command "LAYER" "S" "CGBHZID" "")
 (setq p1 (list 551.50 1624.88) p2 (list 0.00 0.00))
 (command "TEXT" "J" "ML" p1   0.75  0.00 "")
 (setq p1 (list 553.75 1624.88) p2 (list 0.00 0.00))
 (command "TEXT" "J" "ML" p1   0.75  0.00 "7500")
 (command "LAYER" "S" "CGBLITHTXT" "")
 (setq p1 (list 557.50 1624.88) p2 (list 0.00 0.00))
 (command "TEXT" "J" "ML" p1   0.75  0.00 "COAL W/PYRITE STKS")
 (command "LAYER" "S" "CGBCMNT" "")
 (setq p1 (list 577.75 1624.88) p2 (list 0.00 0.00))
 (command "TEXT" "J" "ML" p1   0.75  0.00 "ABDT PYRT")
 (command "LAYER" "S" "CGBMAIN" "")
 (setq p1 (list 535.00 1626.41) p2 (list 541.00 1626.41) p3 (list 541.00 1624.14) p4 (list 535.00 1624.14))
 (command "PLINE" p1 p2 p3 p4 "c")
 (command "HATCH" "ZIGZAG" 0.25 0.00 "L" "")
 (command "COLOR" "BYLAYER")
 (command "LAYER" "S" "CGBLITHCD" "")
 (setq p1 (list 541.00 1625.28) p2 (list 542.35 1624.01))
 (command "LINE" p1 p2 "")
 (setq p1 (list 542.50 1623.63) p2 (list 0.00 0.00))
 (command "TEXT" "J" "ML" p1   0.75  0.00 "327")
 (command "LAYER" "S" "CGBTHK" "")
 (setq p1 (list 547.00 1623.63) p2 (list 0.00 0.00))
 (command "TEXT" "J" "ML" p1   0.75  0.00 "2.27")
 (command "LAYER" "S" "CGBHZID" "")
 (setq p1 (list 551.50 1623.63) p2 (list 0.00 0.00))
 (command "TEXT" "J" "ML" p1   0.75  0.00 "")
 (setq p1 (list 553.75 1623.63) p2 (list 0.00 0.00))
 (command "TEXT" "J" "ML" p1   0.75  0.00 "7451")
 (command "LAYER" "S" "CGBLITHTXT" "")
 (setq p1 (list 557.50 1623.63) p2 (list 0.00 0.00))
 (command "TEXT" "J" "ML" p1   0.75  0.00 "DRK GRY SDY FIRECLAY")
 (command "LAYER" "S" "CGBCMNT" "")
 (setq p1 (list 577.75 1623.63) p2 (list 0.00 0.00))
 (command "TEXT" "J" "ML" p1   0.75  0.00 "")
 (command "LAYER" "S" "CGBMAIN" "")
 (setq p1 (list 535.00 1624.14) p2 (list 541.00 1624.14) p3 (list 541.00 1623.10) p4 (list 535.00 1623.10))
 (command "PLINE" p1 p2 p3 p4 "c")
 (command "HATCH" "ZIGZAG" 4.00 0.00 "L" "")
 (command "COLOR" "BYLAYER")
 (command "LAYER" "S" "CGBLITHCD" "")
 (setq p1 (list 541.00 1623.62) p2 (list 542.35 1622.76))
 (command "LINE" p1 p2 "")
 (setq p1 (list 542.50 1622.38) p2 (list 0.00 0.00))
 (command "TEXT" "J" "ML" p1   0.75  0.00 "547")
 (command "LAYER" "S" "CGBTHK" "")
 (setq p1 (list 547.00 1622.38) p2 (list 0.00 0.00))
 (command "TEXT" "J" "ML" p1   0.75  0.00 "1.04")
 (command "LAYER" "S" "CGBHZID" "")
 (setq p1 (list 551.50 1622.38) p2 (list 0.00 0.00))
 (command "TEXT" "J" "ML" p1   0.75  0.00 "")
 (setq p1 (list 553.75 1622.38) p2 (list 0.00 0.00))
 (command "TEXT" "J" "ML" p1   0.75  0.00 "7451")
 (command "LAYER" "S" "CGBLITHTXT" "")
 (setq p1 (list 557.50 1622.38) p2 (list 0.00 0.00))
 (command "TEXT" "J" "ML" p1   0.75  0.00 "GRY ROOTED SS")
 (command "LAYER" "S" "CGBCMNT" "")
 (setq p1 (list 577.75 1622.38) p2 (list 0.00 0.00))
 (command "TEXT" "J" "ML" p1   0.75  0.00 "")
 (command "LAYER" "S" "CGBMAIN" "")
 (setq p1 (list 535.00 1623.10) p2 (list 541.00 1623.10) p3 (list 541.00 1621.74) p4 (list 535.00 1621.74))
 (command "PLINE" p1 p2 p3 p4 "c")
 (command "HATCH" "ZIGZAG" 0.25 0.00 "L" "")
 (command "COLOR" "BYLAYER")
 (command "LAYER" "S" "CGBLITHCD" "")
 (setq p1 (list 541.00 1622.42) p2 (list 542.35 1621.51))
 (command "LINE" p1 p2 "")
 (setq p1 (list 542.50 1621.13) p2 (list 0.00 0.00))
 (command "TEXT" "J" "ML" p1   0.75  0.00 "327")
 (command "LAYER" "S" "CGBTHK" "")
 (setq p1 (list 547.00 1621.13) p2 (list 0.00 0.00))
 (command "TEXT" "J" "ML" p1   0.75  0.00 "1.36")
 (command "LAYER" "S" "CGBHZID" "")
 (setq p1 (list 551.50 1621.13) p2 (list 0.00 0.00))
 (command "TEXT" "J" "ML" p1   0.75  0.00 "")
 (setq p1 (list 553.75 1621.13) p2 (list 0.00 0.00))
 (command "TEXT" "J" "ML" p1   0.75  0.00 "7451")
 (command "LAYER" "S" "CGBLITHTXT" "")
 (setq p1 (list 557.50 1621.13) p2 (list 0.00 0.00))
 (command "TEXT" "J" "ML" p1   0.75  0.00 "DRK GRY SDY FIRECLAY")
 (command "LAYER" "S" "CGBCMNT" "")
 (setq p1 (list 577.75 1621.13) p2 (list 0.00 0.00))
 (command "TEXT" "J" "ML" p1   0.75  0.00 "")
 (command "LAYER" "S" "CGBMAIN" "")
 (setq p1 (list 535.00 1621.74) p2 (list 541.00 1621.74) p3 (list 541.00 1620.69) p4 (list 535.00 1620.69))
 (command "PLINE" p1 p2 p3 p4 "c")
 (command "HATCH" "ZIGZAG" 0.25 0.00 "L" "")
 (command "COLOR" "BYLAYER")
 (command "LAYER" "S" "CGBLITHCD" "")
 (setq p1 (list 541.00 1621.22) p2 (list 542.35 1620.26))
 (command "LINE" p1 p2 "")
 (setq p1 (list 542.50 1619.88) p2 (list 0.00 0.00))
 (command "TEXT" "J" "ML" p1   0.75  0.00 "327")
 (command "LAYER" "S" "CGBTHK" "")
 (setq p1 (list 547.00 1619.88) p2 (list 0.00 0.00))
 (command "TEXT" "J" "ML" p1   0.75  0.00 "1.05")
 (command "LAYER" "S" "CGBHZID" "")
 (setq p1 (list 551.50 1619.88) p2 (list 0.00 0.00))
 (command "TEXT" "J" "ML" p1   0.75  0.00 "")
 (setq p1 (list 553.75 1619.88) p2 (list 0.00 0.00))
 (command "TEXT" "J" "ML" p1   0.75  0.00 "7451")
 (command "LAYER" "S" "CGBLITHTXT" "")
 (setq p1 (list 557.50 1619.88) p2 (list 0.00 0.00))
 (command "TEXT" "J" "ML" p1   0.75  0.00 "DRK GRY SDY FIRECLAY")
 (command "LAYER" "S" "CGBCMNT" "")
 (setq p1 (list 577.75 1619.88) p2 (list 0.00 0.00))
 (command "TEXT" "J" "ML" p1   0.75  0.00 "")
 (command "LAYER" "S" "CGBMAIN" "")
 (setq p1 (list 535.00 1620.69) p2 (list 541.00 1620.69) p3 (list 541.00 1619.64) p4 (list 535.00 1619.64))
 (command "PLINE" p1 p2 p3 p4 "c")
 (command "HATCH" "ZIGZAG" 5.00 0.00 "L" "")
 (command "COLOR" "BYLAYER")
 (command "LAYER" "S" "CGBLITHCD" "")
 (setq p1 (list 541.00 1620.17) p2 (list 542.35 1619.01))
 (command "LINE" p1 p2 "")
 (setq p1 (list 542.50 1618.63) p2 (list 0.00 0.00))
 (command "TEXT" "J" "ML" p1   0.75  0.00 "904")
 (command "LAYER" "S" "CGBTHK" "")
 (setq p1 (list 547.00 1618.63) p2 (list 0.00 0.00))
 (command "TEXT" "J" "ML" p1   0.75  0.00 "1.05")
 (command "LAYER" "S" "CGBHZID" "")
 (setq p1 (list 551.50 1618.63) p2 (list 0.00 0.00))
 (command "TEXT" "J" "ML" p1   0.75  0.00 "")
 (setq p1 (list 553.75 1618.63) p2 (list 0.00 0.00))
 (command "TEXT" "J" "ML" p1   0.75  0.00 "7451")
 (command "LAYER" "S" "CGBLITHTXT" "")
 (setq p1 (list 557.50 1618.63) p2 (list 0.00 0.00))
 (command "TEXT" "J" "ML" p1   0.75  0.00 "MASS FN GRND LS")
 (command "LAYER" "S" "CGBCMNT" "")
 (setq p1 (list 577.75 1618.63) p2 (list 0.00 0.00))
 (command "TEXT" "J" "ML" p1   0.75  0.00 "")
 (command "LAYER" "S" "CGBMAIN" "")
 (setq p1 (list 535.00 1619.64) p2 (list 541.00 1619.64) p3 (list 541.00 1612.04) p4 (list 535.00 1612.04))
 (command "PLINE" p1 p2 p3 p4 "c")
 (command "HATCH" "ZIGZAG" 2.50 90.00 "L" "")
 (command "COLOR" "BYLAYER")
 (command "LAYER" "S" "CGBLITHCD" "")
 (setq p1 (list 541.00 1615.84) p2 (list 542.35 1615.84))
 (command "LINE" p1 p2 "")
 (setq p1 (list 542.50 1615.47) p2 (list 0.00 0.00))
 (command "TEXT" "J" "ML" p1   0.75  0.00 "328")
 (command "LAYER" "S" "CGBTHK" "")
 (setq p1 (list 547.00 1615.47) p2 (list 0.00 0.00))
 (command "TEXT" "J" "ML" p1   0.75  0.00 "7.60")
 (command "LAYER" "S" "CGBHZID" "")
 (setq p1 (list 551.50 1615.47) p2 (list 0.00 0.00))
 (command "TEXT" "J" "ML" p1   0.75  0.00 "")
 (setq p1 (list 553.75 1615.47) p2 (list 0.00 0.00))
 (command "TEXT" "J" "ML" p1   0.75  0.00 "7451")
 (command "LAYER" "S" "CGBLITHTXT" "")
 (setq p1 (list 557.50 1615.47) p2 (list 0.00 0.00))
 (command "TEXT" "J" "ML" p1   0.75  0.00 "DRK GRY BURROWED SDY SH")
 (command "LAYER" "S" "CGBCMNT" "")
 (setq p1 (list 577.75 1615.47) p2 (list 0.00 0.00))
 (command "TEXT" "J" "ML" p1   0.75  0.00 "SS STKS")
 (command "LAYER" "S" "CGBMAIN" "")
 (setq p1 (list 535.00 1612.04) p2 (list 541.00 1612.04) p3 (list 541.00 1608.02) p4 (list 535.00 1608.02))
 (command "PLINE" p1 p2 p3 p4 "c")
 (command "HATCH" "ZIGZAG" 5.00 0.00 "L" "")
 (command "COLOR" "BYLAYER")
 (command "LAYER" "S" "CGBLITHCD" "")
 (setq p1 (list 541.00 1610.03) p2 (list 542.35 1610.03))
 (command "LINE" p1 p2 "")
 (setq p1 (list 542.50 1609.66) p2 (list 0.00 0.00))
 (command "TEXT" "J" "ML" p1   0.75  0.00 "322")
 (command "LAYER" "S" "CGBTHK" "")
 (setq p1 (list 547.00 1609.66) p2 (list 0.00 0.00))
 (command "TEXT" "J" "ML" p1   0.75  0.00 "4.02")
 (command "LAYER" "S" "CGBHZID" "")
 (setq p1 (list 551.50 1609.66) p2 (list 0.00 0.00))
 (command "TEXT" "J" "ML" p1   0.75  0.00 "")
 (setq p1 (list 553.75 1609.66) p2 (list 0.00 0.00))
 (command "TEXT" "J" "ML" p1   0.75  0.00 "7451")
 (command "LAYER" "S" "CGBLITHTXT" "")
 (setq p1 (list 557.50 1609.66) p2 (list 0.00 0.00))
 (command "TEXT" "J" "ML" p1   0.75  0.00 "DRK GRY SH+INTERBED SS")
 (command "LAYER" "S" "CGBCMNT" "")
 (setq p1 (list 577.75 1609.66) p2 (list 0.00 0.00))
 (command "TEXT" "J" "ML" p1   0.75  0.00 "IRST")
 (command "LAYER" "S" "CGBMAIN" "")
 (setq p1 (list 535.00 1608.02) p2 (list 541.00 1608.02) p3 (list 541.00 1606.74) p4 (list 535.00 1606.74))
 (command "PLINE" p1 p2 p3 p4 "c")
 (command "HATCH" "ZIGZAG" 4.00 0.00 "L" "")
 (command "COLOR" "BYLAYER")
 (command "LAYER" "S" "CGBLITHCD" "")
 (setq p1 (list 541.00 1607.38) p2 (list 542.35 1607.38))
 (command "LINE" p1 p2 "")
 (setq p1 (list 542.50 1607.01) p2 (list 0.00 0.00))
 (command "TEXT" "J" "ML" p1   0.75  0.00 "124")
 (command "LAYER" "S" "CGBTHK" "")
 (setq p1 (list 547.00 1607.01) p2 (list 0.00 0.00))
 (command "TEXT" "J" "ML" p1   0.75  0.00 "1.28")
 (command "LAYER" "S" "CGBHZID" "")
 (setq p1 (list 551.50 1607.01) p2 (list 0.00 0.00))
 (command "TEXT" "J" "ML" p1   0.75  0.00 "")
 (setq p1 (list 553.75 1607.01) p2 (list 0.00 0.00))
 (command "TEXT" "J" "ML" p1   0.75  0.00 "7451")
 (command "LAYER" "S" "CGBLITHTXT" "")
 (setq p1 (list 557.50 1607.01) p2 (list 0.00 0.00))
 (command "TEXT" "J" "ML" p1   0.75  0.00 "DRK GRY SH")
 (command "LAYER" "S" "CGBCMNT" "")
 (setq p1 (list 577.75 1607.01) p2 (list 0.00 0.00))
 (command "TEXT" "J" "ML" p1   0.75  0.00 "")
 (command "LAYER" "S" "CGBMAIN" "")
 (setq p1 (list 535.00 1606.74) p2 (list 541.00 1606.74) p3 (list 541.00 1602.74) p4 (list 535.00 1602.74))
 (command "PLINE" p1 p2 p3 p4 "c")
 (command "HATCH" "ZIGZAG" 4.00 0.00 "L" "")
 (command "COLOR" "BYLAYER")
 (command "LAYER" "S" "CGBLITHCD" "")
 (setq p1 (list 541.00 1604.74) p2 (list 542.35 1604.74))
 (command "LINE" p1 p2 "")
 (setq p1 (list 542.50 1604.37) p2 (list 0.00 0.00))
 (command "TEXT" "J" "ML" p1   0.75  0.00 "124")
 (command "LAYER" "S" "CGBTHK" "")
 (setq p1 (list 547.00 1604.37) p2 (list 0.00 0.00))
 (command "TEXT" "J" "ML" p1   0.75  0.00 "4.00")
 (command "LAYER" "S" "CGBHZID" "")
 (setq p1 (list 551.50 1604.37) p2 (list 0.00 0.00))
 (command "TEXT" "J" "ML" p1   0.75  0.00 "")
 (setq p1 (list 553.75 1604.37) p2 (list 0.00 0.00))
 (command "TEXT" "J" "ML" p1   0.75  0.00 "7451")
 (command "LAYER" "S" "CGBLITHTXT" "")
 (setq p1 (list 557.50 1604.37) p2 (list 0.00 0.00))
 (command "TEXT" "J" "ML" p1   0.75  0.00 "DRK GRY SH")
 (command "LAYER" "S" "CGBCMNT" "")
 (setq p1 (list 577.75 1604.37) p2 (list 0.00 0.00))
 (command "TEXT" "J" "ML" p1   0.75  0.00 "CALC, SLX")
 (command "LAYER" "S" "CGBMAIN" "")
 (setq p1 (list 535.00 1602.74) p2 (list 541.00 1602.74) p3 (list 541.00 1601.89) p4 (list 535.00 1601.89))
 (command "PLINE" p1 p2 p3 p4 "c")
 (command "HATCH" "ZIGZAG" 5.00 0.00 "L" "")
 (command "COLOR" "BYLAYER")
 (command "LAYER" "S" "CGBLITHCD" "")
 (setq p1 (list 541.00 1602.32) p2 (list 542.35 1602.32))
 (command "LINE" p1 p2 "")
 (setq p1 (list 542.50 1601.94) p2 (list 0.00 0.00))
 (command "TEXT" "J" "ML" p1   0.75  0.00 "904")
 (command "LAYER" "S" "CGBTHK" "")
 (setq p1 (list 547.00 1601.94) p2 (list 0.00 0.00))
 (command "TEXT" "J" "ML" p1   0.75  0.00 "0.85")
 (command "LAYER" "S" "CGBHZID" "")
 (setq p1 (list 551.50 1601.94) p2 (list 0.00 0.00))
 (command "TEXT" "J" "ML" p1   0.75  0.00 "")
 (setq p1 (list 553.75 1601.94) p2 (list 0.00 0.00))
 (command "TEXT" "J" "ML" p1   0.75  0.00 "7451")
 (command "LAYER" "S" "CGBLITHTXT" "")
 (setq p1 (list 557.50 1601.94) p2 (list 0.00 0.00))
 (command "TEXT" "J" "ML" p1   0.75  0.00 "MASS FN GRND LS")
 (command "LAYER" "S" "CGBCMNT" "")
 (setq p1 (list 577.75 1601.94) p2 (list 0.00 0.00))
 (command "TEXT" "J" "ML" p1   0.75  0.00 "SLC")
 (command "LAYER" "S" "CGBMAIN" "")
 (setq p1 (list 535.00 1601.89) p2 (list 541.00 1601.89) p3 (list 541.00 1601.26) p4 (list 535.00 1601.26))
 (command "PLINE" p1 p2 p3 p4 "c")
 (command "HATCH" "ZIGZAG" 4.00 0.00 "L" "")
 (command "COLOR" "BYLAYER")
 (command "LAYER" "S" "CGBLITHCD" "")
 (setq p1 (list 541.00 1601.58) p2 (list 542.35 1600.33))
 (command "LINE" p1 p2 "")
 (setq p1 (list 542.50 1599.95) p2 (list 0.00 0.00))
 (command "TEXT" "J" "ML" p1   0.75  0.00 "124")
 (command "LAYER" "S" "CGBTHK" "")
 (setq p1 (list 547.00 1599.95) p2 (list 0.00 0.00))
 (command "TEXT" "J" "ML" p1   0.75  0.00 "0.63")
 (command "LAYER" "S" "CGBHZID" "")
 (setq p1 (list 551.50 1599.95) p2 (list 0.00 0.00))
 (command "TEXT" "J" "ML" p1   0.75  0.00 "")
 (setq p1 (list 553.75 1599.95) p2 (list 0.00 0.00))
 (command "TEXT" "J" "ML" p1   0.75  0.00 "7451")
 (command "LAYER" "S" "CGBLITHTXT" "")
 (setq p1 (list 557.50 1599.95) p2 (list 0.00 0.00))
 (command "TEXT" "J" "ML" p1   0.75  0.00 "DRK GRY SH")
 (command "LAYER" "S" "CGBCMNT" "")
 (setq p1 (list 577.75 1599.95) p2 (list 0.00 0.00))
 (command "TEXT" "J" "ML" p1   0.75  0.00 "")
 (command "LAYER" "S" "CGBMAIN" "")
 (setq p1 (list 535.00 1601.26) p2 (list 541.00 1601.26) p3 (list 541.00 1593.72) p4 (list 535.00 1593.72))
 (command "PLINE" p1 p2 p3 p4 "c")
 (command "HATCH" "ZIGZAG" 5.00 0.00 "L" "")
 (command "COLOR" "BYLAYER")
 (command "LAYER" "S" "CGBLITHCD" "")
 (setq p1 (list 541.00 1597.49) p2 (list 542.35 1597.49))
 (command "LINE" p1 p2 "")
 (setq p1 (list 542.50 1597.12) p2 (list 0.00 0.00))
 (command "TEXT" "J" "ML" p1   0.75  0.00 "224")
 (command "LAYER" "S" "CGBTHK" "")
 (setq p1 (list 547.00 1597.12) p2 (list 0.00 0.00))
 (command "TEXT" "J" "ML" p1   0.75  0.00 "7.54")
 (command "LAYER" "S" "CGBHZID" "")
 (setq p1 (list 551.50 1597.12) p2 (list 0.00 0.00))
 (command "TEXT" "J" "ML" p1   0.75  0.00 "")
 (setq p1 (list 553.75 1597.12) p2 (list 0.00 0.00))
 (command "TEXT" "J" "ML" p1   0.75  0.00 "7451")
 (command "LAYER" "S" "CGBLITHTXT" "")
 (setq p1 (list 557.50 1597.12) p2 (list 0.00 0.00))
 (command "TEXT" "J" "ML" p1   0.75  0.00 "DRK GRY SH W/LS NODS")
 (command "LAYER" "S" "CGBCMNT" "")
 (setq p1 (list 577.75 1597.12) p2 (list 0.00 0.00))
 (command "TEXT" "J" "ML" p1   0.75  0.00 "")
 (command "LAYER" "S" "CGBMAIN" "")
 (setq p1 (list 535.00 1593.72) p2 (list 541.00 1593.72) p3 (list 541.00 1593.49) p4 (list 535.00 1593.49))
 (command "PLINE" p1 p2 p3 p4 "c")
 (command "HATCH" "ZIGZAG" 5.00 0.00 "L" "")
 (command "COLOR" "BYLAYER")
 (command "LAYER" "S" "CGBLITHCD" "")
 (setq p1 (list 541.00 1593.61) p2 (list 542.35 1593.61))
 (command "LINE" p1 p2 "")
 (setq p1 (list 542.50 1593.23) p2 (list 0.00 0.00))
 (command "TEXT" "J" "ML" p1   0.75  0.00 "904")
 (command "LAYER" "S" "CGBTHK" "")
 (setq p1 (list 547.00 1593.23) p2 (list 0.00 0.00))
 (command "TEXT" "J" "ML" p1   0.75  0.00 "0.23")
 (command "LAYER" "S" "CGBHZID" "")
 (setq p1 (list 551.50 1593.23) p2 (list 0.00 0.00))
 (command "TEXT" "J" "ML" p1   0.75  0.00 "")
 (setq p1 (list 553.75 1593.23) p2 (list 0.00 0.00))
 (command "TEXT" "J" "ML" p1   0.75  0.00 "7451")
 (command "LAYER" "S" "CGBLITHTXT" "")
 (setq p1 (list 557.50 1593.23) p2 (list 0.00 0.00))
 (command "TEXT" "J" "ML" p1   0.75  0.00 "MASS FN GRND LS")
 (command "LAYER" "S" "CGBCMNT" "")
 (setq p1 (list 577.75 1593.23) p2 (list 0.00 0.00))
 (command "TEXT" "J" "ML" p1   0.75  0.00 "")
 (command "LAYER" "S" "CGBMAIN" "")
 (setq p1 (list 535.00 1593.49) p2 (list 541.00 1593.49) p3 (list 541.00 1592.53) p4 (list 535.00 1592.53))
 (command "PLINE" p1 p2 p3 p4 "c")
 (command "HATCH" "ZIGZAG" 4.00 0.00 "L" "")
 (command "COLOR" "BYLAYER")
 (command "LAYER" "S" "CGBLITHCD" "")
 (setq p1 (list 541.00 1593.01) p2 (list 542.35 1591.76))
 (command "LINE" p1 p2 "")
 (setq p1 (list 542.50 1591.39) p2 (list 0.00 0.00))
 (command "TEXT" "J" "ML" p1   0.75  0.00 "125")
 (command "LAYER" "S" "CGBTHK" "")
 (setq p1 (list 547.00 1591.39) p2 (list 0.00 0.00))
 (command "TEXT" "J" "ML" p1   0.75  0.00 "0.96")
 (command "LAYER" "S" "CGBHZID" "")
 (setq p1 (list 551.50 1591.39) p2 (list 0.00 0.00))
 (command "TEXT" "J" "ML" p1   0.75  0.00 "")
 (setq p1 (list 553.75 1591.39) p2 (list 0.00 0.00))
 (command "TEXT" "J" "ML" p1   0.75  0.00 "7451")
 (command "LAYER" "S" "CGBLITHTXT" "")
 (setq p1 (list 557.50 1591.39) p2 (list 0.00 0.00))
 (command "TEXT" "J" "ML" p1   0.75  0.00 "DRK GRY CHRND SH")
 (command "LAYER" "S" "CGBCMNT" "")
 (setq p1 (list 577.75 1591.39) p2 (list 0.00 0.00))
 (command "TEXT" "J" "ML" p1   0.75  0.00 "BURS, CARB")
 (command "LAYER" "S" "CGBMAIN" "")
 (setq p1 (list 535.00 1592.53) p2 (list 541.00 1592.53) p3 (list 541.00 1591.74) p4 (list 535.00 1591.74))
 (command "PLINE" p1 p2 p3 p4 "c")
 (command "HATCH" "ZIGZAG" 5.00 0.00 "L" "")
 (command "COLOR" "BYLAYER")
 (command "LAYER" "S" "CGBLITHCD" "")
 (setq p1 (list 541.00 1592.14) p2 (list 542.35 1590.51))
 (command "LINE" p1 p2 "")
 (setq p1 (list 542.50 1590.14) p2 (list 0.00 0.00))
 (command "TEXT" "J" "ML" p1   0.75  0.00 "227")
 (command "LAYER" "S" "CGBTHK" "")
 (setq p1 (list 547.00 1590.14) p2 (list 0.00 0.00))
 (command "TEXT" "J" "ML" p1   0.75  0.00 "0.79")
 (command "LAYER" "S" "CGBHZID" "")
 (setq p1 (list 551.50 1590.14) p2 (list 0.00 0.00))
 (command "TEXT" "J" "ML" p1   0.75  0.00 "")
 (setq p1 (list 553.75 1590.14) p2 (list 0.00 0.00))
 (command "TEXT" "J" "ML" p1   0.75  0.00 "7451")
 (command "LAYER" "S" "CGBLITHTXT" "")
 (setq p1 (list 557.50 1590.14) p2 (list 0.00 0.00))
 (command "TEXT" "J" "ML" p1   0.75  0.00 "DRK GRY FIRECLAY W/LS NOD")
 (command "LAYER" "S" "CGBCMNT" "")
 (setq p1 (list 577.75 1590.14) p2 (list 0.00 0.00))
 (command "TEXT" "J" "ML" p1   0.75  0.00 "MTTLD")
 (command "LAYER" "S" "CGBMAIN" "")
 (setq p1 (list 535.00 1591.74) p2 (list 541.00 1591.74) p3 (list 541.00 1589.22) p4 (list 535.00 1589.22))
 (command "PLINE" p1 p2 p3 p4 "c")
 (command "HATCH" "ZIGZAG" 5.00 0.00 "L" "")
 (command "COLOR" "BYLAYER")
 (command "LAYER" "S" "CGBLITHCD" "")
 (setq p1 (list 541.00 1590.48) p2 (list 542.35 1589.26))
 (command "LINE" p1 p2 "")
 (setq p1 (list 542.50 1588.89) p2 (list 0.00 0.00))
 (command "TEXT" "J" "ML" p1   0.75  0.00 "224")
 (command "LAYER" "S" "CGBTHK" "")
 (setq p1 (list 547.00 1588.89) p2 (list 0.00 0.00))
 (command "TEXT" "J" "ML" p1   0.75  0.00 "2.52")
 (command "LAYER" "S" "CGBHZID" "")
 (setq p1 (list 551.50 1588.89) p2 (list 0.00 0.00))
 (command "TEXT" "J" "ML" p1   0.75  0.00 "")
 (setq p1 (list 553.75 1588.89) p2 (list 0.00 0.00))
 (command "TEXT" "J" "ML" p1   0.75  0.00 "7451")
 (command "LAYER" "S" "CGBLITHTXT" "")
 (setq p1 (list 557.50 1588.89) p2 (list 0.00 0.00))
 (command "TEXT" "J" "ML" p1   0.75  0.00 "DRK GRY SH W/LS NODS")
 (command "LAYER" "S" "CGBCMNT" "")
 (setq p1 (list 577.75 1588.89) p2 (list 0.00 0.00))
 (command "TEXT" "J" "ML" p1   0.75  0.00 "GB")
 (command "LAYER" "S" "CGBMAIN" "")
 (setq p1 (list 535.00 1589.22) p2 (list 541.00 1589.22) p3 (list 541.00 1582.25) p4 (list 535.00 1582.25))
 (command "PLINE" p1 p2 p3 p4 "c")
 (command "HATCH" "ZIGZAG" 4.00 0.00 "L" "")
 (command "COLOR" "BYLAYER")
 (command "LAYER" "S" "CGBLITHCD" "")
 (setq p1 (list 541.00 1585.74) p2 (list 542.35 1585.74))
 (command "LINE" p1 p2 "")
 (setq p1 (list 542.50 1585.36) p2 (list 0.00 0.00))
 (command "TEXT" "J" "ML" p1   0.75  0.00 "424")
 (command "LAYER" "S" "CGBTHK" "")
 (setq p1 (list 547.00 1585.36) p2 (list 0.00 0.00))
 (command "TEXT" "J" "ML" p1   0.75  0.00 "6.97")
 (command "LAYER" "S" "CGBHZID" "")
 (setq p1 (list 551.50 1585.36) p2 (list 0.00 0.00))
 (command "TEXT" "J" "ML" p1   0.75  0.00 "")
 (setq p1 (list 553.75 1585.36) p2 (list 0.00 0.00))
 (command "TEXT" "J" "ML" p1   0.75  0.00 "7451")
 (command "LAYER" "S" "CGBLITHTXT" "")
 (setq p1 (list 557.50 1585.36) p2 (list 0.00 0.00))
 (command "TEXT" "J" "ML" p1   0.75  0.00 "DRK GRY SDY SH W/LS NODS")
 (command "LAYER" "S" "CGBCMNT" "")
 (setq p1 (list 577.75 1585.36) p2 (list 0.00 0.00))
 (command "TEXT" "J" "ML" p1   0.75  0.00 "")
 (command "LAYER" "S" "CGBMAIN" "")
 (setq p1 (list 535.00 1582.25) p2 (list 541.00 1582.25) p3 (list 541.00 1576.74) p4 (list 535.00 1576.74))
 (command "PLINE" p1 p2 p3 p4 "c")
 (command "HATCH" "ZIGZAG" 4.00 0.00 "L" "")
 (command "COLOR" "BYLAYER")
 (command "LAYER" "S" "CGBLITHCD" "")
 (setq p1 (list 541.00 1579.50) p2 (list 542.35 1579.50))
 (command "LINE" p1 p2 "")
 (setq p1 (list 542.50 1579.12) p2 (list 0.00 0.00))
 (command "TEXT" "J" "ML" p1   0.75  0.00 "125")
 (command "LAYER" "S" "CGBTHK" "")
 (setq p1 (list 547.00 1579.12) p2 (list 0.00 0.00))
 (command "TEXT" "J" "ML" p1   0.75  0.00 "5.51")
 (command "LAYER" "S" "CGBHZID" "")
 (setq p1 (list 551.50 1579.12) p2 (list 0.00 0.00))
 (command "TEXT" "J" "ML" p1   0.75  0.00 "")
 (setq p1 (list 553.75 1579.12) p2 (list 0.00 0.00))
 (command "TEXT" "J" "ML" p1   0.75  0.00 "7451")
 (command "LAYER" "S" "CGBLITHTXT" "")
 (setq p1 (list 557.50 1579.12) p2 (list 0.00 0.00))
 (command "TEXT" "J" "ML" p1   0.75  0.00 "DRK GRY CHRND SH")
 (command "LAYER" "S" "CGBCMNT" "")
 (setq p1 (list 577.75 1579.12) p2 (list 0.00 0.00))
 (command "TEXT" "J" "ML" p1   0.75  0.00 "SFT,SLX,BRKN")
 (command "LAYER" "S" "CGBMAIN" "")
 (setq p1 (list 535.00 1576.74) p2 (list 541.00 1576.74) p3 (list 541.00 1576.68) p4 (list 535.00 1576.68))
 (command "PLINE" p1 p2 p3 p4 "c")
 (command "HATCH" "ZIGZAG" 4.00 0.00 "L" "")
 (command "COLOR" "BYLAYER")
 (command "LAYER" "S" "CGBLITHCD" "")
 (setq p1 (list 541.00 1576.71) p2 (list 542.35 1576.71))
 (command "LINE" p1 p2 "")
 (setq p1 (list 542.50 1576.34) p2 (list 0.00 0.00))
 (command "TEXT" "J" "ML" p1   0.75  0.00 "125")
 (command "LAYER" "S" "CGBTHK" "")
 (setq p1 (list 547.00 1576.34) p2 (list 0.00 0.00))
 (command "TEXT" "J" "ML" p1   0.75  0.00 "0.06")
 (command "LAYER" "S" "CGBHZID" "")
 (setq p1 (list 551.50 1576.34) p2 (list 0.00 0.00))
 (command "TEXT" "J" "ML" p1   0.75  0.00 "")
 (setq p1 (list 553.75 1576.34) p2 (list 0.00 0.00))
 (command "TEXT" "J" "ML" p1   0.75  0.00 "7451")
 (command "LAYER" "S" "CGBLITHTXT" "")
 (setq p1 (list 557.50 1576.34) p2 (list 0.00 0.00))
 (command "TEXT" "J" "ML" p1   0.75  0.00 "DRK GRY CHRND SH")
 (command "LAYER" "S" "CGBCMNT" "")
 (setq p1 (list 577.75 1576.34) p2 (list 0.00 0.00))
 (command "TEXT" "J" "ML" p1   0.75  0.00 "")
 (command "LAYER" "S" "CGBMAIN" "")
 (setq p1 (list 535.00 1576.68) p2 (list 541.00 1576.68) p3 (list 541.00 1572.97) p4 (list 535.00 1572.97))
 (command "PLINE" p1 p2 p3 p4 "c")
 (command "HATCH" "ZIGZAG" 5.00 0.00 "L" "")
 (command "COLOR" "BYLAYER")
 (command "LAYER" "S" "CGBLITHCD" "")
 (setq p1 (list 541.00 1574.83) p2 (list 542.35 1574.83))
 (command "LINE" p1 p2 "")
 (setq p1 (list 542.50 1574.45) p2 (list 0.00 0.00))
 (command "TEXT" "J" "ML" p1   0.75  0.00 "224")
 (command "LAYER" "S" "CGBTHK" "")
 (setq p1 (list 547.00 1574.45) p2 (list 0.00 0.00))
 (command "TEXT" "J" "ML" p1   0.75  0.00 "3.71")
 (command "LAYER" "S" "CGBHZID" "")
 (setq p1 (list 551.50 1574.45) p2 (list 0.00 0.00))
 (command "TEXT" "J" "ML" p1   0.75  0.00 "")
 (setq p1 (list 553.75 1574.45) p2 (list 0.00 0.00))
 (command "TEXT" "J" "ML" p1   0.75  0.00 "7451")
 (command "LAYER" "S" "CGBLITHTXT" "")
 (setq p1 (list 557.50 1574.45) p2 (list 0.00 0.00))
 (command "TEXT" "J" "ML" p1   0.75  0.00 "DRK GRY SH W/LS NODS")
 (command "LAYER" "S" "CGBCMNT" "")
 (setq p1 (list 577.75 1574.45) p2 (list 0.00 0.00))
 (command "TEXT" "J" "ML" p1   0.75  0.00 "CALC VEINS")
 (command "LAYER" "S" "CGBMAIN" "")
 (setq p1 (list 535.00 1572.97) p2 (list 541.00 1572.97) p3 (list 541.00 1572.49) p4 (list 535.00 1572.49))
 (command "PLINE" p1 p2 p3 p4 "c")
 (command "HATCH" "ZIGZAG" 4.00 22.50 "L" "")
 (command "COLOR" "BYLAYER")
 (command "LAYER" "S" "CGBLITHCD" "")
 (setq p1 (list 541.00 1572.73) p2 (list 542.35 1572.73))
 (command "LINE" p1 p2 "")
 (setq p1 (list 542.50 1572.36) p2 (list 0.00 0.00))
 (command "TEXT" "J" "ML" p1   0.75  0.00 "114")
 (command "LAYER" "S" "CGBTHK" "")
 (setq p1 (list 547.00 1572.36) p2 (list 0.00 0.00))
 (command "TEXT" "J" "ML" p1   0.75  0.00 "0.48")
 (command "LAYER" "S" "CGBHZID" "")
 (setq p1 (list 551.50 1572.36) p2 (list 0.00 0.00))
 (command "TEXT" "J" "ML" p1   0.75  0.00 "")
 (setq p1 (list 553.75 1572.36) p2 (list 0.00 0.00))
 (command "TEXT" "J" "ML" p1   0.75  0.00 "7451")
 (command "LAYER" "S" "CGBLITHTXT" "")
 (setq p1 (list 557.50 1572.36) p2 (list 0.00 0.00))
 (command "TEXT" "J" "ML" p1   0.75  0.00 "BLK SH")
 (command "LAYER" "S" "CGBCMNT" "")
 (setq p1 (list 577.75 1572.36) p2 (list 0.00 0.00))
 (command "TEXT" "J" "ML" p1   0.75  0.00 "")
 (command "LAYER" "S" "CGBMAIN" "")
 (setq p1 (list 535.00 1572.49) p2 (list 541.00 1572.49) p3 (list 541.00 1570.33) p4 (list 535.00 1570.33))
 (command "PLINE" p1 p2 p3 p4 "c")
 (command "HATCH" "ZIGZAG" 0.25 0.00 "L" "")
 (command "COLOR" "BYLAYER")
 (command "LAYER" "S" "CGBLITHCD" "")
 (setq p1 (list 541.00 1571.41) p2 (list 542.35 1571.41))
 (command "LINE" p1 p2 "")
 (setq p1 (list 542.50 1571.04) p2 (list 0.00 0.00))
 (command "TEXT" "J" "ML" p1   0.75  0.00 "127")
 (command "LAYER" "S" "CGBTHK" "")
 (setq p1 (list 547.00 1571.04) p2 (list 0.00 0.00))
 (command "TEXT" "J" "ML" p1   0.75  0.00 "2.16")
 (command "LAYER" "S" "CGBHZID" "")
 (setq p1 (list 551.50 1571.04) p2 (list 0.00 0.00))
 (command "TEXT" "J" "ML" p1   0.75  0.00 "")
 (setq p1 (list 553.75 1571.04) p2 (list 0.00 0.00))
 (command "TEXT" "J" "ML" p1   0.75  0.00 "7451")
 (command "LAYER" "S" "CGBLITHTXT" "")
 (setq p1 (list 557.50 1571.04) p2 (list 0.00 0.00))
 (command "TEXT" "J" "ML" p1   0.75  0.00 "DRK GRY FIRECLAY")
 (command "LAYER" "S" "CGBCMNT" "")
 (setq p1 (list 577.75 1571.04) p2 (list 0.00 0.00))
 (command "TEXT" "J" "ML" p1   0.75  0.00 "SLX,BRKN")
 (command "LAYER" "S" "CGBMAIN" "")
 (setq p1 (list 535.00 1570.33) p2 (list 541.00 1570.33) p3 (list 541.00 1568.52) p4 (list 535.00 1568.52))
 (command "PLINE" p1 p2 p3 p4 "c")
 (command "HATCH" "ZIGZAG" 10.00 45.00 "L" "")
 (command "COLOR" "BYLAYER")
 (command "LAYER" "S" "CGBLITHCD" "")
 (setq p1 (list 541.00 1569.43) p2 (list 542.35 1569.43))
 (command "LINE" p1 p2 "")
 (setq p1 (list 542.50 1569.05) p2 (list 0.00 0.00))
 (command "TEXT" "J" "ML" p1   0.75  0.00 "094")
 (command "LAYER" "S" "CGBTHK" "")
 (setq p1 (list 547.00 1569.05) p2 (list 0.00 0.00))
 (command "TEXT" "J" "ML" p1   0.75  0.00 "1.81")
 (command "LAYER" "S" "CGBHZID" "")
 (setq p1 (list 551.50 1569.05) p2 (list 0.00 0.00))
 (command "TEXT" "J" "ML" p1   0.75  0.00 "")
 (setq p1 (list 553.75 1569.05) p2 (list 0.00 0.00))
 (command "TEXT" "J" "ML" p1   0.75  0.00 "7451")
 (command "LAYER" "S" "CGBLITHTXT" "")
 (setq p1 (list 557.50 1569.05) p2 (list 0.00 0.00))
 (command "TEXT" "J" "ML" p1   0.75  0.00 "MASS FLINT CLAY")
 (command "LAYER" "S" "CGBCMNT" "")
 (setq p1 (list 577.75 1569.05) p2 (list 0.00 0.00))
 (command "TEXT" "J" "ML" p1   0.75  0.00 "")
 (command "LAYER" "S" "CGBMAIN" "")
 (setq p1 (list 535.00 1568.52) p2 (list 541.00 1568.52) p3 (list 541.00 1566.21) p4 (list 535.00 1566.21))
 (command "PLINE" p1 p2 p3 p4 "c")
 (command "HATCH" "ZIGZAG" 2.00 45.00 "L" "")
 (command "COLOR" "BYLAYER")
 (command "LAYER" "S" "CGBLITHCD" "")
 (setq p1 (list 541.00 1567.37) p2 (list 542.35 1567.37))
 (command "LINE" p1 p2 "")
 (setq p1 (list 542.50 1566.99) p2 (list 0.00 0.00))
 (command "TEXT" "J" "ML" p1   0.75  0.00 "313")
 (command "LAYER" "S" "CGBTHK" "")
 (setq p1 (list 547.00 1566.99) p2 (list 0.00 0.00))
 (command "TEXT" "J" "ML" p1   0.75  0.00 "2.31")
 (command "LAYER" "S" "CGBHZID" "")
 (setq p1 (list 551.50 1566.99) p2 (list 0.00 0.00))
 (command "TEXT" "J" "ML" p1   0.75  0.00 "")
 (setq p1 (list 553.75 1566.99) p2 (list 0.00 0.00))
 (command "TEXT" "J" "ML" p1   0.75  0.00 "7451")
 (command "LAYER" "S" "CGBLITHTXT" "")
 (setq p1 (list 557.50 1566.99) p2 (list 0.00 0.00))
 (command "TEXT" "J" "ML" p1   0.75  0.00 "BLK SH W/SS STKS")
 (command "LAYER" "S" "CGBCMNT" "")
 (setq p1 (list 577.75 1566.99) p2 (list 0.00 0.00))
 (command "TEXT" "J" "ML" p1   0.75  0.00 "SLGHT ANG BED")
 (command "LAYER" "S" "CGBMAIN" "")
 (setq p1 (list 535.00 1566.21) p2 (list 541.00 1566.21) p3 (list 541.00 1564.71) p4 (list 535.00 1564.71))
 (command "PLINE" p1 p2 p3 p4 "c")
 (command "HATCH" "ZIGZAG" 4.00 0.00 "L" "")
 (command "COLOR" "BYLAYER")
 (command "LAYER" "S" "CGBLITHCD" "")
 (setq p1 (list 541.00 1565.46) p2 (list 542.35 1565.46))
 (command "LINE" p1 p2 "")
 (setq p1 (list 542.50 1565.09) p2 (list 0.00 0.00))
 (command "TEXT" "J" "ML" p1   0.75  0.00 "115")
 (command "LAYER" "S" "CGBTHK" "")
 (setq p1 (list 547.00 1565.09) p2 (list 0.00 0.00))
 (command "TEXT" "J" "ML" p1   0.75  0.00 "1.50")
 (command "LAYER" "S" "CGBHZID" "")
 (setq p1 (list 551.50 1565.09) p2 (list 0.00 0.00))
 (command "TEXT" "J" "ML" p1   0.75  0.00 "")
 (setq p1 (list 553.75 1565.09) p2 (list 0.00 0.00))
 (command "TEXT" "J" "ML" p1   0.75  0.00 "7451")
 (command "LAYER" "S" "CGBLITHTXT" "")
 (setq p1 (list 557.50 1565.09) p2 (list 0.00 0.00))
 (command "TEXT" "J" "ML" p1   0.75  0.00 "BLK CHRND SH")
 (command "LAYER" "S" "CGBCMNT" "")
 (setq p1 (list 577.75 1565.09) p2 (list 0.00 0.00))
 (command "TEXT" "J" "ML" p1   0.75  0.00 "BURS,ANG BEDS")
 (command "LAYER" "S" "CGBMAIN" "")
 (setq p1 (list 535.00 1564.71) p2 (list 541.00 1564.71) p3 (list 541.00 1564.59) p4 (list 535.00 1564.59))
 (command "PLINE" p1 p2 p3 p4 "c")
 (command "HATCH" "ZIGZAG" 5.00 0.00 "L" "")
 (command "COLOR" "BYLAYER")
 (command "LAYER" "S" "CGBLITHCD" "")
 (setq p1 (list 541.00 1564.65) p2 (list 542.35 1563.40))
 (command "LINE" p1 p2 "")
 (setq p1 (list 542.50 1563.03) p2 (list 0.00 0.00))
 (command "TEXT" "J" "ML" p1   0.75  0.00 "033")
 (command "LAYER" "S" "CGBTHK" "")
 (setq p1 (list 547.00 1563.03) p2 (list 0.00 0.00))
 (command "TEXT" "J" "ML" p1   0.75  0.00 "0.12")
 (command "LAYER" "S" "CGBHZID" "")
 (setq p1 (list 551.50 1563.03) p2 (list 0.00 0.00))
 (command "TEXT" "J" "ML" p1   0.75  0.00 "")
 (setq p1 (list 553.75 1563.03) p2 (list 0.00 0.00))
 (command "TEXT" "J" "ML" p1   0.75  0.00 "7000")
 (command "LAYER" "S" "CGBLITHTXT" "")
 (setq p1 (list 557.50 1563.03) p2 (list 0.00 0.00))
 (command "TEXT" "J" "ML" p1   0.75  0.00 "BONE W/COAL STKS")
 (command "LAYER" "S" "CGBCMNT" "")
 (setq p1 (list 577.75 1563.03) p2 (list 0.00 0.00))
 (command "TEXT" "J" "ML" p1   0.75  0.00 "")
 (command "LAYER" "S" "CGBMAIN" "")
 (setq p1 (list 535.00 1564.59) p2 (list 541.00 1564.59) p3 (list 541.00 1564.41) p4 (list 535.00 1564.41))
 (command "PLINE" p1 p2 p3 p4 "c")
 (command "HATCH" "ZIGZAG" 5.00 0.00 "L" "")
 (command "COLOR" "BYLAYER")
 (command "LAYER" "S" "CGBLITHCD" "")
 (setq p1 (list 541.00 1564.50) p2 (list 542.35 1562.15))
 (command "LINE" p1 p2 "")
 (setq p1 (list 542.50 1561.78) p2 (list 0.00 0.00))
 (command "TEXT" "J" "ML" p1   0.75  0.00 "037")
 (command "LAYER" "S" "CGBTHK" "")
 (setq p1 (list 547.00 1561.78) p2 (list 0.00 0.00))
 (command "TEXT" "J" "ML" p1   0.75  0.00 "0.18")
 (command "LAYER" "S" "CGBHZID" "")
 (setq p1 (list 551.50 1561.78) p2 (list 0.00 0.00))
 (command "TEXT" "J" "ML" p1   0.75  0.00 "")
 (setq p1 (list 553.75 1561.78) p2 (list 0.00 0.00))
 (command "TEXT" "J" "ML" p1   0.75  0.00 "6951")
 (command "LAYER" "S" "CGBLITHTXT" "")
 (setq p1 (list 557.50 1561.78) p2 (list 0.00 0.00))
 (command "TEXT" "J" "ML" p1   0.75  0.00 "BONE W/SH LAYERS")
 (command "LAYER" "S" "CGBCMNT" "")
 (setq p1 (list 577.75 1561.78) p2 (list 0.00 0.00))
 (command "TEXT" "J" "ML" p1   0.75  0.00 "PYRT, BURS")
 (command "LAYER" "S" "CGBMAIN" "")
 (setq p1 (list 535.00 1564.41) p2 (list 541.00 1564.41) p3 (list 541.00 1563.74) p4 (list 535.00 1563.74))
 (command "PLINE" p1 p2 p3 p4 "c")
 (command "HATCH" "ZIGZAG" 4.00 22.50 "L" "")
 (command "COLOR" "BYLAYER")
 (command "LAYER" "S" "CGBLITHCD" "")
 (setq p1 (list 541.00 1564.08) p2 (list 542.35 1560.90))
 (command "LINE" p1 p2 "")
 (setq p1 (list 542.50 1560.53) p2 (list 0.00 0.00))
 (command "TEXT" "J" "ML" p1   0.75  0.00 "114")
 (command "LAYER" "S" "CGBTHK" "")
 (setq p1 (list 547.00 1560.53) p2 (list 0.00 0.00))
 (command "TEXT" "J" "ML" p1   0.75  0.00 "0.67")
 (command "LAYER" "S" "CGBHZID" "")
 (setq p1 (list 551.50 1560.53) p2 (list 0.00 0.00))
 (command "TEXT" "J" "ML" p1   0.75  0.00 "")
 (setq p1 (list 553.75 1560.53) p2 (list 0.00 0.00))
 (command "TEXT" "J" "ML" p1   0.75  0.00 "6951")
 (command "LAYER" "S" "CGBLITHTXT" "")
 (setq p1 (list 557.50 1560.53) p2 (list 0.00 0.00))
 (command "TEXT" "J" "ML" p1   0.75  0.00 "BLK SH")
 (command "LAYER" "S" "CGBCMNT" "")
 (setq p1 (list 577.75 1560.53) p2 (list 0.00 0.00))
 (command "TEXT" "J" "ML" p1   0.75  0.00 "V BONEY")
 (command "LAYER" "S" "CGBMAIN" "")
 (setq p1 (list 535.00 1563.74) p2 (list 541.00 1563.74) p3 (list 541.00 1563.12) p4 (list 535.00 1563.12))
 (command "PLINE" p1 p2 p3 p4 "c")
 (command "HATCH" "ZIGZAG" 5.00 0.00 "L" "")
 (command "COLOR" "BYLAYER")
 (command "LAYER" "S" "CGBLITHCD" "")
 (setq p1 (list 541.00 1563.43) p2 (list 542.35 1559.65))
 (command "LINE" p1 p2 "")
 (setq p1 (list 542.50 1559.28) p2 (list 0.00 0.00))
 (command "TEXT" "J" "ML" p1   0.75  0.00 "038")
 (command "LAYER" "S" "CGBTHK" "")
 (setq p1 (list 547.00 1559.28) p2 (list 0.00 0.00))
 (command "TEXT" "J" "ML" p1   0.75  0.00 "0.62")
 (command "LAYER" "S" "CGBHZID" "")
 (setq p1 (list 551.50 1559.28) p2 (list 0.00 0.00))
 (command "TEXT" "J" "ML" p1   0.75  0.00 "")
 (setq p1 (list 553.75 1559.28) p2 (list 0.00 0.00))
 (command "TEXT" "J" "ML" p1   0.75  0.00 "6951")
 (command "LAYER" "S" "CGBLITHTXT" "")
 (setq p1 (list 557.50 1559.28) p2 (list 0.00 0.00))
 (command "TEXT" "J" "ML" p1   0.75  0.00 "BONE W/SH STKS")
 (command "LAYER" "S" "CGBCMNT" "")
 (setq p1 (list 577.75 1559.28) p2 (list 0.00 0.00))
 (command "TEXT" "J" "ML" p1   0.75  0.00 "BRKN,SLX, CAL")
 (command "LAYER" "S" "CGBMAIN" "")
 (setq p1 (list 535.00 1563.12) p2 (list 541.00 1563.12) p3 (list 541.00 1562.02) p4 (list 535.00 1562.02))
 (command "PLINE" p1 p2 p3 p4 "c")
 (command "HATCH" "ZIGZAG" 0.25 0.00 "L" "")
 (command "COLOR" "BYLAYER")
 (command "LAYER" "S" "CGBLITHCD" "")
 (setq p1 (list 541.00 1562.57) p2 (list 542.35 1558.40))
 (command "LINE" p1 p2 "")
 (setq p1 (list 542.50 1558.03) p2 (list 0.00 0.00))
 (command "TEXT" "J" "ML" p1   0.75  0.00 "127")
 (command "LAYER" "S" "CGBTHK" "")
 (setq p1 (list 547.00 1558.03) p2 (list 0.00 0.00))
 (command "TEXT" "J" "ML" p1   0.75  0.00 "1.10")
 (command "LAYER" "S" "CGBHZID" "")
 (setq p1 (list 551.50 1558.03) p2 (list 0.00 0.00))
 (command "TEXT" "J" "ML" p1   0.75  0.00 "")
 (setq p1 (list 553.75 1558.03) p2 (list 0.00 0.00))
 (command "TEXT" "J" "ML" p1   0.75  0.00 "6951")
 (command "LAYER" "S" "CGBLITHTXT" "")
 (setq p1 (list 557.50 1558.03) p2 (list 0.00 0.00))
 (command "TEXT" "J" "ML" p1   0.75  0.00 "DRK GRY FIRECLAY")
 (command "LAYER" "S" "CGBCMNT" "")
 (setq p1 (list 577.75 1558.03) p2 (list 0.00 0.00))
 (command "TEXT" "J" "ML" p1   0.75  0.00 "")
 (command "LAYER" "S" "CGBMAIN" "")
 (setq p1 (list 535.00 1562.02) p2 (list 541.00 1562.02) p3 (list 541.00 1561.74) p4 (list 535.00 1561.74))
 (command "PLINE" p1 p2 p3 p4 "c")
 (command "HATCH" "ZIGZAG" 4.00 0.00 "L" "")
 (command "COLOR" "BYLAYER")
 (command "LAYER" "S" "CGBLITHCD" "")
 (setq p1 (list 541.00 1561.88) p2 (list 542.35 1557.15))
 (command "LINE" p1 p2 "")
 (setq p1 (list 542.50 1556.78) p2 (list 0.00 0.00))
 (command "TEXT" "J" "ML" p1   0.75  0.00 "123")
 (command "LAYER" "S" "CGBTHK" "")
 (setq p1 (list 547.00 1556.78) p2 (list 0.00 0.00))
 (command "TEXT" "J" "ML" p1   0.75  0.00 "0.28")
 (command "LAYER" "S" "CGBHZID" "")
 (setq p1 (list 551.50 1556.78) p2 (list 0.00 0.00))
 (command "TEXT" "J" "ML" p1   0.75  0.00 "")
 (setq p1 (list 553.75 1556.78) p2 (list 0.00 0.00))
 (command "TEXT" "J" "ML" p1   0.75  0.00 "6951")
 (command "LAYER" "S" "CGBLITHTXT" "")
 (setq p1 (list 557.50 1556.78) p2 (list 0.00 0.00))
 (command "TEXT" "J" "ML" p1   0.75  0.00 "DRK GRY SH W/COAL STKS")
 (command "LAYER" "S" "CGBCMNT" "")
 (setq p1 (list 577.75 1556.78) p2 (list 0.00 0.00))
 (command "TEXT" "J" "ML" p1   0.75  0.00 "")
 (command "LAYER" "S" "CGBMAIN" "")
 (setq p1 (list 535.00 1561.74) p2 (list 541.00 1561.74) p3 (list 541.00 1560.43) p4 (list 535.00 1560.43))
 (command "PLINE" p1 p2 p3 p4 "c")
 (command "HATCH" "ZIGZAG" 0.25 0.00 "L" "")
 (command "COLOR" "BYLAYER")
 (command "LAYER" "S" "CGBLITHCD" "")
 (setq p1 (list 541.00 1561.09) p2 (list 542.35 1555.90))
 (command "LINE" p1 p2 "")
 (setq p1 (list 542.50 1555.53) p2 (list 0.00 0.00))
 (command "TEXT" "J" "ML" p1   0.75  0.00 "117")
 (command "LAYER" "S" "CGBTHK" "")
 (setq p1 (list 547.00 1555.53) p2 (list 0.00 0.00))
 (command "TEXT" "J" "ML" p1   0.75  0.00 "1.31")
 (command "LAYER" "S" "CGBHZID" "")
 (setq p1 (list 551.50 1555.53) p2 (list 0.00 0.00))
 (command "TEXT" "J" "ML" p1   0.75  0.00 "")
 (setq p1 (list 553.75 1555.53) p2 (list 0.00 0.00))
 (command "TEXT" "J" "ML" p1   0.75  0.00 "6951")
 (command "LAYER" "S" "CGBLITHTXT" "")
 (setq p1 (list 557.50 1555.53) p2 (list 0.00 0.00))
 (command "TEXT" "J" "ML" p1   0.75  0.00 "BLK FIRECLAY")
 (command "LAYER" "S" "CGBCMNT" "")
 (setq p1 (list 577.75 1555.53) p2 (list 0.00 0.00))
 (command "TEXT" "J" "ML" p1   0.75  0.00 "SLC,CALCT STK")
 (command "LAYER" "S" "CGBMAIN" "")
 (setq p1 (list 535.00 1560.43) p2 (list 541.00 1560.43) p3 (list 541.00 1560.18) p4 (list 535.00 1560.18))
 (command "PLINE" p1 p2 p3 p4 "c")
 (command "HATCH" "ZIGZAG" 2.50 90.00 "L" "")
 (command "COLOR" "BYLAYER")
 (command "LAYER" "S" "CGBLITHCD" "")
 (setq p1 (list 541.00 1560.31) p2 (list 542.35 1554.65))
 (command "LINE" p1 p2 "")
 (setq p1 (list 542.50 1554.28) p2 (list 0.00 0.00))
 (command "TEXT" "J" "ML" p1   0.75  0.00 "328")
 (command "LAYER" "S" "CGBTHK" "")
 (setq p1 (list 547.00 1554.28) p2 (list 0.00 0.00))
 (command "TEXT" "J" "ML" p1   0.75  0.00 "0.25")
 (command "LAYER" "S" "CGBHZID" "")
 (setq p1 (list 551.50 1554.28) p2 (list 0.00 0.00))
 (command "TEXT" "J" "ML" p1   0.75  0.00 "")
 (setq p1 (list 553.75 1554.28) p2 (list 0.00 0.00))
 (command "TEXT" "J" "ML" p1   0.75  0.00 "6951")
 (command "LAYER" "S" "CGBLITHTXT" "")
 (setq p1 (list 557.50 1554.28) p2 (list 0.00 0.00))
 (command "TEXT" "J" "ML" p1   0.75  0.00 "DRK GRY BURROWED SDY SH")
 (command "LAYER" "S" "CGBCMNT" "")
 (setq p1 (list 577.75 1554.28) p2 (list 0.00 0.00))
 (command "TEXT" "J" "ML" p1   0.75  0.00 "")
 (command "LAYER" "S" "CGBMAIN" "")
 (setq p1 (list 535.00 1560.18) p2 (list 541.00 1560.18) p3 (list 541.00 1559.03) p4 (list 535.00 1559.03))
 (command "PLINE" p1 p2 p3 p4 "c")
 (command "HATCH" "ZIGZAG" 2.50 90.00 "L" "")
 (command "COLOR" "BYLAYER")
 (command "LAYER" "S" "CGBLITHCD" "")
 (setq p1 (list 541.00 1559.61) p2 (list 542.35 1553.40))
 (command "LINE" p1 p2 "")
 (setq p1 (list 542.50 1553.03) p2 (list 0.00 0.00))
 (command "TEXT" "J" "ML" p1   0.75  0.00 "318")
 (command "LAYER" "S" "CGBTHK" "")
 (setq p1 (list 547.00 1553.03) p2 (list 0.00 0.00))
 (command "TEXT" "J" "ML" p1   0.75  0.00 "1.15")
 (command "LAYER" "S" "CGBHZID" "")
 (setq p1 (list 551.50 1553.03) p2 (list 0.00 0.00))
 (command "TEXT" "J" "ML" p1   0.75  0.00 "")
 (setq p1 (list 553.75 1553.03) p2 (list 0.00 0.00))
 (command "TEXT" "J" "ML" p1   0.75  0.00 "6951")
 (command "LAYER" "S" "CGBLITHTXT" "")
 (setq p1 (list 557.50 1553.03) p2 (list 0.00 0.00))
 (command "TEXT" "J" "ML" p1   0.75  0.00 "BLK BURROWED SDY SH")
 (command "LAYER" "S" "CGBCMNT" "")
 (setq p1 (list 577.75 1553.03) p2 (list 0.00 0.00))
 (command "TEXT" "J" "ML" p1   0.75  0.00 "")
 (command "LAYER" "S" "CGBMAIN" "")
 (setq p1 (list 535.00 1559.03) p2 (list 541.00 1559.03) p3 (list 541.00 1558.86) p4 (list 535.00 1558.86))
 (command "PLINE" p1 p2 p3 p4 "c")
 (command "HATCH" "ZIGZAG" 5.00 0.00 "L" "")
 (command "COLOR" "BYLAYER")
 (command "LAYER" "S" "CGBLITHCD" "")
 (setq p1 (list 541.00 1558.95) p2 (list 542.35 1552.15))
 (command "LINE" p1 p2 "")
 (setq p1 (list 542.50 1551.78) p2 (list 0.00 0.00))
 (command "TEXT" "J" "ML" p1   0.75  0.00 "904")
 (command "LAYER" "S" "CGBTHK" "")
 (setq p1 (list 547.00 1551.78) p2 (list 0.00 0.00))
 (command "TEXT" "J" "ML" p1   0.75  0.00 "0.17")
 (command "LAYER" "S" "CGBHZID" "")
 (setq p1 (list 551.50 1551.78) p2 (list 0.00 0.00))
 (command "TEXT" "J" "ML" p1   0.75  0.00 "")
 (setq p1 (list 553.75 1551.78) p2 (list 0.00 0.00))
 (command "TEXT" "J" "ML" p1   0.75  0.00 "6951")
 (command "LAYER" "S" "CGBLITHTXT" "")
 (setq p1 (list 557.50 1551.78) p2 (list 0.00 0.00))
 (command "TEXT" "J" "ML" p1   0.75  0.00 "MASS FN GRND LS")
 (command "LAYER" "S" "CGBCMNT" "")
 (setq p1 (list 577.75 1551.78) p2 (list 0.00 0.00))
 (command "TEXT" "J" "ML" p1   0.75  0.00 "")
 (command "LAYER" "S" "CGBMAIN" "")
 (setq p1 (list 535.00 1558.86) p2 (list 541.00 1558.86) p3 (list 541.00 1557.44) p4 (list 535.00 1557.44))
 (command "PLINE" p1 p2 p3 p4 "c")
 (command "HATCH" "ZIGZAG" 2.50 90.00 "L" "")
 (command "COLOR" "BYLAYER")
 (command "LAYER" "S" "CGBLITHCD" "")
 (setq p1 (list 541.00 1558.15) p2 (list 542.35 1550.90))
 (command "LINE" p1 p2 "")
 (setq p1 (list 542.50 1550.53) p2 (list 0.00 0.00))
 (command "TEXT" "J" "ML" p1   0.75  0.00 "328")
 (command "LAYER" "S" "CGBTHK" "")
 (setq p1 (list 547.00 1550.53) p2 (list 0.00 0.00))
 (command "TEXT" "J" "ML" p1   0.75  0.00 "1.42")
 (command "LAYER" "S" "CGBHZID" "")
 (setq p1 (list 551.50 1550.53) p2 (list 0.00 0.00))
 (command "TEXT" "J" "ML" p1   0.75  0.00 "")
 (setq p1 (list 553.75 1550.53) p2 (list 0.00 0.00))
 (command "TEXT" "J" "ML" p1   0.75  0.00 "6951")
 (command "LAYER" "S" "CGBLITHTXT" "")
 (setq p1 (list 557.50 1550.53) p2 (list 0.00 0.00))
 (command "TEXT" "J" "ML" p1   0.75  0.00 "DRK GRY BURROWED SDY SH")
 (command "LAYER" "S" "CGBCMNT" "")
 (setq p1 (list 577.75 1550.53) p2 (list 0.00 0.00))
 (command "TEXT" "J" "ML" p1   0.75  0.00 "")
 (command "LAYER" "S" "CGBMAIN" "")
 (setq p1 (list 535.00 1557.44) p2 (list 541.00 1557.44) p3 (list 541.00 1555.83) p4 (list 535.00 1555.83))
 (command "PLINE" p1 p2 p3 p4 "c")
 (command "HATCH" "ZIGZAG" 5.00 0.00 "L" "")
 (command "COLOR" "BYLAYER")
 (command "LAYER" "S" "CGBLITHCD" "")
 (setq p1 (list 541.00 1556.64) p2 (list 542.35 1549.65))
 (command "LINE" p1 p2 "")
 (setq p1 (list 542.50 1549.28) p2 (list 0.00 0.00))
 (command "TEXT" "J" "ML" p1   0.75  0.00 "224")
 (command "LAYER" "S" "CGBTHK" "")
 (setq p1 (list 547.00 1549.28) p2 (list 0.00 0.00))
 (command "TEXT" "J" "ML" p1   0.75  0.00 "1.61")
 (command "LAYER" "S" "CGBHZID" "")
 (setq p1 (list 551.50 1549.28) p2 (list 0.00 0.00))
 (command "TEXT" "J" "ML" p1   0.75  0.00 "")
 (setq p1 (list 553.75 1549.28) p2 (list 0.00 0.00))
 (command "TEXT" "J" "ML" p1   0.75  0.00 "6951")
 (command "LAYER" "S" "CGBLITHTXT" "")
 (setq p1 (list 557.50 1549.28) p2 (list 0.00 0.00))
 (command "TEXT" "J" "ML" p1   0.75  0.00 "DRK GRY SH W/LS NODS")
 (command "LAYER" "S" "CGBCMNT" "")
 (setq p1 (list 577.75 1549.28) p2 (list 0.00 0.00))
 (command "TEXT" "J" "ML" p1   0.75  0.00 "")
 (command "LAYER" "S" "CGBMAIN" "")
 (setq p1 (list 535.00 1555.83) p2 (list 541.00 1555.83) p3 (list 541.00 1554.74) p4 (list 535.00 1554.74))
 (command "PLINE" p1 p2 p3 p4 "c")
 (command "HATCH" "ZIGZAG" 10.00 45.00 "L" "")
 (command "COLOR" "BYLAYER")
 (command "LAYER" "S" "CGBLITHCD" "")
 (setq p1 (list 541.00 1555.29) p2 (list 542.35 1548.40))
 (command "LINE" p1 p2 "")
 (setq p1 (list 542.50 1548.03) p2 (list 0.00 0.00))
 (command "TEXT" "J" "ML" p1   0.75  0.00 "094")
 (command "LAYER" "S" "CGBTHK" "")
 (setq p1 (list 547.00 1548.03) p2 (list 0.00 0.00))
 (command "TEXT" "J" "ML" p1   0.75  0.00 "1.09")
 (command "LAYER" "S" "CGBHZID" "")
 (setq p1 (list 551.50 1548.03) p2 (list 0.00 0.00))
 (command "TEXT" "J" "ML" p1   0.75  0.00 "")
 (setq p1 (list 553.75 1548.03) p2 (list 0.00 0.00))
 (command "TEXT" "J" "ML" p1   0.75  0.00 "6951")
 (command "LAYER" "S" "CGBLITHTXT" "")
 (setq p1 (list 557.50 1548.03) p2 (list 0.00 0.00))
 (command "TEXT" "J" "ML" p1   0.75  0.00 "MASS FLINT CLAY")
 (command "LAYER" "S" "CGBCMNT" "")
 (setq p1 (list 577.75 1548.03) p2 (list 0.00 0.00))
 (command "TEXT" "J" "ML" p1   0.75  0.00 "")
 (command "LAYER" "S" "CGBMAIN" "")
 (setq p1 (list 535.00 1554.74) p2 (list 541.00 1554.74) p3 (list 541.00 1554.54) p4 (list 535.00 1554.54))
 (command "PLINE" p1 p2 p3 p4 "c")
 (command "HATCH" "ZIGZAG" 5.00 0.00 "L" "")
 (command "COLOR" "BYLAYER")
 (command "LAYER" "S" "CGBLITHCD" "")
 (setq p1 (list 541.00 1554.64) p2 (list 542.35 1547.15))
 (command "LINE" p1 p2 "")
 (setq p1 (list 542.50 1546.78) p2 (list 0.00 0.00))
 (command "TEXT" "J" "ML" p1   0.75  0.00 "904")
 (command "LAYER" "S" "CGBTHK" "")
 (setq p1 (list 547.00 1546.78) p2 (list 0.00 0.00))
 (command "TEXT" "J" "ML" p1   0.75  0.00 "0.20")
 (command "LAYER" "S" "CGBHZID" "")
 (setq p1 (list 551.50 1546.78) p2 (list 0.00 0.00))
 (command "TEXT" "J" "ML" p1   0.75  0.00 "")
 (setq p1 (list 553.75 1546.78) p2 (list 0.00 0.00))
 (command "TEXT" "J" "ML" p1   0.75  0.00 "6951")
 (command "LAYER" "S" "CGBLITHTXT" "")
 (setq p1 (list 557.50 1546.78) p2 (list 0.00 0.00))
 (command "TEXT" "J" "ML" p1   0.75  0.00 "MASS FN GRND LS")
 (command "LAYER" "S" "CGBCMNT" "")
 (setq p1 (list 577.75 1546.78) p2 (list 0.00 0.00))
 (command "TEXT" "J" "ML" p1   0.75  0.00 "")
 (command "LAYER" "S" "CGBMAIN" "")
 (setq p1 (list 535.00 1554.54) p2 (list 541.00 1554.54) p3 (list 541.00 1550.96) p4 (list 535.00 1550.96))
 (command "PLINE" p1 p2 p3 p4 "c")
 (command "HATCH" "ZIGZAG" 5.00 0.00 "L" "")
 (command "COLOR" "BYLAYER")
 (command "LAYER" "S" "CGBLITHCD" "")
 (setq p1 (list 541.00 1552.75) p2 (list 542.35 1545.90))
 (command "LINE" p1 p2 "")
 (setq p1 (list 542.50 1545.53) p2 (list 0.00 0.00))
 (command "TEXT" "J" "ML" p1   0.75  0.00 "224")
 (command "LAYER" "S" "CGBTHK" "")
 (setq p1 (list 547.00 1545.53) p2 (list 0.00 0.00))
 (command "TEXT" "J" "ML" p1   0.75  0.00 "3.58")
 (command "LAYER" "S" "CGBHZID" "")
 (setq p1 (list 551.50 1545.53) p2 (list 0.00 0.00))
 (command "TEXT" "J" "ML" p1   0.75  0.00 "")
 (setq p1 (list 553.75 1545.53) p2 (list 0.00 0.00))
 (command "TEXT" "J" "ML" p1   0.75  0.00 "6951")
 (command "LAYER" "S" "CGBLITHTXT" "")
 (setq p1 (list 557.50 1545.53) p2 (list 0.00 0.00))
 (command "TEXT" "J" "ML" p1   0.75  0.00 "DRK GRY SH W/LS NODS")
 (command "LAYER" "S" "CGBCMNT" "")
 (setq p1 (list 577.75 1545.53) p2 (list 0.00 0.00))
 (command "TEXT" "J" "ML" p1   0.75  0.00 "")
 (command "LAYER" "S" "CGBMAIN" "")
 (setq p1 (list 535.00 1550.96) p2 (list 541.00 1550.96) p3 (list 541.00 1550.18) p4 (list 535.00 1550.18))
 (command "PLINE" p1 p2 p3 p4 "c")
 (command "HATCH" "ZIGZAG" 10.00 45.00 "L" "")
 (command "COLOR" "BYLAYER")
 (command "LAYER" "S" "CGBLITHCD" "")
 (setq p1 (list 541.00 1550.57) p2 (list 542.35 1544.65))
 (command "LINE" p1 p2 "")
 (setq p1 (list 542.50 1544.28) p2 (list 0.00 0.00))
 (command "TEXT" "J" "ML" p1   0.75  0.00 "094")
 (command "LAYER" "S" "CGBTHK" "")
 (setq p1 (list 547.00 1544.28) p2 (list 0.00 0.00))
 (command "TEXT" "J" "ML" p1   0.75  0.00 "0.78")
 (command "LAYER" "S" "CGBHZID" "")
 (setq p1 (list 551.50 1544.28) p2 (list 0.00 0.00))
 (command "TEXT" "J" "ML" p1   0.75  0.00 "")
 (setq p1 (list 553.75 1544.28) p2 (list 0.00 0.00))
 (command "TEXT" "J" "ML" p1   0.75  0.00 "6951")
 (command "LAYER" "S" "CGBLITHTXT" "")
 (setq p1 (list 557.50 1544.28) p2 (list 0.00 0.00))
 (command "TEXT" "J" "ML" p1   0.75  0.00 "MASS FLINT CLAY")
 (command "LAYER" "S" "CGBCMNT" "")
 (setq p1 (list 577.75 1544.28) p2 (list 0.00 0.00))
 (command "TEXT" "J" "ML" p1   0.75  0.00 "")
 (command "LAYER" "S" "CGBMAIN" "")
 (setq p1 (list 535.00 1550.18) p2 (list 541.00 1550.18) p3 (list 541.00 1548.76) p4 (list 535.00 1548.76))
 (command "PLINE" p1 p2 p3 p4 "c")
 (command "HATCH" "ZIGZAG" 4.00 0.00 "L" "")
 (command "COLOR" "BYLAYER")
 (command "LAYER" "S" "CGBLITHCD" "")
 (setq p1 (list 541.00 1549.47) p2 (list 542.35 1543.40))
 (command "LINE" p1 p2 "")
 (setq p1 (list 542.50 1543.03) p2 (list 0.00 0.00))
 (command "TEXT" "J" "ML" p1   0.75  0.00 "125")
 (command "LAYER" "S" "CGBTHK" "")
 (setq p1 (list 547.00 1543.03) p2 (list 0.00 0.00))
 (command "TEXT" "J" "ML" p1   0.75  0.00 "1.42")
 (command "LAYER" "S" "CGBHZID" "")
 (setq p1 (list 551.50 1543.03) p2 (list 0.00 0.00))
 (command "TEXT" "J" "ML" p1   0.75  0.00 "")
 (setq p1 (list 553.75 1543.03) p2 (list 0.00 0.00))
 (command "TEXT" "J" "ML" p1   0.75  0.00 "6951")
 (command "LAYER" "S" "CGBLITHTXT" "")
 (setq p1 (list 557.50 1543.03) p2 (list 0.00 0.00))
 (command "TEXT" "J" "ML" p1   0.75  0.00 "DRK GRY CHRND SH")
 (command "LAYER" "S" "CGBCMNT" "")
 (setq p1 (list 577.75 1543.03) p2 (list 0.00 0.00))
 (command "TEXT" "J" "ML" p1   0.75  0.00 "SLC")
 (command "LAYER" "S" "CGBMAIN" "")
 (setq p1 (list 535.00 1548.76) p2 (list 541.00 1548.76) p3 (list 541.00 1548.04) p4 (list 535.00 1548.04))
 (command "PLINE" p1 p2 p3 p4 "c")
 (command "HATCH" "ZIGZAG" 2.50 90.00 "L" "")
 (command "COLOR" "BYLAYER")
 (command "LAYER" "S" "CGBLITHCD" "")
 (setq p1 (list 541.00 1548.40) p2 (list 542.35 1542.15))
 (command "LINE" p1 p2 "")
 (setq p1 (list 542.50 1541.78) p2 (list 0.00 0.00))
 (command "TEXT" "J" "ML" p1   0.75  0.00 "328")
 (command "LAYER" "S" "CGBTHK" "")
 (setq p1 (list 547.00 1541.78) p2 (list 0.00 0.00))
 (command "TEXT" "J" "ML" p1   0.75  0.00 "0.72")
 (command "LAYER" "S" "CGBHZID" "")
 (setq p1 (list 551.50 1541.78) p2 (list 0.00 0.00))
 (command "TEXT" "J" "ML" p1   0.75  0.00 "")
 (setq p1 (list 553.75 1541.78) p2 (list 0.00 0.00))
 (command "TEXT" "J" "ML" p1   0.75  0.00 "6951")
 (command "LAYER" "S" "CGBLITHTXT" "")
 (setq p1 (list 557.50 1541.78) p2 (list 0.00 0.00))
 (command "TEXT" "J" "ML" p1   0.75  0.00 "DRK GRY BURROWED SDY SH")
 (command "LAYER" "S" "CGBCMNT" "")
 (setq p1 (list 577.75 1541.78) p2 (list 0.00 0.00))
 (command "TEXT" "J" "ML" p1   0.75  0.00 "SS STKS")
 (command "LAYER" "S" "CGBMAIN" "")
 (setq p1 (list 535.00 1548.04) p2 (list 541.00 1548.04) p3 (list 541.00 1546.74) p4 (list 535.00 1546.74))
 (command "PLINE" p1 p2 p3 p4 "c")
 (command "HATCH" "ZIGZAG" 4.00 0.00 "L" "")
 (command "COLOR" "BYLAYER")
 (command "LAYER" "S" "CGBLITHCD" "")
 (setq p1 (list 541.00 1547.39) p2 (list 542.35 1540.90))
 (command "LINE" p1 p2 "")
 (setq p1 (list 542.50 1540.53) p2 (list 0.00 0.00))
 (command "TEXT" "J" "ML" p1   0.75  0.00 "543")
 (command "LAYER" "S" "CGBTHK" "")
 (setq p1 (list 547.00 1540.53) p2 (list 0.00 0.00))
 (command "TEXT" "J" "ML" p1   0.75  0.00 "1.30")
 (command "LAYER" "S" "CGBHZID" "")
 (setq p1 (list 551.50 1540.53) p2 (list 0.00 0.00))
 (command "TEXT" "J" "ML" p1   0.75  0.00 "")
 (setq p1 (list 553.75 1540.53) p2 (list 0.00 0.00))
 (command "TEXT" "J" "ML" p1   0.75  0.00 "6951")
 (command "LAYER" "S" "CGBLITHTXT" "")
 (setq p1 (list 557.50 1540.53) p2 (list 0.00 0.00))
 (command "TEXT" "J" "ML" p1   0.75  0.00 "GRY SS W/SH STKS")
 (command "LAYER" "S" "CGBCMNT" "")
 (setq p1 (list 577.75 1540.53) p2 (list 0.00 0.00))
 (command "TEXT" "J" "ML" p1   0.75  0.00 "V F GR")
 (command "LAYER" "S" "CGBMAIN" "")
 (setq p1 (list 535.00 1546.74) p2 (list 541.00 1546.74) p3 (list 541.00 1546.47) p4 (list 535.00 1546.47))
 (command "PLINE" p1 p2 p3 p4 "c")
 (command "HATCH" "ZIGZAG" 4.00 0.00 "L" "")
 (command "COLOR" "BYLAYER")
 (command "LAYER" "S" "CGBLITHCD" "")
 (setq p1 (list 541.00 1546.61) p2 (list 542.35 1539.65))
 (command "LINE" p1 p2 "")
 (setq p1 (list 542.50 1539.28) p2 (list 0.00 0.00))
 (command "TEXT" "J" "ML" p1   0.75  0.00 "543")
 (command "LAYER" "S" "CGBTHK" "")
 (setq p1 (list 547.00 1539.28) p2 (list 0.00 0.00))
 (command "TEXT" "J" "ML" p1   0.75  0.00 "0.27")
 (command "LAYER" "S" "CGBHZID" "")
 (setq p1 (list 551.50 1539.28) p2 (list 0.00 0.00))
 (command "TEXT" "J" "ML" p1   0.75  0.00 "")
 (setq p1 (list 553.75 1539.28) p2 (list 0.00 0.00))
 (command "TEXT" "J" "ML" p1   0.75  0.00 "6951")
 (command "LAYER" "S" "CGBLITHTXT" "")
 (setq p1 (list 557.50 1539.28) p2 (list 0.00 0.00))
 (command "TEXT" "J" "ML" p1   0.75  0.00 "GRY SS W/SH STKS")
 (command "LAYER" "S" "CGBCMNT" "")
 (setq p1 (list 577.75 1539.28) p2 (list 0.00 0.00))
 (command "TEXT" "J" "ML" p1   0.75  0.00 "SLC")
 (command "LAYER" "S" "CGBMAIN" "")
 (setq p1 (list 535.00 1546.47) p2 (list 541.00 1546.47) p3 (list 541.00 1543.89) p4 (list 535.00 1543.89))
 (command "PLINE" p1 p2 p3 p4 "c")
 (command "HATCH" "ZIGZAG" 0.50 0.00 "L" "")
 (command "COLOR" "BYLAYER")
 (command "LAYER" "S" "CGBLITHCD" "")
 (setq p1 (list 541.00 1545.18) p2 (list 542.35 1538.40))
 (command "LINE" p1 p2 "")
 (setq p1 (list 542.50 1538.03) p2 (list 0.00 0.00))
 (command "TEXT" "J" "ML" p1   0.75  0.00 "323")
 (command "LAYER" "S" "CGBTHK" "")
 (setq p1 (list 547.00 1538.03) p2 (list 0.00 0.00))
 (command "TEXT" "J" "ML" p1   0.75  0.00 "2.58")
 (command "LAYER" "S" "CGBHZID" "")
 (setq p1 (list 551.50 1538.03) p2 (list 0.00 0.00))
 (command "TEXT" "J" "ML" p1   0.75  0.00 "")
 (setq p1 (list 553.75 1538.03) p2 (list 0.00 0.00))
 (command "TEXT" "J" "ML" p1   0.75  0.00 "6951")
 (command "LAYER" "S" "CGBLITHTXT" "")
 (setq p1 (list 557.50 1538.03) p2 (list 0.00 0.00))
 (command "TEXT" "J" "ML" p1   0.75  0.00 "DRK GRY SH W/SS STKS")
 (command "LAYER" "S" "CGBCMNT" "")
 (setq p1 (list 577.75 1538.03) p2 (list 0.00 0.00))
 (command "TEXT" "J" "ML" p1   0.75  0.00 "50-70%SS, BUR")
 (command "LAYER" "S" "CGBMAIN" "")
 (setq p1 (list 535.00 1543.89) p2 (list 541.00 1543.89) p3 (list 541.00 1543.21) p4 (list 535.00 1543.21))
 (command "PLINE" p1 p2 p3 p4 "c")
 (command "HATCH" "ZIGZAG" 4.00 0.00 "L" "")
 (command "COLOR" "BYLAYER")
 (command "LAYER" "S" "CGBLITHCD" "")
 (setq p1 (list 541.00 1543.55) p2 (list 542.35 1537.15))
 (command "LINE" p1 p2 "")
 (setq p1 (list 542.50 1536.78) p2 (list 0.00 0.00))
 (command "TEXT" "J" "ML" p1   0.75  0.00 "543")
 (command "LAYER" "S" "CGBTHK" "")
 (setq p1 (list 547.00 1536.78) p2 (list 0.00 0.00))
 (command "TEXT" "J" "ML" p1   0.75  0.00 "0.68")
 (command "LAYER" "S" "CGBHZID" "")
 (setq p1 (list 551.50 1536.78) p2 (list 0.00 0.00))
 (command "TEXT" "J" "ML" p1   0.75  0.00 "")
 (setq p1 (list 553.75 1536.78) p2 (list 0.00 0.00))
 (command "TEXT" "J" "ML" p1   0.75  0.00 "6951")
 (command "LAYER" "S" "CGBLITHTXT" "")
 (setq p1 (list 557.50 1536.78) p2 (list 0.00 0.00))
 (command "TEXT" "J" "ML" p1   0.75  0.00 "GRY SS W/SH STKS")
 (command "LAYER" "S" "CGBCMNT" "")
 (setq p1 (list 577.75 1536.78) p2 (list 0.00 0.00))
 (command "TEXT" "J" "ML" p1   0.75  0.00 "")
 (command "LAYER" "S" "CGBMAIN" "")
 (setq p1 (list 535.00 1543.21) p2 (list 541.00 1543.21) p3 (list 541.00 1539.14) p4 (list 535.00 1539.14))
 (command "PLINE" p1 p2 p3 p4 "c")
 (command "HATCH" "ZIGZAG" 0.50 0.00 "L" "")
 (command "COLOR" "BYLAYER")
 (command "LAYER" "S" "CGBLITHCD" "")
 (setq p1 (list 541.00 1541.18) p2 (list 542.35 1535.90))
 (command "LINE" p1 p2 "")
 (setq p1 (list 542.50 1535.53) p2 (list 0.00 0.00))
 (command "TEXT" "J" "ML" p1   0.75  0.00 "323")
 (command "LAYER" "S" "CGBTHK" "")
 (setq p1 (list 547.00 1535.53) p2 (list 0.00 0.00))
 (command "TEXT" "J" "ML" p1   0.75  0.00 "4.07")
 (command "LAYER" "S" "CGBHZID" "")
 (setq p1 (list 551.50 1535.53) p2 (list 0.00 0.00))
 (command "TEXT" "J" "ML" p1   0.75  0.00 "")
 (setq p1 (list 553.75 1535.53) p2 (list 0.00 0.00))
 (command "TEXT" "J" "ML" p1   0.75  0.00 "6951")
 (command "LAYER" "S" "CGBLITHTXT" "")
 (setq p1 (list 557.50 1535.53) p2 (list 0.00 0.00))
 (command "TEXT" "J" "ML" p1   0.75  0.00 "DRK GRY SH W/SS STKS")
 (command "LAYER" "S" "CGBCMNT" "")
 (setq p1 (list 577.75 1535.53) p2 (list 0.00 0.00))
 (command "TEXT" "J" "ML" p1   0.75  0.00 "70 % SS")
 (command "LAYER" "S" "CGBMAIN" "")
 (setq p1 (list 535.00 1539.14) p2 (list 541.00 1539.14) p3 (list 541.00 1538.42) p4 (list 535.00 1538.42))
 (command "PLINE" p1 p2 p3 p4 "c")
 (command "HATCH" "ZIGZAG" 4.00 0.00 "L" "")
 (command "COLOR" "BYLAYER")
 (command "LAYER" "S" "CGBLITHCD" "")
 (setq p1 (list 541.00 1538.78) p2 (list 542.35 1534.65))
 (command "LINE" p1 p2 "")
 (setq p1 (list 542.50 1534.28) p2 (list 0.00 0.00))
 (command "TEXT" "J" "ML" p1   0.75  0.00 "543")
 (command "LAYER" "S" "CGBTHK" "")
 (setq p1 (list 547.00 1534.28) p2 (list 0.00 0.00))
 (command "TEXT" "J" "ML" p1   0.75  0.00 "0.72")
 (command "LAYER" "S" "CGBHZID" "")
 (setq p1 (list 551.50 1534.28) p2 (list 0.00 0.00))
 (command "TEXT" "J" "ML" p1   0.75  0.00 "")
 (setq p1 (list 553.75 1534.28) p2 (list 0.00 0.00))
 (command "TEXT" "J" "ML" p1   0.75  0.00 "6951")
 (command "LAYER" "S" "CGBLITHTXT" "")
 (setq p1 (list 557.50 1534.28) p2 (list 0.00 0.00))
 (command "TEXT" "J" "ML" p1   0.75  0.00 "GRY SS W/SH STKS")
 (command "LAYER" "S" "CGBCMNT" "")
 (setq p1 (list 577.75 1534.28) p2 (list 0.00 0.00))
 (command "TEXT" "J" "ML" p1   0.75  0.00 "")
 (command "LAYER" "S" "CGBMAIN" "")
 (setq p1 (list 535.00 1538.42) p2 (list 541.00 1538.42) p3 (list 541.00 1537.82) p4 (list 535.00 1537.82))
 (command "PLINE" p1 p2 p3 p4 "c")
 (command "HATCH" "ZIGZAG" 0.50 0.00 "L" "")
 (command "COLOR" "BYLAYER")
 (command "LAYER" "S" "CGBLITHCD" "")
 (setq p1 (list 541.00 1538.12) p2 (list 542.35 1533.40))
 (command "LINE" p1 p2 "")
 (setq p1 (list 542.50 1533.03) p2 (list 0.00 0.00))
 (command "TEXT" "J" "ML" p1   0.75  0.00 "323")
 (command "LAYER" "S" "CGBTHK" "")
 (setq p1 (list 547.00 1533.03) p2 (list 0.00 0.00))
 (command "TEXT" "J" "ML" p1   0.75  0.00 "0.60")
 (command "LAYER" "S" "CGBHZID" "")
 (setq p1 (list 551.50 1533.03) p2 (list 0.00 0.00))
 (command "TEXT" "J" "ML" p1   0.75  0.00 "")
 (setq p1 (list 553.75 1533.03) p2 (list 0.00 0.00))
 (command "TEXT" "J" "ML" p1   0.75  0.00 "6951")
 (command "LAYER" "S" "CGBLITHTXT" "")
 (setq p1 (list 557.50 1533.03) p2 (list 0.00 0.00))
 (command "TEXT" "J" "ML" p1   0.75  0.00 "DRK GRY SH W/SS STKS")
 (command "LAYER" "S" "CGBCMNT" "")
 (setq p1 (list 577.75 1533.03) p2 (list 0.00 0.00))
 (command "TEXT" "J" "ML" p1   0.75  0.00 "60% SS")
 (command "LAYER" "S" "CGBMAIN" "")
 (setq p1 (list 535.00 1537.82) p2 (list 541.00 1537.82) p3 (list 541.00 1537.11) p4 (list 535.00 1537.11))
 (command "PLINE" p1 p2 p3 p4 "c")
 (command "HATCH" "ZIGZAG" 4.00 0.00 "L" "")
 (command "COLOR" "BYLAYER")
 (command "LAYER" "S" "CGBLITHCD" "")
 (setq p1 (list 541.00 1537.47) p2 (list 542.35 1532.15))
 (command "LINE" p1 p2 "")
 (setq p1 (list 542.50 1531.78) p2 (list 0.00 0.00))
 (command "TEXT" "J" "ML" p1   0.75  0.00 "124")
 (command "LAYER" "S" "CGBTHK" "")
 (setq p1 (list 547.00 1531.78) p2 (list 0.00 0.00))
 (command "TEXT" "J" "ML" p1   0.75  0.00 "0.71")
 (command "LAYER" "S" "CGBHZID" "")
 (setq p1 (list 551.50 1531.78) p2 (list 0.00 0.00))
 (command "TEXT" "J" "ML" p1   0.75  0.00 "")
 (setq p1 (list 553.75 1531.78) p2 (list 0.00 0.00))
 (command "TEXT" "J" "ML" p1   0.75  0.00 "6951")
 (command "LAYER" "S" "CGBLITHTXT" "")
 (setq p1 (list 557.50 1531.78) p2 (list 0.00 0.00))
 (command "TEXT" "J" "ML" p1   0.75  0.00 "DRK GRY SH")
 (command "LAYER" "S" "CGBCMNT" "")
 (setq p1 (list 577.75 1531.78) p2 (list 0.00 0.00))
 (command "TEXT" "J" "ML" p1   0.75  0.00 "")
 (command "LAYER" "S" "CGBMAIN" "")
 (setq p1 (list 535.00 1537.11) p2 (list 541.00 1537.11) p3 (list 541.00 1535.42) p4 (list 535.00 1535.42))
 (command "PLINE" p1 p2 p3 p4 "c")
 (command "HATCH" "ZIGZAG" 5.00 0.00 "L" "")
 (command "COLOR" "BYLAYER")
 (command "LAYER" "S" "CGBLITHCD" "")
 (setq p1 (list 541.00 1536.27) p2 (list 542.35 1530.90))
 (command "LINE" p1 p2 "")
 (setq p1 (list 542.50 1530.53) p2 (list 0.00 0.00))
 (command "TEXT" "J" "ML" p1   0.75  0.00 "322")
 (command "LAYER" "S" "CGBTHK" "")
 (setq p1 (list 547.00 1530.53) p2 (list 0.00 0.00))
 (command "TEXT" "J" "ML" p1   0.75  0.00 "1.69")
 (command "LAYER" "S" "CGBHZID" "")
 (setq p1 (list 551.50 1530.53) p2 (list 0.00 0.00))
 (command "TEXT" "J" "ML" p1   0.75  0.00 "")
 (setq p1 (list 553.75 1530.53) p2 (list 0.00 0.00))
 (command "TEXT" "J" "ML" p1   0.75  0.00 "6951")
 (command "LAYER" "S" "CGBLITHTXT" "")
 (setq p1 (list 557.50 1530.53) p2 (list 0.00 0.00))
 (command "TEXT" "J" "ML" p1   0.75  0.00 "DRK GRY SH+INTERBED SS")
 (command "LAYER" "S" "CGBCMNT" "")
 (setq p1 (list 577.75 1530.53) p2 (list 0.00 0.00))
 (command "TEXT" "J" "ML" p1   0.75  0.00 "50 % SS")
 (command "LAYER" "S" "CGBMAIN" "")
 (setq p1 (list 535.00 1535.42) p2 (list 541.00 1535.42) p3 (list 541.00 1533.79) p4 (list 535.00 1533.79))
 (command "PLINE" p1 p2 p3 p4 "c")
 (command "HATCH" "ZIGZAG" 4.00 22.50 "L" "")
 (command "COLOR" "BYLAYER")
 (command "LAYER" "S" "CGBLITHCD" "")
 (setq p1 (list 541.00 1534.61) p2 (list 542.35 1529.65))
 (command "LINE" p1 p2 "")
 (setq p1 (list 542.50 1529.28) p2 (list 0.00 0.00))
 (command "TEXT" "J" "ML" p1   0.75  0.00 "114")
 (command "LAYER" "S" "CGBTHK" "")
 (setq p1 (list 547.00 1529.28) p2 (list 0.00 0.00))
 (command "TEXT" "J" "ML" p1   0.75  0.00 "1.63")
 (command "LAYER" "S" "CGBHZID" "")
 (setq p1 (list 551.50 1529.28) p2 (list 0.00 0.00))
 (command "TEXT" "J" "ML" p1   0.75  0.00 "")
 (setq p1 (list 553.75 1529.28) p2 (list 0.00 0.00))
 (command "TEXT" "J" "ML" p1   0.75  0.00 "6951")
 (command "LAYER" "S" "CGBLITHTXT" "")
 (setq p1 (list 557.50 1529.28) p2 (list 0.00 0.00))
 (command "TEXT" "J" "ML" p1   0.75  0.00 "BLK SH")
 (command "LAYER" "S" "CGBCMNT" "")
 (setq p1 (list 577.75 1529.28) p2 (list 0.00 0.00))
 (command "TEXT" "J" "ML" p1   0.75  0.00 "IRST")
 (command "LAYER" "S" "CGBMAIN" "")
 (setq p1 (list 535.00 1533.79) p2 (list 541.00 1533.79) p3 (list 541.00 1532.84) p4 (list 535.00 1532.84))
 (command "PLINE" p1 p2 p3 p4 "c")
 (command "HATCH" "ZIGZAG" 4.00 0.00 "L" "")
 (command "COLOR" "BYLAYER")
 (command "LAYER" "S" "CGBLITHCD" "")
 (setq p1 (list 541.00 1533.32) p2 (list 542.35 1528.40))
 (command "LINE" p1 p2 "")
 (setq p1 (list 542.50 1528.03) p2 (list 0.00 0.00))
 (command "TEXT" "J" "ML" p1   0.75  0.00 "424")
 (command "LAYER" "S" "CGBTHK" "")
 (setq p1 (list 547.00 1528.03) p2 (list 0.00 0.00))
 (command "TEXT" "J" "ML" p1   0.75  0.00 "0.95")
 (command "LAYER" "S" "CGBHZID" "")
 (setq p1 (list 551.50 1528.03) p2 (list 0.00 0.00))
 (command "TEXT" "J" "ML" p1   0.75  0.00 "")
 (setq p1 (list 553.75 1528.03) p2 (list 0.00 0.00))
 (command "TEXT" "J" "ML" p1   0.75  0.00 "6951")
 (command "LAYER" "S" "CGBLITHTXT" "")
 (setq p1 (list 557.50 1528.03) p2 (list 0.00 0.00))
 (command "TEXT" "J" "ML" p1   0.75  0.00 "DRK GRY SDY SH W/LS NODS")
 (command "LAYER" "S" "CGBCMNT" "")
 (setq p1 (list 577.75 1528.03) p2 (list 0.00 0.00))
 (command "TEXT" "J" "ML" p1   0.75  0.00 "")
 (command "LAYER" "S" "CGBMAIN" "")
 (setq p1 (list 535.00 1532.84) p2 (list 541.00 1532.84) p3 (list 541.00 1531.74) p4 (list 535.00 1531.74))
 (command "PLINE" p1 p2 p3 p4 "c")
 (command "HATCH" "ZIGZAG" 5.00 0.00 "L" "")
 (command "COLOR" "BYLAYER")
 (command "LAYER" "S" "CGBLITHCD" "")
 (setq p1 (list 541.00 1532.29) p2 (list 542.35 1527.15))
 (command "LINE" p1 p2 "")
 (setq p1 (list 542.50 1526.78) p2 (list 0.00 0.00))
 (command "TEXT" "J" "ML" p1   0.75  0.00 "904")
 (command "LAYER" "S" "CGBTHK" "")
 (setq p1 (list 547.00 1526.78) p2 (list 0.00 0.00))
 (command "TEXT" "J" "ML" p1   0.75  0.00 "1.10")
 (command "LAYER" "S" "CGBHZID" "")
 (setq p1 (list 551.50 1526.78) p2 (list 0.00 0.00))
 (command "TEXT" "J" "ML" p1   0.75  0.00 "")
 (setq p1 (list 553.75 1526.78) p2 (list 0.00 0.00))
 (command "TEXT" "J" "ML" p1   0.75  0.00 "6951")
 (command "LAYER" "S" "CGBLITHTXT" "")
 (setq p1 (list 557.50 1526.78) p2 (list 0.00 0.00))
 (command "TEXT" "J" "ML" p1   0.75  0.00 "MASS FN GRND LS")
 (command "LAYER" "S" "CGBCMNT" "")
 (setq p1 (list 577.75 1526.78) p2 (list 0.00 0.00))
 (command "TEXT" "J" "ML" p1   0.75  0.00 "")
 (command "LAYER" "S" "CGBMAIN" "")
 (setq p1 (list 535.00 1531.74) p2 (list 541.00 1531.74) p3 (list 541.00 1531.44) p4 (list 535.00 1531.44))
 (command "PLINE" p1 p2 p3 p4 "c")
 (command "HATCH" "ZIGZAG" 4.00 22.50 "L" "")
 (command "COLOR" "BYLAYER")
 (command "LAYER" "S" "CGBLITHCD" "")
 (setq p1 (list 541.00 1531.59) p2 (list 542.35 1525.90))
 (command "LINE" p1 p2 "")
 (setq p1 (list 542.50 1525.53) p2 (list 0.00 0.00))
 (command "TEXT" "J" "ML" p1   0.75  0.00 "135")
 (command "LAYER" "S" "CGBTHK" "")
 (setq p1 (list 547.00 1525.53) p2 (list 0.00 0.00))
 (command "TEXT" "J" "ML" p1   0.75  0.00 "0.30")
 (command "LAYER" "S" "CGBHZID" "")
 (setq p1 (list 551.50 1525.53) p2 (list 0.00 0.00))
 (command "TEXT" "J" "ML" p1   0.75  0.00 "")
 (setq p1 (list 553.75 1525.53) p2 (list 0.00 0.00))
 (command "TEXT" "J" "ML" p1   0.75  0.00 "6951")
 (command "LAYER" "S" "CGBLITHTXT" "")
 (setq p1 (list 557.50 1525.53) p2 (list 0.00 0.00))
 (command "TEXT" "J" "ML" p1   0.75  0.00 "LT GRY CHRND SH")
 (command "LAYER" "S" "CGBCMNT" "")
 (setq p1 (list 577.75 1525.53) p2 (list 0.00 0.00))
 (command "TEXT" "J" "ML" p1   0.75  0.00 "")
 (command "LAYER" "S" "CGBMAIN" "")
 (setq p1 (list 535.00 1531.44) p2 (list 541.00 1531.44) p3 (list 541.00 1529.92) p4 (list 535.00 1529.92))
 (command "PLINE" p1 p2 p3 p4 "c")
 (command "HATCH" "ZIGZAG" 10.00 45.00 "L" "")
 (command "COLOR" "BYLAYER")
 (command "LAYER" "S" "CGBLITHCD" "")
 (setq p1 (list 541.00 1530.68) p2 (list 542.35 1524.65))
 (command "LINE" p1 p2 "")
 (setq p1 (list 542.50 1524.28) p2 (list 0.00 0.00))
 (command "TEXT" "J" "ML" p1   0.75  0.00 "094")
 (command "LAYER" "S" "CGBTHK" "")
 (setq p1 (list 547.00 1524.28) p2 (list 0.00 0.00))
 (command "TEXT" "J" "ML" p1   0.75  0.00 "1.52")
 (command "LAYER" "S" "CGBHZID" "")
 (setq p1 (list 551.50 1524.28) p2 (list 0.00 0.00))
 (command "TEXT" "J" "ML" p1   0.75  0.00 "")
 (setq p1 (list 553.75 1524.28) p2 (list 0.00 0.00))
 (command "TEXT" "J" "ML" p1   0.75  0.00 "6951")
 (command "LAYER" "S" "CGBLITHTXT" "")
 (setq p1 (list 557.50 1524.28) p2 (list 0.00 0.00))
 (command "TEXT" "J" "ML" p1   0.75  0.00 "MASS FLINT CLAY")
 (command "LAYER" "S" "CGBCMNT" "")
 (setq p1 (list 577.75 1524.28) p2 (list 0.00 0.00))
 (command "TEXT" "J" "ML" p1   0.75  0.00 "")
 (command "LAYER" "S" "CGBMAIN" "")
 (setq p1 (list 535.00 1529.92) p2 (list 541.00 1529.92) p3 (list 541.00 1529.74) p4 (list 535.00 1529.74))
 (command "PLINE" p1 p2 p3 p4 "c")
 (command "HATCH" "ZIGZAG" 4.00 0.00 "L" "")
 (command "COLOR" "BYLAYER")
 (command "LAYER" "S" "CGBLITHCD" "")
 (setq p1 (list 541.00 1529.83) p2 (list 542.35 1523.40))
 (command "LINE" p1 p2 "")
 (setq p1 (list 542.50 1523.03) p2 (list 0.00 0.00))
 (command "TEXT" "J" "ML" p1   0.75  0.00 "123")
 (command "LAYER" "S" "CGBTHK" "")
 (setq p1 (list 547.00 1523.03) p2 (list 0.00 0.00))
 (command "TEXT" "J" "ML" p1   0.75  0.00 "0.18")
 (command "LAYER" "S" "CGBHZID" "")
 (setq p1 (list 551.50 1523.03) p2 (list 0.00 0.00))
 (command "TEXT" "J" "ML" p1   0.75  0.00 "")
 (setq p1 (list 553.75 1523.03) p2 (list 0.00 0.00))
 (command "TEXT" "J" "ML" p1   0.75  0.00 "6951")
 (command "LAYER" "S" "CGBLITHTXT" "")
 (setq p1 (list 557.50 1523.03) p2 (list 0.00 0.00))
 (command "TEXT" "J" "ML" p1   0.75  0.00 "DRK GRY SH W/COAL STKS")
 (command "LAYER" "S" "CGBCMNT" "")
 (setq p1 (list 577.75 1523.03) p2 (list 0.00 0.00))
 (command "TEXT" "J" "ML" p1   0.75  0.00 "")
 (command "LAYER" "S" "CGBMAIN" "")
 (setq p1 (list 535.00 1529.74) p2 (list 541.00 1529.74) p3 (list 541.00 1527.54) p4 (list 535.00 1527.54))
 (command "PLINE" p1 p2 p3 p4 "c")
 (command "HATCH" "ZIGZAG" 0.50 0.00 "L" "")
 (command "COLOR" "BYLAYER")
 (command "LAYER" "S" "CGBLITHCD" "")
 (setq p1 (list 541.00 1528.64) p2 (list 542.35 1522.15))
 (command "LINE" p1 p2 "")
 (setq p1 (list 542.50 1521.78) p2 (list 0.00 0.00))
 (command "TEXT" "J" "ML" p1   0.75  0.00 "323")
 (command "LAYER" "S" "CGBTHK" "")
 (setq p1 (list 547.00 1521.78) p2 (list 0.00 0.00))
 (command "TEXT" "J" "ML" p1   0.75  0.00 "2.20")
 (command "LAYER" "S" "CGBHZID" "")
 (setq p1 (list 551.50 1521.78) p2 (list 0.00 0.00))
 (command "TEXT" "J" "ML" p1   0.75  0.00 "")
 (setq p1 (list 553.75 1521.78) p2 (list 0.00 0.00))
 (command "TEXT" "J" "ML" p1   0.75  0.00 "6951")
 (command "LAYER" "S" "CGBLITHTXT" "")
 (setq p1 (list 557.50 1521.78) p2 (list 0.00 0.00))
 (command "TEXT" "J" "ML" p1   0.75  0.00 "DRK GRY SH W/SS STKS")
 (command "LAYER" "S" "CGBCMNT" "")
 (setq p1 (list 577.75 1521.78) p2 (list 0.00 0.00))
 (command "TEXT" "J" "ML" p1   0.75  0.00 "")
 (command "LAYER" "S" "CGBMAIN" "")
 (setq p1 (list 535.00 1527.54) p2 (list 541.00 1527.54) p3 (list 541.00 1527.33) p4 (list 535.00 1527.33))
 (command "PLINE" p1 p2 p3 p4 "c")
 (command "HATCH" "ZIGZAG" 0.50 0.00 "L" "")
 (command "COLOR" "BYLAYER")
 (command "LAYER" "S" "CGBLITHCD" "")
 (setq p1 (list 541.00 1527.44) p2 (list 542.35 1520.90))
 (command "LINE" p1 p2 "")
 (setq p1 (list 542.50 1520.53) p2 (list 0.00 0.00))
 (command "TEXT" "J" "ML" p1   0.75  0.00 "323")
 (command "LAYER" "S" "CGBTHK" "")
 (setq p1 (list 547.00 1520.53) p2 (list 0.00 0.00))
 (command "TEXT" "J" "ML" p1   0.75  0.00 "0.21")
 (command "LAYER" "S" "CGBHZID" "")
 (setq p1 (list 551.50 1520.53) p2 (list 0.00 0.00))
 (command "TEXT" "J" "ML" p1   0.75  0.00 "")
 (setq p1 (list 553.75 1520.53) p2 (list 0.00 0.00))
 (command "TEXT" "J" "ML" p1   0.75  0.00 "6951")
 (command "LAYER" "S" "CGBLITHTXT" "")
 (setq p1 (list 557.50 1520.53) p2 (list 0.00 0.00))
 (command "TEXT" "J" "ML" p1   0.75  0.00 "DRK GRY SH W/SS STKS")
 (command "LAYER" "S" "CGBCMNT" "")
 (setq p1 (list 577.75 1520.53) p2 (list 0.00 0.00))
 (command "TEXT" "J" "ML" p1   0.75  0.00 "")
 (command "LAYER" "S" "CGBMAIN" "")
 (setq p1 (list 535.00 1527.33) p2 (list 541.00 1527.33) p3 (list 541.00 1526.47) p4 (list 535.00 1526.47))
 (command "PLINE" p1 p2 p3 p4 "c")
 (command "HATCH" "ZIGZAG" 4.00 0.00 "L" "")
 (command "COLOR" "BYLAYER")
 (command "LAYER" "S" "CGBLITHCD" "")
 (setq p1 (list 541.00 1526.90) p2 (list 542.35 1519.65))
 (command "LINE" p1 p2 "")
 (setq p1 (list 542.50 1519.28) p2 (list 0.00 0.00))
 (command "TEXT" "J" "ML" p1   0.75  0.00 "543")
 (command "LAYER" "S" "CGBTHK" "")
 (setq p1 (list 547.00 1519.28) p2 (list 0.00 0.00))
 (command "TEXT" "J" "ML" p1   0.75  0.00 "0.86")
 (command "LAYER" "S" "CGBHZID" "")
 (setq p1 (list 551.50 1519.28) p2 (list 0.00 0.00))
 (command "TEXT" "J" "ML" p1   0.75  0.00 "")
 (setq p1 (list 553.75 1519.28) p2 (list 0.00 0.00))
 (command "TEXT" "J" "ML" p1   0.75  0.00 "6700")
 (command "LAYER" "S" "CGBLITHTXT" "")
 (setq p1 (list 557.50 1519.28) p2 (list 0.00 0.00))
 (command "TEXT" "J" "ML" p1   0.75  0.00 "GRY SS W/SH STKS")
 (command "LAYER" "S" "CGBCMNT" "")
 (setq p1 (list 577.75 1519.28) p2 (list 0.00 0.00))
 (command "TEXT" "J" "ML" p1   0.75  0.00 "SLGHT ANG BED")
 (command "LAYER" "S" "CGBMAIN" "")
 (setq p1 (list 535.00 1526.47) p2 (list 541.00 1526.47) p3 (list 541.00 1522.76) p4 (list 535.00 1522.76))
 (command "PLINE" p1 p2 p3 p4 "c")
 (command "HATCH" "ZIGZAG" 4.00 0.00 "L" "")
 (command "COLOR" "BYLAYER")
 (command "LAYER" "S" "CGBLITHCD" "")
 (setq p1 (list 541.00 1524.62) p2 (list 542.35 1518.40))
 (command "LINE" p1 p2 "")
 (setq p1 (list 542.50 1518.03) p2 (list 0.00 0.00))
 (command "TEXT" "J" "ML" p1   0.75  0.00 "541")
 (command "LAYER" "S" "CGBTHK" "")
 (setq p1 (list 547.00 1518.03) p2 (list 0.00 0.00))
 (command "TEXT" "J" "ML" p1   0.75  0.00 "3.71")
 (command "LAYER" "S" "CGBHZID" "")
 (setq p1 (list 551.50 1518.03) p2 (list 0.00 0.00))
 (command "TEXT" "J" "ML" p1   0.75  0.00 "")
 (setq p1 (list 553.75 1518.03) p2 (list 0.00 0.00))
 (command "TEXT" "J" "ML" p1   0.75  0.00 "6700")
 (command "LAYER" "S" "CGBLITHTXT" "")
 (setq p1 (list 557.50 1518.03) p2 (list 0.00 0.00))
 (command "TEXT" "J" "ML" p1   0.75  0.00 "GRY CROSSBED SS")
 (command "LAYER" "S" "CGBCMNT" "")
 (setq p1 (list 577.75 1518.03) p2 (list 0.00 0.00))
 (command "TEXT" "J" "ML" p1   0.75  0.00 "AS ABOVE, CRS")
 (command "LAYER" "S" "CGBMAIN" "")
 (setq p1 (list 535.00 1522.76) p2 (list 541.00 1522.76) p3 (list 541.00 1521.61) p4 (list 535.00 1521.61))
 (command "PLINE" p1 p2 p3 p4 "c")
 (command "HATCH" "ZIGZAG" 5.00 0.00 "L" "")
 (command "COLOR" "BYLAYER")
 (command "LAYER" "S" "CGBLITHCD" "")
 (setq p1 (list 541.00 1522.19) p2 (list 542.35 1517.15))
 (command "LINE" p1 p2 "")
 (setq p1 (list 542.50 1516.78) p2 (list 0.00 0.00))
 (command "TEXT" "J" "ML" p1   0.75  0.00 "322")
 (command "LAYER" "S" "CGBTHK" "")
 (setq p1 (list 547.00 1516.78) p2 (list 0.00 0.00))
 (command "TEXT" "J" "ML" p1   0.75  0.00 "1.15")
 (command "LAYER" "S" "CGBHZID" "")
 (setq p1 (list 551.50 1516.78) p2 (list 0.00 0.00))
 (command "TEXT" "J" "ML" p1   0.75  0.00 "")
 (setq p1 (list 553.75 1516.78) p2 (list 0.00 0.00))
 (command "TEXT" "J" "ML" p1   0.75  0.00 "6700")
 (command "LAYER" "S" "CGBLITHTXT" "")
 (setq p1 (list 557.50 1516.78) p2 (list 0.00 0.00))
 (command "TEXT" "J" "ML" p1   0.75  0.00 "DRK GRY SH+INTERBED SS")
 (command "LAYER" "S" "CGBCMNT" "")
 (setq p1 (list 577.75 1516.78) p2 (list 0.00 0.00))
 (command "TEXT" "J" "ML" p1   0.75  0.00 "AS ABOVE,50%")
 (command "LAYER" "S" "CGBMAIN" "")
 (setq p1 (list 535.00 1521.61) p2 (list 541.00 1521.61) p3 (list 541.00 1520.92) p4 (list 535.00 1520.92))
 (command "PLINE" p1 p2 p3 p4 "c")
 (command "HATCH" "ZIGZAG" 4.00 0.00 "L" "")
 (command "COLOR" "BYLAYER")
 (command "LAYER" "S" "CGBLITHCD" "")
 (setq p1 (list 541.00 1521.27) p2 (list 542.35 1515.90))
 (command "LINE" p1 p2 "")
 (setq p1 (list 542.50 1515.53) p2 (list 0.00 0.00))
 (command "TEXT" "J" "ML" p1   0.75  0.00 "543")
 (command "LAYER" "S" "CGBTHK" "")
 (setq p1 (list 547.00 1515.53) p2 (list 0.00 0.00))
 (command "TEXT" "J" "ML" p1   0.75  0.00 "0.69")
 (command "LAYER" "S" "CGBHZID" "")
 (setq p1 (list 551.50 1515.53) p2 (list 0.00 0.00))
 (command "TEXT" "J" "ML" p1   0.75  0.00 "")
 (setq p1 (list 553.75 1515.53) p2 (list 0.00 0.00))
 (command "TEXT" "J" "ML" p1   0.75  0.00 "6700")
 (command "LAYER" "S" "CGBLITHTXT" "")
 (setq p1 (list 557.50 1515.53) p2 (list 0.00 0.00))
 (command "TEXT" "J" "ML" p1   0.75  0.00 "GRY SS W/SH STKS")
 (command "LAYER" "S" "CGBCMNT" "")
 (setq p1 (list 577.75 1515.53) p2 (list 0.00 0.00))
 (command "TEXT" "J" "ML" p1   0.75  0.00 "SLC, ANG RIPS")
 (command "LAYER" "S" "CGBMAIN" "")
 (setq p1 (list 535.00 1520.92) p2 (list 541.00 1520.92) p3 (list 541.00 1519.12) p4 (list 535.00 1519.12))
 (command "PLINE" p1 p2 p3 p4 "c")
 (command "HATCH" "ZIGZAG" 4.00 0.00 "L" "")
 (command "COLOR" "BYLAYER")
 (command "LAYER" "S" "CGBLITHCD" "")
 (setq p1 (list 541.00 1520.02) p2 (list 542.35 1514.65))
 (command "LINE" p1 p2 "")
 (setq p1 (list 542.50 1514.28) p2 (list 0.00 0.00))
 (command "TEXT" "J" "ML" p1   0.75  0.00 "124")
 (command "LAYER" "S" "CGBTHK" "")
 (setq p1 (list 547.00 1514.28) p2 (list 0.00 0.00))
 (command "TEXT" "J" "ML" p1   0.75  0.00 "1.80")
 (command "LAYER" "S" "CGBHZID" "")
 (setq p1 (list 551.50 1514.28) p2 (list 0.00 0.00))
 (command "TEXT" "J" "ML" p1   0.75  0.00 "")
 (setq p1 (list 553.75 1514.28) p2 (list 0.00 0.00))
 (command "TEXT" "J" "ML" p1   0.75  0.00 "6651")
 (command "LAYER" "S" "CGBLITHTXT" "")
 (setq p1 (list 557.50 1514.28) p2 (list 0.00 0.00))
 (command "TEXT" "J" "ML" p1   0.75  0.00 "DRK GRY SH")
 (command "LAYER" "S" "CGBCMNT" "")
 (setq p1 (list 577.75 1514.28) p2 (list 0.00 0.00))
 (command "TEXT" "J" "ML" p1   0.75  0.00 "V SFT,SLX,BRK")
 (command "LAYER" "S" "CGBMAIN" "")
 (setq p1 (list 535.00 1519.12) p2 (list 541.00 1519.12) p3 (list 541.00 1518.96) p4 (list 535.00 1518.96))
 (command "PLINE" p1 p2 p3 p4 "c")
 (command "HATCH" "ZIGZAG" 5.00 0.00 "L" "")
 (command "COLOR" "BYLAYER")
 (command "LAYER" "S" "CGBLITHCD" "")
 (setq p1 (list 541.00 1519.04) p2 (list 542.35 1513.40))
 (command "LINE" p1 p2 "")
 (setq p1 (list 542.50 1513.03) p2 (list 0.00 0.00))
 (command "TEXT" "J" "ML" p1   0.75  0.00 "322")
 (command "LAYER" "S" "CGBTHK" "")
 (setq p1 (list 547.00 1513.03) p2 (list 0.00 0.00))
 (command "TEXT" "J" "ML" p1   0.75  0.00 "0.16")
 (command "LAYER" "S" "CGBHZID" "")
 (setq p1 (list 551.50 1513.03) p2 (list 0.00 0.00))
 (command "TEXT" "J" "ML" p1   0.75  0.00 "")
 (setq p1 (list 553.75 1513.03) p2 (list 0.00 0.00))
 (command "TEXT" "J" "ML" p1   0.75  0.00 "6651")
 (command "LAYER" "S" "CGBLITHTXT" "")
 (setq p1 (list 557.50 1513.03) p2 (list 0.00 0.00))
 (command "TEXT" "J" "ML" p1   0.75  0.00 "DRK GRY SH+INTERBED SS")
 (command "LAYER" "S" "CGBCMNT" "")
 (setq p1 (list 577.75 1513.03) p2 (list 0.00 0.00))
 (command "TEXT" "J" "ML" p1   0.75  0.00 "ANGULAR")
 (command "LAYER" "S" "CGBMAIN" "")
 (setq p1 (list 535.00 1518.96) p2 (list 541.00 1518.96) p3 (list 541.00 1517.11) p4 (list 535.00 1517.11))
 (command "PLINE" p1 p2 p3 p4 "c")
 (command "HATCH" "ZIGZAG" 4.00 0.00 "L" "")
 (command "COLOR" "BYLAYER")
 (command "LAYER" "S" "CGBLITHCD" "")
 (setq p1 (list 541.00 1518.04) p2 (list 542.35 1512.15))
 (command "LINE" p1 p2 "")
 (setq p1 (list 542.50 1511.78) p2 (list 0.00 0.00))
 (command "TEXT" "J" "ML" p1   0.75  0.00 "124")
 (command "LAYER" "S" "CGBTHK" "")
 (setq p1 (list 547.00 1511.78) p2 (list 0.00 0.00))
 (command "TEXT" "J" "ML" p1   0.75  0.00 "1.85")
 (command "LAYER" "S" "CGBHZID" "")
 (setq p1 (list 551.50 1511.78) p2 (list 0.00 0.00))
 (command "TEXT" "J" "ML" p1   0.75  0.00 "")
 (setq p1 (list 553.75 1511.78) p2 (list 0.00 0.00))
 (command "TEXT" "J" "ML" p1   0.75  0.00 "6651")
 (command "LAYER" "S" "CGBLITHTXT" "")
 (setq p1 (list 557.50 1511.78) p2 (list 0.00 0.00))
 (command "TEXT" "J" "ML" p1   0.75  0.00 "DRK GRY SH")
 (command "LAYER" "S" "CGBCMNT" "")
 (setq p1 (list 577.75 1511.78) p2 (list 0.00 0.00))
 (command "TEXT" "J" "ML" p1   0.75  0.00 "SFT")
 (command "LAYER" "S" "CGBMAIN" "")
 (setq p1 (list 535.00 1517.11) p2 (list 541.00 1517.11) p3 (list 541.00 1514.87) p4 (list 535.00 1514.87))
 (command "PLINE" p1 p2 p3 p4 "c")
 (command "HATCH" "ZIGZAG" 4.00 0.00 "L" "")
 (command "COLOR" "BYLAYER")
 (command "LAYER" "S" "CGBLITHCD" "")
 (setq p1 (list 541.00 1515.99) p2 (list 542.35 1510.90))
 (command "LINE" p1 p2 "")
 (setq p1 (list 542.50 1510.53) p2 (list 0.00 0.00))
 (command "TEXT" "J" "ML" p1   0.75  0.00 "124")
 (command "LAYER" "S" "CGBTHK" "")
 (setq p1 (list 547.00 1510.53) p2 (list 0.00 0.00))
 (command "TEXT" "J" "ML" p1   0.75  0.00 "2.24")
 (command "LAYER" "S" "CGBHZID" "")
 (setq p1 (list 551.50 1510.53) p2 (list 0.00 0.00))
 (command "TEXT" "J" "ML" p1   0.75  0.00 "")
 (setq p1 (list 553.75 1510.53) p2 (list 0.00 0.00))
 (command "TEXT" "J" "ML" p1   0.75  0.00 "6651")
 (command "LAYER" "S" "CGBLITHTXT" "")
 (setq p1 (list 557.50 1510.53) p2 (list 0.00 0.00))
 (command "TEXT" "J" "ML" p1   0.75  0.00 "DRK GRY SH")
 (command "LAYER" "S" "CGBCMNT" "")
 (setq p1 (list 577.75 1510.53) p2 (list 0.00 0.00))
 (command "TEXT" "J" "ML" p1   0.75  0.00 "V SFT,ANG BED")
 (command "LAYER" "S" "CGBMAIN" "")
 (setq p1 (list 535.00 1514.87) p2 (list 541.00 1514.87) p3 (list 541.00 1514.48) p4 (list 535.00 1514.48))
 (command "PLINE" p1 p2 p3 p4 "c")
 (command "HATCH" "ZIGZAG" 5.00 0.00 "L" "")
 (command "COLOR" "BYLAYER")
 (command "LAYER" "S" "CGBLITHCD" "")
 (setq p1 (list 541.00 1514.68) p2 (list 542.35 1509.65))
 (command "LINE" p1 p2 "")
 (setq p1 (list 542.50 1509.28) p2 (list 0.00 0.00))
 (command "TEXT" "J" "ML" p1   0.75  0.00 "322")
 (command "LAYER" "S" "CGBTHK" "")
 (setq p1 (list 547.00 1509.28) p2 (list 0.00 0.00))
 (command "TEXT" "J" "ML" p1   0.75  0.00 "0.39")
 (command "LAYER" "S" "CGBHZID" "")
 (setq p1 (list 551.50 1509.28) p2 (list 0.00 0.00))
 (command "TEXT" "J" "ML" p1   0.75  0.00 "")
 (setq p1 (list 553.75 1509.28) p2 (list 0.00 0.00))
 (command "TEXT" "J" "ML" p1   0.75  0.00 "6651")
 (command "LAYER" "S" "CGBLITHTXT" "")
 (setq p1 (list 557.50 1509.28) p2 (list 0.00 0.00))
 (command "TEXT" "J" "ML" p1   0.75  0.00 "DRK GRY SH+INTERBED SS")
 (command "LAYER" "S" "CGBCMNT" "")
 (setq p1 (list 577.75 1509.28) p2 (list 0.00 0.00))
 (command "TEXT" "J" "ML" p1   0.75  0.00 "ANG (ACCRTION")
 (command "LAYER" "S" "CGBMAIN" "")
 (setq p1 (list 535.00 1514.48) p2 (list 541.00 1514.48) p3 (list 541.00 1514.11) p4 (list 535.00 1514.11))
 (command "PLINE" p1 p2 p3 p4 "c")
 (command "HATCH" "ZIGZAG" 4.00 0.00 "L" "")
 (command "COLOR" "BYLAYER")
 (command "LAYER" "S" "CGBLITHCD" "")
 (setq p1 (list 541.00 1514.30) p2 (list 542.35 1508.40))
 (command "LINE" p1 p2 "")
 (setq p1 (list 542.50 1508.03) p2 (list 0.00 0.00))
 (command "TEXT" "J" "ML" p1   0.75  0.00 "124")
 (command "LAYER" "S" "CGBTHK" "")
 (setq p1 (list 547.00 1508.03) p2 (list 0.00 0.00))
 (command "TEXT" "J" "ML" p1   0.75  0.00 "0.37")
 (command "LAYER" "S" "CGBHZID" "")
 (setq p1 (list 551.50 1508.03) p2 (list 0.00 0.00))
 (command "TEXT" "J" "ML" p1   0.75  0.00 "")
 (setq p1 (list 553.75 1508.03) p2 (list 0.00 0.00))
 (command "TEXT" "J" "ML" p1   0.75  0.00 "6651")
 (command "LAYER" "S" "CGBLITHTXT" "")
 (setq p1 (list 557.50 1508.03) p2 (list 0.00 0.00))
 (command "TEXT" "J" "ML" p1   0.75  0.00 "DRK GRY SH")
 (command "LAYER" "S" "CGBCMNT" "")
 (setq p1 (list 577.75 1508.03) p2 (list 0.00 0.00))
 (command "TEXT" "J" "ML" p1   0.75  0.00 "SFT,ANG BDS")
 (command "LAYER" "S" "CGBMAIN" "")
 (setq p1 (list 535.00 1514.11) p2 (list 541.00 1514.11) p3 (list 541.00 1509.60) p4 (list 535.00 1509.60))
 (command "PLINE" p1 p2 p3 p4 "c")
 (command "HATCH" "ZIGZAG" 5.00 0.00 "L" "")
 (command "COLOR" "BYLAYER")
 (command "LAYER" "S" "CGBLITHCD" "")
 (setq p1 (list 541.00 1511.86) p2 (list 542.35 1507.15))
 (command "LINE" p1 p2 "")
 (setq p1 (list 542.50 1506.78) p2 (list 0.00 0.00))
 (command "TEXT" "J" "ML" p1   0.75  0.00 "322")
 (command "LAYER" "S" "CGBTHK" "")
 (setq p1 (list 547.00 1506.78) p2 (list 0.00 0.00))
 (command "TEXT" "J" "ML" p1   0.75  0.00 "4.51")
 (command "LAYER" "S" "CGBHZID" "")
 (setq p1 (list 551.50 1506.78) p2 (list 0.00 0.00))
 (command "TEXT" "J" "ML" p1   0.75  0.00 "")
 (setq p1 (list 553.75 1506.78) p2 (list 0.00 0.00))
 (command "TEXT" "J" "ML" p1   0.75  0.00 "6651")
 (command "LAYER" "S" "CGBLITHTXT" "")
 (setq p1 (list 557.50 1506.78) p2 (list 0.00 0.00))
 (command "TEXT" "J" "ML" p1   0.75  0.00 "DRK GRY SH+INTERBED SS")
 (command "LAYER" "S" "CGBCMNT" "")
 (setq p1 (list 577.75 1506.78) p2 (list 0.00 0.00))
 (command "TEXT" "J" "ML" p1   0.75  0.00 "ANG RIP W/V S")
 (command "LAYER" "S" "CGBMAIN" "")
 (setq p1 (list 535.00 1509.60) p2 (list 541.00 1509.60) p3 (list 541.00 1508.65) p4 (list 535.00 1508.65))
 (command "PLINE" p1 p2 p3 p4 "c")
 (command "HATCH" "ZIGZAG" 4.00 0.00 "L" "")
 (command "COLOR" "BYLAYER")
 (command "LAYER" "S" "CGBLITHCD" "")
 (setq p1 (list 541.00 1509.13) p2 (list 542.35 1505.90))
 (command "LINE" p1 p2 "")
 (setq p1 (list 542.50 1505.53) p2 (list 0.00 0.00))
 (command "TEXT" "J" "ML" p1   0.75  0.00 "543")
 (command "LAYER" "S" "CGBTHK" "")
 (setq p1 (list 547.00 1505.53) p2 (list 0.00 0.00))
 (command "TEXT" "J" "ML" p1   0.75  0.00 "0.95")
 (command "LAYER" "S" "CGBHZID" "")
 (setq p1 (list 551.50 1505.53) p2 (list 0.00 0.00))
 (command "TEXT" "J" "ML" p1   0.75  0.00 "")
 (setq p1 (list 553.75 1505.53) p2 (list 0.00 0.00))
 (command "TEXT" "J" "ML" p1   0.75  0.00 "6400")
 (command "LAYER" "S" "CGBLITHTXT" "")
 (setq p1 (list 557.50 1505.53) p2 (list 0.00 0.00))
 (command "TEXT" "J" "ML" p1   0.75  0.00 "GRY SS W/SH STKS")
 (command "LAYER" "S" "CGBCMNT" "")
 (setq p1 (list 577.75 1505.53) p2 (list 0.00 0.00))
 (command "TEXT" "J" "ML" p1   0.75  0.00 "SFT ANG SH LA")
 (command "LAYER" "S" "CGBMAIN" "")
 (setq p1 (list 535.00 1508.65) p2 (list 541.00 1508.65) p3 (list 541.00 1508.19) p4 (list 535.00 1508.19))
 (command "PLINE" p1 p2 p3 p4 "c")
 (command "HATCH" "ZIGZAG" 5.00 0.00 "L" "")
 (command "COLOR" "BYLAYER")
 (command "LAYER" "S" "CGBLITHCD" "")
 (setq p1 (list 541.00 1508.42) p2 (list 542.35 1504.65))
 (command "LINE" p1 p2 "")
 (setq p1 (list 542.50 1504.28) p2 (list 0.00 0.00))
 (command "TEXT" "J" "ML" p1   0.75  0.00 "322")
 (command "LAYER" "S" "CGBTHK" "")
 (setq p1 (list 547.00 1504.28) p2 (list 0.00 0.00))
 (command "TEXT" "J" "ML" p1   0.75  0.00 "0.46")
 (command "LAYER" "S" "CGBHZID" "")
 (setq p1 (list 551.50 1504.28) p2 (list 0.00 0.00))
 (command "TEXT" "J" "ML" p1   0.75  0.00 "")
 (setq p1 (list 553.75 1504.28) p2 (list 0.00 0.00))
 (command "TEXT" "J" "ML" p1   0.75  0.00 "6400")
 (command "LAYER" "S" "CGBLITHTXT" "")
 (setq p1 (list 557.50 1504.28) p2 (list 0.00 0.00))
 (command "TEXT" "J" "ML" p1   0.75  0.00 "DRK GRY SH+INTERBED SS")
 (command "LAYER" "S" "CGBCMNT" "")
 (setq p1 (list 577.75 1504.28) p2 (list 0.00 0.00))
 (command "TEXT" "J" "ML" p1   0.75  0.00 "SFT,ANG BEDS")
 (command "LAYER" "S" "CGBMAIN" "")
 (setq p1 (list 535.00 1508.19) p2 (list 541.00 1508.19) p3 (list 541.00 1506.36) p4 (list 535.00 1506.36))
 (command "PLINE" p1 p2 p3 p4 "c")
 (command "HATCH" "ZIGZAG" 4.00 0.00 "L" "")
 (command "COLOR" "BYLAYER")
 (command "LAYER" "S" "CGBLITHCD" "")
 (setq p1 (list 541.00 1507.28) p2 (list 542.35 1503.40))
 (command "LINE" p1 p2 "")
 (setq p1 (list 542.50 1503.03) p2 (list 0.00 0.00))
 (command "TEXT" "J" "ML" p1   0.75  0.00 "124")
 (command "LAYER" "S" "CGBTHK" "")
 (setq p1 (list 547.00 1503.03) p2 (list 0.00 0.00))
 (command "TEXT" "J" "ML" p1   0.75  0.00 "1.83")
 (command "LAYER" "S" "CGBHZID" "")
 (setq p1 (list 551.50 1503.03) p2 (list 0.00 0.00))
 (command "TEXT" "J" "ML" p1   0.75  0.00 "")
 (setq p1 (list 553.75 1503.03) p2 (list 0.00 0.00))
 (command "TEXT" "J" "ML" p1   0.75  0.00 "6400")
 (command "LAYER" "S" "CGBLITHTXT" "")
 (setq p1 (list 557.50 1503.03) p2 (list 0.00 0.00))
 (command "TEXT" "J" "ML" p1   0.75  0.00 "DRK GRY SH")
 (command "LAYER" "S" "CGBCMNT" "")
 (setq p1 (list 577.75 1503.03) p2 (list 0.00 0.00))
 (command "TEXT" "J" "ML" p1   0.75  0.00 "V SFT,SLX")
 (command "LAYER" "S" "CGBMAIN" "")
 (setq p1 (list 535.00 1506.36) p2 (list 541.00 1506.36) p3 (list 541.00 1505.55) p4 (list 535.00 1505.55))
 (command "PLINE" p1 p2 p3 p4 "c")
 (command "HATCH" "ZIGZAG" 4.00 0.00 "L" "")
 (command "COLOR" "BYLAYER")
 (command "LAYER" "S" "CGBLITHCD" "")
 (setq p1 (list 541.00 1505.96) p2 (list 542.35 1502.15))
 (command "LINE" p1 p2 "")
 (setq p1 (list 542.50 1501.78) p2 (list 0.00 0.00))
 (command "TEXT" "J" "ML" p1   0.75  0.00 "115")
 (command "LAYER" "S" "CGBTHK" "")
 (setq p1 (list 547.00 1501.78) p2 (list 0.00 0.00))
 (command "TEXT" "J" "ML" p1   0.75  0.00 "0.81")
 (command "LAYER" "S" "CGBHZID" "")
 (setq p1 (list 551.50 1501.78) p2 (list 0.00 0.00))
 (command "TEXT" "J" "ML" p1   0.75  0.00 "")
 (setq p1 (list 553.75 1501.78) p2 (list 0.00 0.00))
 (command "TEXT" "J" "ML" p1   0.75  0.00 "6400")
 (command "LAYER" "S" "CGBLITHTXT" "")
 (setq p1 (list 557.50 1501.78) p2 (list 0.00 0.00))
 (command "TEXT" "J" "ML" p1   0.75  0.00 "BLK CHRND SH")
 (command "LAYER" "S" "CGBCMNT" "")
 (setq p1 (list 577.75 1501.78) p2 (list 0.00 0.00))
 (command "TEXT" "J" "ML" p1   0.75  0.00 "BURS,SS FISS")
 (command "LAYER" "S" "CGBMAIN" "")
 (setq p1 (list 535.00 1505.55) p2 (list 541.00 1505.55) p3 (list 541.00 1505.13) p4 (list 535.00 1505.13))
 (command "PLINE" p1 p2 p3 p4 "c")
 (command "HATCH" "ZIGZAG" 0.25 0.00 "L" "")
 (command "COLOR" "BYLAYER")
 (command "LAYER" "S" "CGBLITHCD" "")
 (setq p1 (list 541.00 1505.34) p2 (list 542.35 1500.90))
 (command "LINE" p1 p2 "")
 (setq p1 (list 542.50 1500.53) p2 (list 0.00 0.00))
 (command "TEXT" "J" "ML" p1   0.75  0.00 "742")
 (command "LAYER" "S" "CGBTHK" "")
 (setq p1 (list 547.00 1500.53) p2 (list 0.00 0.00))
 (command "TEXT" "J" "ML" p1   0.75  0.00 "0.42")
 (command "LAYER" "S" "CGBHZID" "")
 (setq p1 (list 551.50 1500.53) p2 (list 0.00 0.00))
 (command "TEXT" "J" "ML" p1   0.75  0.00 "")
 (setq p1 (list 553.75 1500.53) p2 (list 0.00 0.00))
 (command "TEXT" "J" "ML" p1   0.75  0.00 "6400")
 (command "LAYER" "S" "CGBLITHTXT" "")
 (setq p1 (list 557.50 1500.53) p2 (list 0.00 0.00))
 (command "TEXT" "J" "ML" p1   0.75  0.00 "GRY SH PEB CGL")
 (command "LAYER" "S" "CGBCMNT" "")
 (setq p1 (list 577.75 1500.53) p2 (list 0.00 0.00))
 (command "TEXT" "J" "ML" p1   0.75  0.00 "SLC")
 (command "LAYER" "S" "CGBMAIN" "")
 (setq p1 (list 535.00 1505.13) p2 (list 541.00 1505.13) p3 (list 541.00 1504.80) p4 (list 535.00 1504.80))
 (command "PLINE" p1 p2 p3 p4 "c")
 (command "HATCH" "ZIGZAG" 6.00 0.00 "L" "")
 (command "COLOR" "BYLAYER")
 (command "LAYER" "S" "CGBLITHCD" "")
 (setq p1 (list 541.00 1504.97) p2 (list 542.35 1499.65))
 (command "LINE" p1 p2 "")
 (setq p1 (list 542.50 1499.28) p2 (list 0.00 0.00))
 (command "TEXT" "J" "ML" p1   0.75  0.00 "113")
 (command "LAYER" "S" "CGBTHK" "")
 (setq p1 (list 547.00 1499.28) p2 (list 0.00 0.00))
 (command "TEXT" "J" "ML" p1   0.75  0.00 "0.33")
 (command "LAYER" "S" "CGBHZID" "")
 (setq p1 (list 551.50 1499.28) p2 (list 0.00 0.00))
 (command "TEXT" "J" "ML" p1   0.75  0.00 "")
 (setq p1 (list 553.75 1499.28) p2 (list 0.00 0.00))
 (command "TEXT" "J" "ML" p1   0.75  0.00 "6351")
 (command "LAYER" "S" "CGBLITHTXT" "")
 (setq p1 (list 557.50 1499.28) p2 (list 0.00 0.00))
 (command "TEXT" "J" "ML" p1   0.75  0.00 "BLK SH W/COAL STKS")
 (command "LAYER" "S" "CGBCMNT" "")
 (setq p1 (list 577.75 1499.28) p2 (list 0.00 0.00))
 (command "TEXT" "J" "ML" p1   0.75  0.00 "DEFRMD")
 (command "LAYER" "S" "CGBMAIN" "")
 (setq p1 (list 535.00 1504.80) p2 (list 541.00 1504.80) p3 (list 541.00 1504.61) p4 (list 535.00 1504.61))
 (command "PLINE" p1 p2 p3 p4 "c")
 (command "HATCH" "ZIGZAG" 5.00 0.00 "L" "")
 (command "COLOR" "BYLAYER")
 (command "LAYER" "S" "CGBLITHCD" "")
 (setq p1 (list 541.00 1504.71) p2 (list 542.35 1498.40))
 (command "LINE" p1 p2 "")
 (setq p1 (list 542.50 1498.03) p2 (list 0.00 0.00))
 (command "TEXT" "J" "ML" p1   0.75  0.00 "032")
 (command "LAYER" "S" "CGBTHK" "")
 (setq p1 (list 547.00 1498.03) p2 (list 0.00 0.00))
 (command "TEXT" "J" "ML" p1   0.75  0.00 "0.19")
 (command "LAYER" "S" "CGBHZID" "")
 (setq p1 (list 551.50 1498.03) p2 (list 0.00 0.00))
 (command "TEXT" "J" "ML" p1   0.75  0.00 "")
 (setq p1 (list 553.75 1498.03) p2 (list 0.00 0.00))
 (command "TEXT" "J" "ML" p1   0.75  0.00 "6000")
 (command "LAYER" "S" "CGBLITHTXT" "")
 (setq p1 (list 557.50 1498.03) p2 (list 0.00 0.00))
 (command "TEXT" "J" "ML" p1   0.75  0.00 "BONE W/COAL LAYERS")
 (command "LAYER" "S" "CGBCMNT" "")
 (setq p1 (list 577.75 1498.03) p2 (list 0.00 0.00))
 (command "TEXT" "J" "ML" p1   0.75  0.00 "DULL W/VIT")
 (command "LAYER" "S" "CGBMAIN" "")
 (setq p1 (list 535.00 1504.61) p2 (list 541.00 1504.61) p3 (list 541.00 1503.51) p4 (list 535.00 1503.51))
 (command "PLINE" p1 p2 p3 p4 "c")
 (command "COLOR" "BLUE")
 (command "SOLID" p1 p2 p4 p3 "")
 (command "COLOR" "BYLAYER")
 (command "LAYER" "S" "CGBLITHCD" "")
 (setq p1 (list 541.00 1504.06) p2 (list 542.35 1497.15))
 (command "LINE" p1 p2 "")
 (setq p1 (list 542.50 1496.78) p2 (list 0.00 0.00))
 (command "TEXT" "J" "ML" p1   0.75  0.00 "021")
 (command "LAYER" "S" "CGBTHK" "")
 (setq p1 (list 547.00 1496.78) p2 (list 0.00 0.00))
 (command "TEXT" "J" "ML" p1   0.75  0.00 "1.10")
 (command "LAYER" "S" "CGBHZID" "")
 (setq p1 (list 551.50 1496.78) p2 (list 0.00 0.00))
 (command "TEXT" "J" "ML" p1   0.75  0.00 "")
 (setq p1 (list 553.75 1496.78) p2 (list 0.00 0.00))
 (command "TEXT" "J" "ML" p1   0.75  0.00 "6000")
 (command "LAYER" "S" "CGBLITHTXT" "")
 (setq p1 (list 557.50 1496.78) p2 (list 0.00 0.00))
 (command "TEXT" "J" "ML" p1   0.75  0.00 "COMMON BANDED COAL")
 (command "LAYER" "S" "CGBCMNT" "")
 (setq p1 (list 577.75 1496.78) p2 (list 0.00 0.00))
 (command "TEXT" "J" "ML" p1   0.75  0.00 "SLGHT ANG BDS")
 (command "LAYER" "S" "CGBMAIN" "")
 (setq p1 (list 535.00 1503.51) p2 (list 541.00 1503.51) p3 (list 541.00 1503.14) p4 (list 535.00 1503.14))
 (command "PLINE" p1 p2 p3 p4 "c")
 (command "HATCH" "ZIGZAG" 6.00 0.00 "L" "")
 (command "COLOR" "BYLAYER")
 (command "LAYER" "S" "CGBLITHCD" "")
 (setq p1 (list 541.00 1503.33) p2 (list 542.35 1495.90))
 (command "LINE" p1 p2 "")
 (setq p1 (list 542.50 1495.53) p2 (list 0.00 0.00))
 (command "TEXT" "J" "ML" p1   0.75  0.00 "113")
 (command "LAYER" "S" "CGBTHK" "")
 (setq p1 (list 547.00 1495.53) p2 (list 0.00 0.00))
 (command "TEXT" "J" "ML" p1   0.75  0.00 "0.37")
 (command "LAYER" "S" "CGBHZID" "")
 (setq p1 (list 551.50 1495.53) p2 (list 0.00 0.00))
 (command "TEXT" "J" "ML" p1   0.75  0.00 "")
 (setq p1 (list 553.75 1495.53) p2 (list 0.00 0.00))
 (command "TEXT" "J" "ML" p1   0.75  0.00 "5951")
 (command "LAYER" "S" "CGBLITHTXT" "")
 (setq p1 (list 557.50 1495.53) p2 (list 0.00 0.00))
 (command "TEXT" "J" "ML" p1   0.75  0.00 "BLK SH W/COAL STKS")
 (command "LAYER" "S" "CGBCMNT" "")
 (setq p1 (list 577.75 1495.53) p2 (list 0.00 0.00))
 (command "TEXT" "J" "ML" p1   0.75  0.00 "")
 (command "LAYER" "S" "CGBMAIN" "")
 (setq p1 (list 535.00 1503.14) p2 (list 541.00 1503.14) p3 (list 541.00 1503.08) p4 (list 535.00 1503.08))
 (command "PLINE" p1 p2 p3 p4 "c")
 (command "HATCH" "ZIGZAG" 5.00 0.00 "L" "")
 (command "COLOR" "BYLAYER")
 (command "LAYER" "S" "CGBLITHCD" "")
 (setq p1 (list 541.00 1503.11) p2 (list 542.35 1494.65))
 (command "LINE" p1 p2 "")
 (setq p1 (list 542.50 1494.28) p2 (list 0.00 0.00))
 (command "TEXT" "J" "ML" p1   0.75  0.00 "033")
 (command "LAYER" "S" "CGBTHK" "")
 (setq p1 (list 547.00 1494.28) p2 (list 0.00 0.00))
 (command "TEXT" "J" "ML" p1   0.75  0.00 "0.06")
 (command "LAYER" "S" "CGBHZID" "")
 (setq p1 (list 551.50 1494.28) p2 (list 0.00 0.00))
 (command "TEXT" "J" "ML" p1   0.75  0.00 "")
 (setq p1 (list 553.75 1494.28) p2 (list 0.00 0.00))
 (command "TEXT" "J" "ML" p1   0.75  0.00 "5951")
 (command "LAYER" "S" "CGBLITHTXT" "")
 (setq p1 (list 557.50 1494.28) p2 (list 0.00 0.00))
 (command "TEXT" "J" "ML" p1   0.75  0.00 "BONE W/COAL STKS")
 (command "LAYER" "S" "CGBCMNT" "")
 (setq p1 (list 577.75 1494.28) p2 (list 0.00 0.00))
 (command "TEXT" "J" "ML" p1   0.75  0.00 "")
 (command "LAYER" "S" "CGBMAIN" "")
 (command "LAYER" "S" "CGBLITHCD" "")
 (setq p1 (list 541.00 1503.08) p2 (list 542.35 1493.40))
 (command "LINE" p1 p2 "")
 (setq p1 (list 542.50 1493.03) p2 (list 0.00 0.00))
 (command "TEXT" "J" "ML" p1   0.75  0.00 "020")
 (command "LAYER" "S" "CGBTHK" "")
 (setq p1 (list 547.00 1493.03) p2 (list 0.00 0.00))
 (command "TEXT" "J" "ML" p1   0.75  0.00 "0.00")
 (command "LAYER" "S" "CGBHZID" "")
 (setq p1 (list 551.50 1493.03) p2 (list 0.00 0.00))
 (command "TEXT" "J" "ML" p1   0.75  0.00 "")
 (setq p1 (list 553.75 1493.03) p2 (list 0.00 0.00))
 (command "TEXT" "J" "ML" p1   0.75  0.00 "5800")
 (command "LAYER" "S" "CGBLITHTXT" "")
 (setq p1 (list 557.50 1493.03) p2 (list 0.00 0.00))
 (command "TEXT" "J" "ML" p1   0.75  0.00 "COAL")
 (command "LAYER" "S" "CGBCMNT" "")
 (setq p1 (list 577.75 1493.03) p2 (list 0.00 0.00))
 (command "TEXT" "J" "ML" p1   0.75  0.00 "")
 (command "LAYER" "S" "CGBMAIN" "")
 (setq p1 (list 535.00 1503.08) p2 (list 541.00 1503.08) p3 (list 541.00 1502.22) p4 (list 535.00 1502.22))
 (command "PLINE" p1 p2 p3 p4 "c")
 (command "HATCH" "ZIGZAG" 1.00 45.00 "L" "")
 (command "COLOR" "BYLAYER")
 (command "LAYER" "S" "CGBLITHCD" "")
 (setq p1 (list 541.00 1502.65) p2 (list 542.35 1492.15))
 (command "LINE" p1 p2 "")
 (setq p1 (list 542.50 1491.78) p2 (list 0.00 0.00))
 (command "TEXT" "J" "ML" p1   0.75  0.00 "028")
 (command "LAYER" "S" "CGBTHK" "")
 (setq p1 (list 547.00 1491.78) p2 (list 0.00 0.00))
 (command "TEXT" "J" "ML" p1   0.75  0.00 "0.86")
 (command "LAYER" "S" "CGBHZID" "")
 (setq p1 (list 551.50 1491.78) p2 (list 0.00 0.00))
 (command "TEXT" "J" "ML" p1   0.75  0.00 "")
 (setq p1 (list 553.75 1491.78) p2 (list 0.00 0.00))
 (command "TEXT" "J" "ML" p1   0.75  0.00 "5500")
 (command "LAYER" "S" "CGBLITHTXT" "")
 (setq p1 (list 557.50 1491.78) p2 (list 0.00 0.00))
 (command "TEXT" "J" "ML" p1   0.75  0.00 "COAL W/SH STKS")
 (command "LAYER" "S" "CGBCMNT" "")
 (setq p1 (list 577.75 1491.78) p2 (list 0.00 0.00))
 (command "TEXT" "J" "ML" p1   0.75  0.00 "DULL W/VIT")
 (command "LAYER" "S" "CGBMAIN" "")
 (setq p1 (list 535.00 1502.22) p2 (list 541.00 1502.22) p3 (list 541.00 1502.14) p4 (list 535.00 1502.14))
 (command "PLINE" p1 p2 p3 p4 "c")
 (command "HATCH" "ZIGZAG" 4.00 22.50 "L" "")
 (command "COLOR" "BYLAYER")
 (command "LAYER" "S" "CGBLITHCD" "")
 (setq p1 (list 541.00 1502.18) p2 (list 542.35 1490.90))
 (command "LINE" p1 p2 "")
 (setq p1 (list 542.50 1490.53) p2 (list 0.00 0.00))
 (command "TEXT" "J" "ML" p1   0.75  0.00 "114")
 (command "LAYER" "S" "CGBTHK" "")
 (setq p1 (list 547.00 1490.53) p2 (list 0.00 0.00))
 (command "TEXT" "J" "ML" p1   0.75  0.00 "0.08")
 (command "LAYER" "S" "CGBHZID" "")
 (setq p1 (list 551.50 1490.53) p2 (list 0.00 0.00))
 (command "TEXT" "J" "ML" p1   0.75  0.00 "")
 (setq p1 (list 553.75 1490.53) p2 (list 0.00 0.00))
 (command "TEXT" "J" "ML" p1   0.75  0.00 "5500")
 (command "LAYER" "S" "CGBLITHTXT" "")
 (setq p1 (list 557.50 1490.53) p2 (list 0.00 0.00))
 (command "TEXT" "J" "ML" p1   0.75  0.00 "BLK SH")
 (command "LAYER" "S" "CGBCMNT" "")
 (setq p1 (list 577.75 1490.53) p2 (list 0.00 0.00))
 (command "TEXT" "J" "ML" p1   0.75  0.00 "")
 (command "LAYER" "S" "CGBMAIN" "")
 (setq p1 (list 535.00 1502.14) p2 (list 541.00 1502.14) p3 (list 541.00 1501.28) p4 (list 535.00 1501.28))
 (command "PLINE" p1 p2 p3 p4 "c")
 (command "COLOR" "BLUE")
 (command "SOLID" p1 p2 p4 p3 "")
 (command "COLOR" "BYLAYER")
 (command "LAYER" "S" "CGBLITHCD" "")
 (setq p1 (list 541.00 1501.71) p2 (list 542.35 1489.65))
 (command "LINE" p1 p2 "")
 (setq p1 (list 542.50 1489.28) p2 (list 0.00 0.00))
 (command "TEXT" "J" "ML" p1   0.75  0.00 "021")
 (command "LAYER" "S" "CGBTHK" "")
 (setq p1 (list 547.00 1489.28) p2 (list 0.00 0.00))
 (command "TEXT" "J" "ML" p1   0.75  0.00 "0.86")
 (command "LAYER" "S" "CGBHZID" "")
 (setq p1 (list 551.50 1489.28) p2 (list 0.00 0.00))
 (command "TEXT" "J" "ML" p1   0.75  0.00 "")
 (setq p1 (list 553.75 1489.28) p2 (list 0.00 0.00))
 (command "TEXT" "J" "ML" p1   0.75  0.00 "5500")
 (command "LAYER" "S" "CGBLITHTXT" "")
 (setq p1 (list 557.50 1489.28) p2 (list 0.00 0.00))
 (command "TEXT" "J" "ML" p1   0.75  0.00 "COMMON BANDED COAL")
 (command "LAYER" "S" "CGBCMNT" "")
 (setq p1 (list 577.75 1489.28) p2 (list 0.00 0.00))
 (command "TEXT" "J" "ML" p1   0.75  0.00 "VITRAIN")
 (command "LAYER" "S" "CGBMAIN" "")
 (setq p1 (list 535.00 1501.28) p2 (list 541.00 1501.28) p3 (list 541.00 1501.16) p4 (list 535.00 1501.16))
 (command "PLINE" p1 p2 p3 p4 "c")
 (command "HATCH" "ZIGZAG" 4.00 22.50 "L" "")
 (command "COLOR" "BYLAYER")
 (command "LAYER" "S" "CGBLITHCD" "")
 (setq p1 (list 541.00 1501.22) p2 (list 542.35 1488.40))
 (command "LINE" p1 p2 "")
 (setq p1 (list 542.50 1488.03) p2 (list 0.00 0.00))
 (command "TEXT" "J" "ML" p1   0.75  0.00 "114")
 (command "LAYER" "S" "CGBTHK" "")
 (setq p1 (list 547.00 1488.03) p2 (list 0.00 0.00))
 (command "TEXT" "J" "ML" p1   0.75  0.00 "0.12")
 (command "LAYER" "S" "CGBHZID" "")
 (setq p1 (list 551.50 1488.03) p2 (list 0.00 0.00))
 (command "TEXT" "J" "ML" p1   0.75  0.00 "")
 (setq p1 (list 553.75 1488.03) p2 (list 0.00 0.00))
 (command "TEXT" "J" "ML" p1   0.75  0.00 "5500")
 (command "LAYER" "S" "CGBLITHTXT" "")
 (setq p1 (list 557.50 1488.03) p2 (list 0.00 0.00))
 (command "TEXT" "J" "ML" p1   0.75  0.00 "BLK SH")
 (command "LAYER" "S" "CGBCMNT" "")
 (setq p1 (list 577.75 1488.03) p2 (list 0.00 0.00))
 (command "TEXT" "J" "ML" p1   0.75  0.00 "")
 (command "LAYER" "S" "CGBMAIN" "")
 (setq p1 (list 535.00 1501.16) p2 (list 541.00 1501.16) p3 (list 541.00 1500.00) p4 (list 535.00 1500.00))
 (command "PLINE" p1 p2 p3 p4 "c")
 (command "HATCH" "ZIGZAG" 0.40 45.00 "L" "")
 (command "COLOR" "BYLAYER")
 (command "LAYER" "S" "CGBLITHCD" "")
 (setq p1 (list 541.00 1500.58) p2 (list 542.35 1487.15))
 (command "LINE" p1 p2 "")
 (setq p1 (list 542.50 1486.78) p2 (list 0.00 0.00))
 (command "TEXT" "J" "ML" p1   0.75  0.00 "023")
 (command "LAYER" "S" "CGBTHK" "")
 (setq p1 (list 547.00 1486.78) p2 (list 0.00 0.00))
 (command "TEXT" "J" "ML" p1   0.75  0.00 "1.16")
 (command "LAYER" "S" "CGBHZID" "")
 (setq p1 (list 551.50 1486.78) p2 (list 0.00 0.00))
 (command "TEXT" "J" "ML" p1   0.75  0.00 "")
 (setq p1 (list 553.75 1486.78) p2 (list 0.00 0.00))
 (command "TEXT" "J" "ML" p1   0.75  0.00 "5500")
 (command "LAYER" "S" "CGBLITHTXT" "")
 (setq p1 (list 557.50 1486.78) p2 (list 0.00 0.00))
 (command "TEXT" "J" "ML" p1   0.75  0.00 "COAL W/BONE STKS")
 (command "LAYER" "S" "CGBCMNT" "")
 (setq p1 (list 577.75 1486.78) p2 (list 0.00 0.00))
 (command "TEXT" "J" "ML" p1   0.75  0.00 "DULL W/VIT")
 (command "LAYER" "S" "CGBMAIN" "")
 (setq p1 (list 535.00 1500.00) p2 (list 541.00 1500.00) p3 (list 541.00 1499.22) p4 (list 535.00 1499.22))
 (command "PLINE" p1 p2 p3 p4 "c")
 (command "HATCH" "ZIGZAG" 0.25 0.00 "L" "")
 (command "COLOR" "BYLAYER")
 (command "LAYER" "S" "CGBLITHCD" "")
 (setq p1 (list 541.00 1499.61) p2 (list 542.35 1485.90))
 (command "LINE" p1 p2 "")
 (setq p1 (list 542.50 1485.53) p2 (list 0.00 0.00))
 (command "TEXT" "J" "ML" p1   0.75  0.00 "327")
 (command "LAYER" "S" "CGBTHK" "")
 (setq p1 (list 547.00 1485.53) p2 (list 0.00 0.00))
 (command "TEXT" "J" "ML" p1   0.75  0.00 "0.78")
 (command "LAYER" "S" "CGBHZID" "")
 (setq p1 (list 551.50 1485.53) p2 (list 0.00 0.00))
 (command "TEXT" "J" "ML" p1   0.75  0.00 "")
 (setq p1 (list 553.75 1485.53) p2 (list 0.00 0.00))
 (command "TEXT" "J" "ML" p1   0.75  0.00 "5451")
 (command "LAYER" "S" "CGBLITHTXT" "")
 (setq p1 (list 557.50 1485.53) p2 (list 0.00 0.00))
 (command "TEXT" "J" "ML" p1   0.75  0.00 "DRK GRY SDY FIRECLAY")
 (command "LAYER" "S" "CGBCMNT" "")
 (setq p1 (list 577.75 1485.53) p2 (list 0.00 0.00))
 (command "TEXT" "J" "ML" p1   0.75  0.00 "MED HRD,GOOD")
 (command "LAYER" "S" "CGBMAIN" "")
 (setq p1 (list 535.00 1499.22) p2 (list 541.00 1499.22) p3 (list 541.00 1496.93) p4 (list 535.00 1496.93))
 (command "PLINE" p1 p2 p3 p4 "c")
 (command "HATCH" "ZIGZAG" 0.25 0.00 "L" "")
 (command "COLOR" "BYLAYER")
 (command "LAYER" "S" "CGBLITHCD" "")
 (setq p1 (list 541.00 1498.08) p2 (list 542.35 1484.65))
 (command "LINE" p1 p2 "")
 (setq p1 (list 542.50 1484.28) p2 (list 0.00 0.00))
 (command "TEXT" "J" "ML" p1   0.75  0.00 "327")
 (command "LAYER" "S" "CGBTHK" "")
 (setq p1 (list 547.00 1484.28) p2 (list 0.00 0.00))
 (command "TEXT" "J" "ML" p1   0.75  0.00 "2.29")
 (command "LAYER" "S" "CGBHZID" "")
 (setq p1 (list 551.50 1484.28) p2 (list 0.00 0.00))
 (command "TEXT" "J" "ML" p1   0.75  0.00 "")
 (setq p1 (list 553.75 1484.28) p2 (list 0.00 0.00))
 (command "TEXT" "J" "ML" p1   0.75  0.00 "5451")
 (command "LAYER" "S" "CGBLITHTXT" "")
 (setq p1 (list 557.50 1484.28) p2 (list 0.00 0.00))
 (command "TEXT" "J" "ML" p1   0.75  0.00 "DRK GRY SDY FIRECLAY")
 (command "LAYER" "S" "CGBCMNT" "")
 (setq p1 (list 577.75 1484.28) p2 (list 0.00 0.00))
 (command "TEXT" "J" "ML" p1   0.75  0.00 "")
 (command "LAYER" "S" "CGBMAIN" "")
 (setq p1 (list 535.00 1496.93) p2 (list 541.00 1496.93) p3 (list 541.00 1495.70) p4 (list 535.00 1495.70))
 (command "PLINE" p1 p2 p3 p4 "c")
 (command "HATCH" "ZIGZAG" 2.50 90.00 "L" "")
 (command "COLOR" "BYLAYER")
 (command "LAYER" "S" "CGBLITHCD" "")
 (setq p1 (list 541.00 1496.32) p2 (list 542.35 1483.40))
 (command "LINE" p1 p2 "")
 (setq p1 (list 542.50 1483.03) p2 (list 0.00 0.00))
 (command "TEXT" "J" "ML" p1   0.75  0.00 "324")
 (command "LAYER" "S" "CGBTHK" "")
 (setq p1 (list 547.00 1483.03) p2 (list 0.00 0.00))
 (command "TEXT" "J" "ML" p1   0.75  0.00 "1.23")
 (command "LAYER" "S" "CGBHZID" "")
 (setq p1 (list 551.50 1483.03) p2 (list 0.00 0.00))
 (command "TEXT" "J" "ML" p1   0.75  0.00 "")
 (setq p1 (list 553.75 1483.03) p2 (list 0.00 0.00))
 (command "TEXT" "J" "ML" p1   0.75  0.00 "5451")
 (command "LAYER" "S" "CGBLITHTXT" "")
 (setq p1 (list 557.50 1483.03) p2 (list 0.00 0.00))
 (command "TEXT" "J" "ML" p1   0.75  0.00 "DRK GRY MASS SDY SH")
 (command "LAYER" "S" "CGBCMNT" "")
 (setq p1 (list 577.75 1483.03) p2 (list 0.00 0.00))
 (command "TEXT" "J" "ML" p1   0.75  0.00 "")
 (command "LAYER" "S" "CGBMAIN" "")
 (setq p1 (list 535.00 1495.70) p2 (list 541.00 1495.70) p3 (list 541.00 1494.75) p4 (list 535.00 1494.75))
 (command "PLINE" p1 p2 p3 p4 "c")
 (command "HATCH" "ZIGZAG" 5.00 0.00 "L" "")
 (command "COLOR" "BYLAYER")
 (command "LAYER" "S" "CGBLITHCD" "")
 (setq p1 (list 541.00 1495.23) p2 (list 542.35 1482.15))
 (command "LINE" p1 p2 "")
 (setq p1 (list 542.50 1481.78) p2 (list 0.00 0.00))
 (command "TEXT" "J" "ML" p1   0.75  0.00 "904")
 (command "LAYER" "S" "CGBTHK" "")
 (setq p1 (list 547.00 1481.78) p2 (list 0.00 0.00))
 (command "TEXT" "J" "ML" p1   0.75  0.00 "0.95")
 (command "LAYER" "S" "CGBHZID" "")
 (setq p1 (list 551.50 1481.78) p2 (list 0.00 0.00))
 (command "TEXT" "J" "ML" p1   0.75  0.00 "")
 (setq p1 (list 553.75 1481.78) p2 (list 0.00 0.00))
 (command "TEXT" "J" "ML" p1   0.75  0.00 "5451")
 (command "LAYER" "S" "CGBLITHTXT" "")
 (setq p1 (list 557.50 1481.78) p2 (list 0.00 0.00))
 (command "TEXT" "J" "ML" p1   0.75  0.00 "MASS FN GRND LS")
 (command "LAYER" "S" "CGBCMNT" "")
 (setq p1 (list 577.75 1481.78) p2 (list 0.00 0.00))
 (command "TEXT" "J" "ML" p1   0.75  0.00 "")
 (command "LAYER" "S" "CGBMAIN" "")
 (setq p1 (list 535.00 1494.75) p2 (list 541.00 1494.75) p3 (list 541.00 1492.25) p4 (list 535.00 1492.25))
 (command "PLINE" p1 p2 p3 p4 "c")
 (command "HATCH" "ZIGZAG" 2.50 90.00 "L" "")
 (command "COLOR" "BYLAYER")
 (command "LAYER" "S" "CGBLITHCD" "")
 (setq p1 (list 541.00 1493.50) p2 (list 542.35 1480.90))
 (command "LINE" p1 p2 "")
 (setq p1 (list 542.50 1480.53) p2 (list 0.00 0.00))
 (command "TEXT" "J" "ML" p1   0.75  0.00 "328")
 (command "LAYER" "S" "CGBTHK" "")
 (setq p1 (list 547.00 1480.53) p2 (list 0.00 0.00))
 (command "TEXT" "J" "ML" p1   0.75  0.00 "2.50")
 (command "LAYER" "S" "CGBHZID" "")
 (setq p1 (list 551.50 1480.53) p2 (list 0.00 0.00))
 (command "TEXT" "J" "ML" p1   0.75  0.00 "")
 (setq p1 (list 553.75 1480.53) p2 (list 0.00 0.00))
 (command "TEXT" "J" "ML" p1   0.75  0.00 "5451")
 (command "LAYER" "S" "CGBLITHTXT" "")
 (setq p1 (list 557.50 1480.53) p2 (list 0.00 0.00))
 (command "TEXT" "J" "ML" p1   0.75  0.00 "DRK GRY BURROWED SDY SH")
 (command "LAYER" "S" "CGBCMNT" "")
 (setq p1 (list 577.75 1480.53) p2 (list 0.00 0.00))
 (command "TEXT" "J" "ML" p1   0.75  0.00 "")
 (command "LAYER" "S" "CGBMAIN" "")
 (setq p1 (list 535.00 1492.25) p2 (list 541.00 1492.25) p3 (list 541.00 1492.00) p4 (list 535.00 1492.00))
 (command "PLINE" p1 p2 p3 p4 "c")
 (command "HATCH" "ZIGZAG" 4.00 0.00 "L" "")
 (command "COLOR" "BYLAYER")
 (command "LAYER" "S" "CGBLITHCD" "")
 (setq p1 (list 541.00 1492.13) p2 (list 542.35 1479.65))
 (command "LINE" p1 p2 "")
 (setq p1 (list 542.50 1479.28) p2 (list 0.00 0.00))
 (command "TEXT" "J" "ML" p1   0.75  0.00 "543")
 (command "LAYER" "S" "CGBTHK" "")
 (setq p1 (list 547.00 1479.28) p2 (list 0.00 0.00))
 (command "TEXT" "J" "ML" p1   0.75  0.00 "0.25")
 (command "LAYER" "S" "CGBHZID" "")
 (setq p1 (list 551.50 1479.28) p2 (list 0.00 0.00))
 (command "TEXT" "J" "ML" p1   0.75  0.00 "")
 (setq p1 (list 553.75 1479.28) p2 (list 0.00 0.00))
 (command "TEXT" "J" "ML" p1   0.75  0.00 "5451")
 (command "LAYER" "S" "CGBLITHTXT" "")
 (setq p1 (list 557.50 1479.28) p2 (list 0.00 0.00))
 (command "TEXT" "J" "ML" p1   0.75  0.00 "GRY SS W/SH STKS")
 (command "LAYER" "S" "CGBCMNT" "")
 (setq p1 (list 577.75 1479.28) p2 (list 0.00 0.00))
 (command "TEXT" "J" "ML" p1   0.75  0.00 "")
 (command "LAYER" "S" "CGBMAIN" "")
 (setq p1 (list 535.00 1492.00) p2 (list 541.00 1492.00) p3 (list 541.00 1490.88) p4 (list 535.00 1490.88))
 (command "PLINE" p1 p2 p3 p4 "c")
 (command "HATCH" "ZIGZAG" 2.50 90.00 "L" "")
 (command "COLOR" "BYLAYER")
 (command "LAYER" "S" "CGBLITHCD" "")
 (setq p1 (list 541.00 1491.44) p2 (list 542.35 1478.40))
 (command "LINE" p1 p2 "")
 (setq p1 (list 542.50 1478.03) p2 (list 0.00 0.00))
 (command "TEXT" "J" "ML" p1   0.75  0.00 "324")
 (command "LAYER" "S" "CGBTHK" "")
 (setq p1 (list 547.00 1478.03) p2 (list 0.00 0.00))
 (command "TEXT" "J" "ML" p1   0.75  0.00 "1.12")
 (command "LAYER" "S" "CGBHZID" "")
 (setq p1 (list 551.50 1478.03) p2 (list 0.00 0.00))
 (command "TEXT" "J" "ML" p1   0.75  0.00 "")
 (setq p1 (list 553.75 1478.03) p2 (list 0.00 0.00))
 (command "TEXT" "J" "ML" p1   0.75  0.00 "5451")
 (command "LAYER" "S" "CGBLITHTXT" "")
 (setq p1 (list 557.50 1478.03) p2 (list 0.00 0.00))
 (command "TEXT" "J" "ML" p1   0.75  0.00 "DRK GRY MASS SDY SH")
 (command "LAYER" "S" "CGBCMNT" "")
 (setq p1 (list 577.75 1478.03) p2 (list 0.00 0.00))
 (command "TEXT" "J" "ML" p1   0.75  0.00 "")
 (command "LAYER" "S" "CGBMAIN" "")
 (setq p1 (list 535.00 1490.88) p2 (list 541.00 1490.88) p3 (list 541.00 1485.91) p4 (list 535.00 1485.91))
 (command "PLINE" p1 p2 p3 p4 "c")
 (command "HATCH" "ZIGZAG" 5.00 0.00 "L" "")
 (command "COLOR" "BYLAYER")
 (command "LAYER" "S" "CGBLITHCD" "")
 (setq p1 (list 541.00 1488.40) p2 (list 542.35 1477.15))
 (command "LINE" p1 p2 "")
 (setq p1 (list 542.50 1476.78) p2 (list 0.00 0.00))
 (command "TEXT" "J" "ML" p1   0.75  0.00 "322")
 (command "LAYER" "S" "CGBTHK" "")
 (setq p1 (list 547.00 1476.78) p2 (list 0.00 0.00))
 (command "TEXT" "J" "ML" p1   0.75  0.00 "4.97")
 (command "LAYER" "S" "CGBHZID" "")
 (setq p1 (list 551.50 1476.78) p2 (list 0.00 0.00))
 (command "TEXT" "J" "ML" p1   0.75  0.00 "")
 (setq p1 (list 553.75 1476.78) p2 (list 0.00 0.00))
 (command "TEXT" "J" "ML" p1   0.75  0.00 "5451")
 (command "LAYER" "S" "CGBLITHTXT" "")
 (setq p1 (list 557.50 1476.78) p2 (list 0.00 0.00))
 (command "TEXT" "J" "ML" p1   0.75  0.00 "DRK GRY SH+INTERBED SS")
 (command "LAYER" "S" "CGBCMNT" "")
 (setq p1 (list 577.75 1476.78) p2 (list 0.00 0.00))
 (command "TEXT" "J" "ML" p1   0.75  0.00 "")
 (command "LAYER" "S" "CGBMAIN" "")
 (setq p1 (list 535.00 1485.91) p2 (list 541.00 1485.91) p3 (list 541.00 1483.54) p4 (list 535.00 1483.54))
 (command "PLINE" p1 p2 p3 p4 "c")
 (command "HATCH" "ZIGZAG" 5.00 0.00 "L" "")
 (command "COLOR" "BYLAYER")
 (command "LAYER" "S" "CGBLITHCD" "")
 (setq p1 (list 541.00 1484.73) p2 (list 542.35 1475.90))
 (command "LINE" p1 p2 "")
 (setq p1 (list 542.50 1475.53) p2 (list 0.00 0.00))
 (command "TEXT" "J" "ML" p1   0.75  0.00 "322")
 (command "LAYER" "S" "CGBTHK" "")
 (setq p1 (list 547.00 1475.53) p2 (list 0.00 0.00))
 (command "TEXT" "J" "ML" p1   0.75  0.00 "2.37")
 (command "LAYER" "S" "CGBHZID" "")
 (setq p1 (list 551.50 1475.53) p2 (list 0.00 0.00))
 (command "TEXT" "J" "ML" p1   0.75  0.00 "")
 (setq p1 (list 553.75 1475.53) p2 (list 0.00 0.00))
 (command "TEXT" "J" "ML" p1   0.75  0.00 "5451")
 (command "LAYER" "S" "CGBLITHTXT" "")
 (setq p1 (list 557.50 1475.53) p2 (list 0.00 0.00))
 (command "TEXT" "J" "ML" p1   0.75  0.00 "DRK GRY SH+INTERBED SS")
 (command "LAYER" "S" "CGBCMNT" "")
 (setq p1 (list 577.75 1475.53) p2 (list 0.00 0.00))
 (command "TEXT" "J" "ML" p1   0.75  0.00 "SLC")
 (command "LAYER" "S" "CGBMAIN" "")
 (setq p1 (list 535.00 1483.54) p2 (list 541.00 1483.54) p3 (list 541.00 1483.28) p4 (list 535.00 1483.28))
 (command "PLINE" p1 p2 p3 p4 "c")
 (command "HATCH" "ZIGZAG" 4.00 0.00 "L" "")
 (command "COLOR" "BYLAYER")
 (command "LAYER" "S" "CGBLITHCD" "")
 (setq p1 (list 541.00 1483.41) p2 (list 542.35 1474.65))
 (command "LINE" p1 p2 "")
 (setq p1 (list 542.50 1474.28) p2 (list 0.00 0.00))
 (command "TEXT" "J" "ML" p1   0.75  0.00 "123")
 (command "LAYER" "S" "CGBTHK" "")
 (setq p1 (list 547.00 1474.28) p2 (list 0.00 0.00))
 (command "TEXT" "J" "ML" p1   0.75  0.00 "0.26")
 (command "LAYER" "S" "CGBHZID" "")
 (setq p1 (list 551.50 1474.28) p2 (list 0.00 0.00))
 (command "TEXT" "J" "ML" p1   0.75  0.00 "")
 (setq p1 (list 553.75 1474.28) p2 (list 0.00 0.00))
 (command "TEXT" "J" "ML" p1   0.75  0.00 "5451")
 (command "LAYER" "S" "CGBLITHTXT" "")
 (setq p1 (list 557.50 1474.28) p2 (list 0.00 0.00))
 (command "TEXT" "J" "ML" p1   0.75  0.00 "DRK GRY SH W/COAL STKS")
 (command "LAYER" "S" "CGBCMNT" "")
 (setq p1 (list 577.75 1474.28) p2 (list 0.00 0.00))
 (command "TEXT" "J" "ML" p1   0.75  0.00 "")
 (command "LAYER" "S" "CGBMAIN" "")
 (setq p1 (list 534.50 1807.74) p2 (list 535.00 1807.74))
 (command "LINE" p1 p2 "")
 (setq p1 (list 534.13 1807.74) p2 (list 0.00 0.00))
 (command "TEXT" "J" "MR" p1   0.75  0.00 "0.00")
 (setq p1 (list 534.13 1806.62) p2 (list 0.00 0.00))
 (command "TEXT" "J" "MR" p1   0.75  0.00 "3332.88")
 (setq p1 (list 534.50 1797.74) p2 (list 535.00 1797.74))
 (command "LINE" p1 p2 "")
 (setq p1 (list 534.13 1797.74) p2 (list 0.00 0.00))
 (command "TEXT" "J" "MR" p1   0.75  0.00 "10.00")
 (setq p1 (list 534.13 1796.62) p2 (list 0.00 0.00))
 (command "TEXT" "J" "MR" p1   0.75  0.00 "3322.88")
 (setq p1 (list 534.50 1787.74) p2 (list 535.00 1787.74))
 (command "LINE" p1 p2 "")
 (setq p1 (list 534.13 1787.74) p2 (list 0.00 0.00))
 (command "TEXT" "J" "MR" p1   0.75  0.00 "20.00")
 (setq p1 (list 534.13 1786.62) p2 (list 0.00 0.00))
 (command "TEXT" "J" "MR" p1   0.75  0.00 "3312.88")
 (setq p1 (list 534.50 1777.74) p2 (list 535.00 1777.74))
 (command "LINE" p1 p2 "")
 (setq p1 (list 534.13 1777.74) p2 (list 0.00 0.00))
 (command "TEXT" "J" "MR" p1   0.75  0.00 "30.00")
 (setq p1 (list 534.13 1776.62) p2 (list 0.00 0.00))
 (command "TEXT" "J" "MR" p1   0.75  0.00 "3302.88")
 (setq p1 (list 534.50 1767.74) p2 (list 535.00 1767.74))
 (command "LINE" p1 p2 "")
 (setq p1 (list 534.13 1767.74) p2 (list 0.00 0.00))
 (command "TEXT" "J" "MR" p1   0.75  0.00 "40.00")
 (setq p1 (list 534.13 1766.62) p2 (list 0.00 0.00))
 (command "TEXT" "J" "MR" p1   0.75  0.00 "3292.88")
 (setq p1 (list 534.50 1757.74) p2 (list 535.00 1757.74))
 (command "LINE" p1 p2 "")
 (setq p1 (list 534.13 1757.74) p2 (list 0.00 0.00))
 (command "TEXT" "J" "MR" p1   0.75  0.00 "50.00")
 (setq p1 (list 534.13 1756.62) p2 (list 0.00 0.00))
 (command "TEXT" "J" "MR" p1   0.75  0.00 "3282.88")
 (setq p1 (list 534.50 1747.74) p2 (list 535.00 1747.74))
 (command "LINE" p1 p2 "")
 (setq p1 (list 534.13 1747.74) p2 (list 0.00 0.00))
 (command "TEXT" "J" "MR" p1   0.75  0.00 "60.00")
 (setq p1 (list 534.13 1746.62) p2 (list 0.00 0.00))
 (command "TEXT" "J" "MR" p1   0.75  0.00 "3272.88")
 (setq p1 (list 534.50 1737.74) p2 (list 535.00 1737.74))
 (command "LINE" p1 p2 "")
 (setq p1 (list 534.13 1737.74) p2 (list 0.00 0.00))
 (command "TEXT" "J" "MR" p1   0.75  0.00 "70.00")
 (setq p1 (list 534.13 1736.62) p2 (list 0.00 0.00))
 (command "TEXT" "J" "MR" p1   0.75  0.00 "3262.88")
 (setq p1 (list 534.50 1727.74) p2 (list 535.00 1727.74))
 (command "LINE" p1 p2 "")
 (setq p1 (list 534.13 1727.74) p2 (list 0.00 0.00))
 (command "TEXT" "J" "MR" p1   0.75  0.00 "80.00")
 (setq p1 (list 534.13 1726.62) p2 (list 0.00 0.00))
 (command "TEXT" "J" "MR" p1   0.75  0.00 "3252.88")
 (setq p1 (list 534.50 1717.74) p2 (list 535.00 1717.74))
 (command "LINE" p1 p2 "")
 (setq p1 (list 534.13 1717.74) p2 (list 0.00 0.00))
 (command "TEXT" "J" "MR" p1   0.75  0.00 "90.00")
 (setq p1 (list 534.13 1716.62) p2 (list 0.00 0.00))
 (command "TEXT" "J" "MR" p1   0.75  0.00 "3242.88")
 (setq p1 (list 534.50 1707.74) p2 (list 535.00 1707.74))
 (command "LINE" p1 p2 "")
 (setq p1 (list 534.13 1707.74) p2 (list 0.00 0.00))
 (command "TEXT" "J" "MR" p1   0.75  0.00 "100.00")
 (setq p1 (list 534.13 1706.62) p2 (list 0.00 0.00))
 (command "TEXT" "J" "MR" p1   0.75  0.00 "3232.88")
 (setq p1 (list 534.50 1697.74) p2 (list 535.00 1697.74))
 (command "LINE" p1 p2 "")
 (setq p1 (list 534.13 1697.74) p2 (list 0.00 0.00))
 (command "TEXT" "J" "MR" p1   0.75  0.00 "110.00")
 (setq p1 (list 534.13 1696.62) p2 (list 0.00 0.00))
 (command "TEXT" "J" "MR" p1   0.75  0.00 "3222.88")
 (setq p1 (list 534.50 1687.74) p2 (list 535.00 1687.74))
 (command "LINE" p1 p2 "")
 (setq p1 (list 534.13 1687.74) p2 (list 0.00 0.00))
 (command "TEXT" "J" "MR" p1   0.75  0.00 "120.00")
 (setq p1 (list 534.13 1686.62) p2 (list 0.00 0.00))
 (command "TEXT" "J" "MR" p1   0.75  0.00 "3212.88")
 (setq p1 (list 534.50 1677.74) p2 (list 535.00 1677.74))
 (command "LINE" p1 p2 "")
 (setq p1 (list 534.13 1677.74) p2 (list 0.00 0.00))
 (command "TEXT" "J" "MR" p1   0.75  0.00 "130.00")
 (setq p1 (list 534.13 1676.62) p2 (list 0.00 0.00))
 (command "TEXT" "J" "MR" p1   0.75  0.00 "3202.88")
 (setq p1 (list 534.50 1667.74) p2 (list 535.00 1667.74))
 (command "LINE" p1 p2 "")
 (setq p1 (list 534.13 1667.74) p2 (list 0.00 0.00))
 (command "TEXT" "J" "MR" p1   0.75  0.00 "140.00")
 (setq p1 (list 534.13 1666.62) p2 (list 0.00 0.00))
 (command "TEXT" "J" "MR" p1   0.75  0.00 "3192.88")
 (setq p1 (list 534.50 1657.74) p2 (list 535.00 1657.74))
 (command "LINE" p1 p2 "")
 (setq p1 (list 534.13 1657.74) p2 (list 0.00 0.00))
 (command "TEXT" "J" "MR" p1   0.75  0.00 "150.00")
 (setq p1 (list 534.13 1656.62) p2 (list 0.00 0.00))
 (command "TEXT" "J" "MR" p1   0.75  0.00 "3182.88")
 (setq p1 (list 534.50 1647.74) p2 (list 535.00 1647.74))
 (command "LINE" p1 p2 "")
 (setq p1 (list 534.13 1647.74) p2 (list 0.00 0.00))
 (command "TEXT" "J" "MR" p1   0.75  0.00 "160.00")
 (setq p1 (list 534.13 1646.62) p2 (list 0.00 0.00))
 (command "TEXT" "J" "MR" p1   0.75  0.00 "3172.88")
 (setq p1 (list 534.50 1637.74) p2 (list 535.00 1637.74))
 (command "LINE" p1 p2 "")
 (setq p1 (list 534.13 1637.74) p2 (list 0.00 0.00))
 (command "TEXT" "J" "MR" p1   0.75  0.00 "170.00")
 (setq p1 (list 534.13 1636.62) p2 (list 0.00 0.00))
 (command "TEXT" "J" "MR" p1   0.75  0.00 "3162.88")
 (setq p1 (list 534.50 1627.74) p2 (list 535.00 1627.74))
 (command "LINE" p1 p2 "")
 (setq p1 (list 534.13 1627.74) p2 (list 0.00 0.00))
 (command "TEXT" "J" "MR" p1   0.75  0.00 "180.00")
 (setq p1 (list 534.13 1626.62) p2 (list 0.00 0.00))
 (command "TEXT" "J" "MR" p1   0.75  0.00 "3152.88")
 (setq p1 (list 534.50 1617.74) p2 (list 535.00 1617.74))
 (command "LINE" p1 p2 "")
 (setq p1 (list 534.13 1617.74) p2 (list 0.00 0.00))
 (command "TEXT" "J" "MR" p1   0.75  0.00 "190.00")
 (setq p1 (list 534.13 1616.62) p2 (list 0.00 0.00))
 (command "TEXT" "J" "MR" p1   0.75  0.00 "3142.88")
 (setq p1 (list 534.50 1607.74) p2 (list 535.00 1607.74))
 (command "LINE" p1 p2 "")
 (setq p1 (list 534.13 1607.74) p2 (list 0.00 0.00))
 (command "TEXT" "J" "MR" p1   0.75  0.00 "200.00")
 (setq p1 (list 534.13 1606.62) p2 (list 0.00 0.00))
 (command "TEXT" "J" "MR" p1   0.75  0.00 "3132.88")
 (setq p1 (list 534.50 1597.74) p2 (list 535.00 1597.74))
 (command "LINE" p1 p2 "")
 (setq p1 (list 534.13 1597.74) p2 (list 0.00 0.00))
 (command "TEXT" "J" "MR" p1   0.75  0.00 "210.00")
 (setq p1 (list 534.13 1596.62) p2 (list 0.00 0.00))
 (command "TEXT" "J" "MR" p1   0.75  0.00 "3122.88")
 (setq p1 (list 534.50 1587.74) p2 (list 535.00 1587.74))
 (command "LINE" p1 p2 "")
 (setq p1 (list 534.13 1587.74) p2 (list 0.00 0.00))
 (command "TEXT" "J" "MR" p1   0.75  0.00 "220.00")
 (setq p1 (list 534.13 1586.62) p2 (list 0.00 0.00))
 (command "TEXT" "J" "MR" p1   0.75  0.00 "3112.88")
 (setq p1 (list 534.50 1577.74) p2 (list 535.00 1577.74))
 (command "LINE" p1 p2 "")
 (setq p1 (list 534.13 1577.74) p2 (list 0.00 0.00))
 (command "TEXT" "J" "MR" p1   0.75  0.00 "230.00")
 (setq p1 (list 534.13 1576.62) p2 (list 0.00 0.00))
 (command "TEXT" "J" "MR" p1   0.75  0.00 "3102.88")
 (setq p1 (list 534.50 1567.74) p2 (list 535.00 1567.74))
 (command "LINE" p1 p2 "")
 (setq p1 (list 534.13 1567.74) p2 (list 0.00 0.00))
 (command "TEXT" "J" "MR" p1   0.75  0.00 "240.00")
 (setq p1 (list 534.13 1566.62) p2 (list 0.00 0.00))
 (command "TEXT" "J" "MR" p1   0.75  0.00 "3092.88")
 (setq p1 (list 534.50 1557.74) p2 (list 535.00 1557.74))
 (command "LINE" p1 p2 "")
 (setq p1 (list 534.13 1557.74) p2 (list 0.00 0.00))
 (command "TEXT" "J" "MR" p1   0.75  0.00 "250.00")
 (setq p1 (list 534.13 1556.62) p2 (list 0.00 0.00))
 (command "TEXT" "J" "MR" p1   0.75  0.00 "3082.88")
 (setq p1 (list 534.50 1547.74) p2 (list 535.00 1547.74))
 (command "LINE" p1 p2 "")
 (setq p1 (list 534.13 1547.74) p2 (list 0.00 0.00))
 (command "TEXT" "J" "MR" p1   0.75  0.00 "260.00")
 (setq p1 (list 534.13 1546.62) p2 (list 0.00 0.00))
 (command "TEXT" "J" "MR" p1   0.75  0.00 "3072.88")
 (setq p1 (list 534.50 1537.74) p2 (list 535.00 1537.74))
 (command "LINE" p1 p2 "")
 (setq p1 (list 534.13 1537.74) p2 (list 0.00 0.00))
 (command "TEXT" "J" "MR" p1   0.75  0.00 "270.00")
 (setq p1 (list 534.13 1536.62) p2 (list 0.00 0.00))
 (command "TEXT" "J" "MR" p1   0.75  0.00 "3062.88")
 (setq p1 (list 534.50 1527.74) p2 (list 535.00 1527.74))
 (command "LINE" p1 p2 "")
 (setq p1 (list 534.13 1527.74) p2 (list 0.00 0.00))
 (command "TEXT" "J" "MR" p1   0.75  0.00 "280.00")
 (setq p1 (list 534.13 1526.62) p2 (list 0.00 0.00))
 (command "TEXT" "J" "MR" p1   0.75  0.00 "3052.88")
 (setq p1 (list 534.50 1517.74) p2 (list 535.00 1517.74))
 (command "LINE" p1 p2 "")
 (setq p1 (list 534.13 1517.74) p2 (list 0.00 0.00))
 (command "TEXT" "J" "MR" p1   0.75  0.00 "290.00")
 (setq p1 (list 534.13 1516.62) p2 (list 0.00 0.00))
 (command "TEXT" "J" "MR" p1   0.75  0.00 "3042.88")
 (setq p1 (list 534.50 1507.74) p2 (list 535.00 1507.74))
 (command "LINE" p1 p2 "")
 (setq p1 (list 534.13 1507.74) p2 (list 0.00 0.00))
 (command "TEXT" "J" "MR" p1   0.75  0.00 "300.00")
 (setq p1 (list 534.13 1506.62) p2 (list 0.00 0.00))
 (command "TEXT" "J" "MR" p1   0.75  0.00 "3032.88")
 (setq p1 (list 534.50 1497.74) p2 (list 535.00 1497.74))
 (command "LINE" p1 p2 "")
 (setq p1 (list 534.13 1497.74) p2 (list 0.00 0.00))
 (command "TEXT" "J" "MR" p1   0.75  0.00 "310.00")
 (setq p1 (list 534.13 1496.62) p2 (list 0.00 0.00))
 (command "TEXT" "J" "MR" p1   0.75  0.00 "3022.88")
 (setq p1 (list 534.50 1483.28) p2 (list 535.00 1483.28))
 (command "LINE" p1 p2 "")
 (setq p1 (list 534.13 1483.28) p2 (list 0.00 0.00))
 (command "TEXT" "J" "MR" p1   0.75  0.00 "324.46")
 (setq p1 (list 534.13 1482.16) p2 (list 0.00 0.00))
 (command "TEXT" "J" "MR" p1   0.75  0.00 "3008.42")
 (command "LAYER" "S" "CGBHLHDR" "")
 (setq p1 (list 528.00 1819.24) p2 (list 528.00 1809.24) p3 (list 548.00 1809.24) p4 (list 548.00 1819.24))
 (command "LINE" p1 p2 p3 p4 "c")
 (setq p1 (list 528.50 1817.49) p2 (list 0.00 0.00))
 (command "TEXT" "J" "ML" p1   1.13  0.00 "Hole:")
 (setq p1 (list 528.50 1815.24) p2 (list 0.00 0.00))
 (command "TEXT" "J" "ML" p1   0.83  0.00 "Easting:")
 (setq p1 (list 528.50 1813.49) p2 (list 0.00 0.00))
 (command "TEXT" "J" "ML" p1   0.83  0.00 "Northing:")
 (setq p1 (list 528.50 1811.74) p2 (list 0.00 0.00))
 (command "TEXT" "J" "ML" p1   0.83  0.00 "Collar Elev:")
 (setq p1 (list 528.50 1809.99) p2 (list 0.00 0.00))
 (command "TEXT" "J" "ML" p1   0.83  0.00 "Drill Depth:")
 (setq p1 (list 547.50 1817.49) p2 (list 0.00 0.00))
 (command "TEXT" "J" "MR" p1   1.13  0.00 "XY-3")
 (setq p1 (list 547.50 1815.24) p2 (list 0.00 0.00))
 (command "TEXT" "J" "MR" p1   0.83  0.00 "4050000.00")
 (setq p1 (list 547.50 1813.49) p2 (list 0.00 0.00))
 (command "TEXT" "J" "MR" p1   0.83  0.00 "265000.00")
 (setq p1 (list 547.50 1811.74) p2 (list 0.00 0.00))
 (command "TEXT" "J" "MR" p1   0.83  0.00 "3332.88")
 (setq p1 (list 547.50 1809.99) p2 (list 0.00 0.00))
 (command "TEXT" "J" "MR" p1   0.83  0.00 "328.41")
 (setq p1 (list 538.00 1809.24) p2 (list 538.00 1807.74))
 (command "LINE" p1 p2 "")
 (command "LAYER" "S" "CGBSEAM" "")
 (command "COLOR" "WHITE")
 (setq p1 (list 113.00 1507.65) p2 (list 214.00 1507.95))
 (command "LINE" p1 p2 "")
 (command "COLOR" "WHITE")
 (setq p1 (list 113.00 1500.00) p2 (list 214.00 1500.00))
 (command "LINE" p1 p2 "")
 (command "COLOR" "WHITE")
 (setq p1 (list 220.00 1507.95) p2 (list 321.00 1507.56))
 (command "LINE" p1 p2 "")
 (command "COLOR" "WHITE")
 (setq p1 (list 220.00 1500.00) p2 (list 321.00 1500.00))
 (command "LINE" p1 p2 "")
 (command "COLOR" "WHITE")
 (setq p1 (list 327.00 1507.56) p2 (list 428.00 1506.54))
 (command "LINE" p1 p2 "")
 (command "COLOR" "WHITE")
 (setq p1 (list 327.00 1500.00) p2 (list 428.00 1500.00))
 (command "LINE" p1 p2 "")
 (command "COLOR" "WHITE")
 (setq p1 (list 434.00 1506.54) p2 (list 535.00 1504.80))
 (command "LINE" p1 p2 "")
 (command "COLOR" "WHITE")
 (setq p1 (list 434.00 1500.00) p2 (list 535.00 1500.00))
 (command "LINE" p1 p2 "")
 (command "COLOR" "WHITE")
 (setq p1 (list 113.00 1740.67) p2 (list 214.00 1729.72))
 (command "LINE" p1 p2 "")
 (command "COLOR" "WHITE")
 (setq p1 (list 113.00 1740.67) p2 (list 214.00 1729.72))
 (command "LINE" p1 p2 "")
 (command "COLOR" "WHITE")
 (setq p1 (list 434.00 1710.65) p2 (list 535.00 1722.18))
 (command "LINE" p1 p2 "")
 (command "COLOR" "WHITE")
 (setq p1 (list 434.00 1707.84) p2 (list 535.00 1719.75))
 (command "LINE" p1 p2 "")
 (command "COLOR" "WHITE")
 (setq p1 (list 113.00 1829.45) p2 (list 214.00 1829.00))
 (command "LINE" p1 p2 "")
 (command "COLOR" "WHITE")
 (setq p1 (list 113.00 1826.80) p2 (list 214.00 1826.92))
 (command "LINE" p1 p2 "")
T
)
