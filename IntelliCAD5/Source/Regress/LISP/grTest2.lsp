(defun c:grTest2()
(command "pline" "0,0" "w" "0" "1" "4,0" "4,8" "w" "1" "0" "8,8" "")
(command "donut" "0.5" "1.5" "4,4" "0,0" "8,8" "")
(command "zoom" "extents")
(command "vports" "" "")
(command "tilemode" "0")
(command "mview" "0,0" "10,10")
(command "mview" "0,10" "20,10")
(command "mspace")
(command "pspace")
(command "tilemode" "1")
)
