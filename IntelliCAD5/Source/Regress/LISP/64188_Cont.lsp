(defun c:64188_Cont()
(Command "line" 
	(list 2 7) (list  5 7) (list 5 6) (list  8 6) (list  8 7) (list 10 7) (list 10 5)
	(list 12 5) (list  12 6) (list 13 6) (list 13 3) (list 12 3) (list 12 4)
	 (list 10 4) (list 10 2) (list  8 2) (list 8 4) (list 6 4) (list  6 2)
	(list  3 2) (list 3 6) (list 1 6) (list 1 8) (list 2 8) (list 2 7)  ""
	"dimaligned" (list 1 8) (list 2 8) (list 2 9)
	"dimbaseline" (list 5 7) (list 8 7) (list 10 7) (list 12 6) (list 13 6) "" ""
	"dimaligned" (list 13 3) (list 12 3)  (list 12 1)
	"dimbaseline" (list  10 2) (list  8 2) (list 6 2) (list 3 2) (list 1 6) "" ""
)
)
