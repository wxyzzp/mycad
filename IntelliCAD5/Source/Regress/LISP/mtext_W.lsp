(defun c:test_W()
	(command "textsize" 2)
	(setq stX 0)
	(setq enX 175)
	(setq IncreX 75)	
	(setq IncreI 0.5)
	(setq IncreY 7.5)
;________1___________\W0
	(command "color" 1)
	(setq i -10)
	(setq yy 0)
	(while (< i 10)
		(command "-mtext" (list stX yy) (list enX (+ yy i)) (strcat "\\W0;Intelli\\W" (rtos i) ";CAD" (rtos i)) "")
		(command "zoom" "C" (cdr (assoc '10. (entget (entlast)))) "4")
		(setq i (+ i IncreI))
		(setq yy (+ yy IncreY))
	)
;________2___________\W
	(command "color" 2)
	(setq i -10)
	(setq yy 0)
	(setq stX (+ stX IncreX))
	(setq enX (+ enX IncreX))
	(while (< i 10)
		(command "-mtext" (list stX yy) (list enX (+ yy i)) (strcat "\\W;Intelli\\W" (rtos i) ";CAD" (rtos i)) "")
		(command "zoom" "C" (cdr (assoc '10. (entget (entlast)))) "4")
		(setq i (+ i IncreI))
		(setq yy (+ yy IncreY))
	)
;________3___________\W0X_\W0x
	(command "color" 3)
	(setq i -10)
	(setq yy 0)
	(setq stX (+ stX IncreX))
	(setq enX (+ enX IncreX))
	(while (< i 10)
		(command "-mtext" (list stX yy) (list enX (+ yy i)) (strcat "\\W0X;Intelli\\W" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\W0x;Intelli\\W" (rtos i) "x;CAD" (rtos i)) "")
		(command "zoom" "C" (cdr (assoc '10. (entget (entlast)))) "4")
		(setq i (+ i IncreI))
		(setq yy (+ yy IncreY))

	)
;________4___________\WX_\Wx
	(command "color" 4)
	(setq i -10)
	(setq stX (+ stX IncreX))
	(setq enX (+ enX IncreX))
	(setq yy 0)
	(while (< i 10)
		(command "-mtext" (list stX yy) (list enX (+ yy i)) (strcat "\\WX;Intelli\\W" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\Wx;Intelli\\W" (rtos i) "x;CAD" (rtos i)) "")
		(command "zoom" "C" (cdr (assoc '10. (entget (entlast)))) "4")
		(setq i (+ i IncreI))
		(setq yy (+ yy IncreY))

	)
;________1___________\w0
	(command "color" 5)
	(setq i -10)
	(setq stX (+ stX IncreX))
	(setq enX (+ enX IncreX))
	(setq IncreX 50)
	(setq yy 0)
	(while (< i 10)
		(command "-mtext" (list stX yy) (list enX (+ yy i)) (strcat "\\w0;Intelli\\w" (rtos i) ";CAD" (rtos i)) "")
		(command "zoom" "C" (cdr (assoc '10. (entget (entlast)))) "4")
		(setq i (+ i IncreI))
		(setq yy (+ yy IncreY))
	)
;________2___________\w
	(command "color" 6)
	(setq i -10)
	(setq yy 0)
	(setq stX (+ stX IncreX))
	(setq enX (+ enX IncreX))
	(while (< i 10)
		(command "-mtext" (list stX yy) (list enX (+ yy i)) (strcat "\\w;Intelli\\w" (rtos i) ";CAD" (rtos i)) "")
		(command "zoom" "C" (cdr (assoc '10. (entget (entlast)))) "4")
		(setq i (+ i IncreI))
		(setq yy (+ yy IncreY))
	)
;________3___________\w0X_\w0x
	(command "color" 7)
	(setq i -10)
	(setq yy 0)
	(setq stX (+ stX IncreX))
	(setq enX (+ enX IncreX))
	(while (< i 10)
		(command "-mtext" (list stX yy) (list enX (+ yy i)) (strcat "\\w0X;Intelli\\w" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\w0x;Intelli\\w" (rtos i) "x;CAD" (rtos i)) "")
		(command "zoom" "C" (cdr (assoc '10. (entget (entlast)))) "4")
		(setq i (+ i IncreI))
		(setq yy (+ yy IncreY))

	)
;________4___________\wX_\wx
	(command "color" 8)
	(setq i -10)
	(setq stX (+ stX IncreX))
	(setq enX (+ enX IncreX))
	(setq yy 0)
	(while (< i 10)
		(command "-mtext" (list stX yy) (list enX (+ yy i)) (strcat "\\wX;Intelli\\w" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\wx;Intelli\\w" (rtos i) "x;CAD" (rtos i)) "")
		(command "zoom" "C" (cdr (assoc '10. (entget (entlast)))) "4")
		(setq i (+ i IncreI))
		(setq yy (+ yy IncreY))

	)

	(command "zoom" "extents")
)
