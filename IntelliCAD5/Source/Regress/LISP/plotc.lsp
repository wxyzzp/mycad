(defun c:plotc()
(setq ssall (ssget "x"))
(setq sshat (ssget "x" '((0 . "HATCH"))))
(setq n 0)
(repeat (sslength sshat)
(setq ent (ssname sshat n))
(setq ssall (ssdel ent ssall))
(setq n (1+ n))
)
(command "Copy" ssall "" "0,0" "0,0" "Erase" ssall "")
(command "regen")
)
