(defun c:laylist()
(setq lay (tblnext "Layer" T) n 0)
(setq layname (cdr (assoc 2 lay)))
(setq ltname (cdr (assoc 6 lay)))
(setq colname (cdr (assoc 62 lay)))
(princ "\nLAYERS\t\tLINETYPE\t\tCOLOR\t\tNO OF ENTITIES")
(while (/= lay nil)
(princ "\n||")(princ layname)(princ "||\t\t||")(princ ltname)(princ "||\t\t||")(princ colname)(princ "||\t\t||")
(setq ssa (ssget "X" (list (cons 8 layname))))
(if (not ssa)
(setq ssl 0)
(progn
(setq ssl (sslength ssa))
)
)
(princ ssl)(princ "||")
(princ)
(setq lay (tblnext "Layer"))
(setq layname (cdr (assoc 2 lay)))
(setq ltname (cdr (assoc 6 lay)))
(setq colname (cdr (assoc 62 lay)))
)
(princ)
)
