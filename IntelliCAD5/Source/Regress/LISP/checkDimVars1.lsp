(defun checkFromToVar(varname from to)
	(setq tmp (getvar varname))
	(setq i from)
	(while (<= i to)
		(setvar varname i)
		(if (/= (getvar varname) i) (alert varname))
		(command "dimaligned" "0,4" "4,0" "4,4" 
			 "dimlinear" "0,4" "4,0" "2,-1" 
			 "dimlinear" "0,4" "4,0" "-1,2" 
			 "dimlinear" "0,4" "4,0" "R" "110" "4,4"
			 "circle" "4,0" "7,1" "dimradius" "7,1" "6,-1" 
			 "dimdiameter" "1,1" "2,-1" 
			 "dimangular" "" "0,0" "4,0" "0,4" "4,4"
			"erase" "all" "")
		(setq i (1+ i))
	)
	(setvar varname tmp)
	(princ varname)
)

(defun checkBoolVar(varname)
	(checkfromtovar varname 0 1)
)
;;;;;;;;;;;;;;;;;;;;;;;;;;;;;;;;;;;;;;;;;;;;;;;;;;;;;;;;
(checkfromtovar "dimadec" -1 8)
(checkboolvar "dimalt")
(checkfromtovar "dimaltd" 0 8)
(checkfromtovar "dimalttd" 0 8)
(checkfromtovar "dimalttz" 0 15)
(checkfromtovar "dimaltu" 1 8)
(checkfromtovar "dimaltz" 0 15)
(checkboolvar "dimaso")
(checkfromtovar "dimatfit" 0 3)
(checkfromtovar "dimaunit" 0 4)
(checkfromtovar "dimazin" 0 3)
(checkfromtovar "dimdec" 0 8)
(checkfromtovar "dimfit" 0 5)
(checkfromtovar "dimfrac" 0 2)
(checkfromtovar "dimjust" 0 4)
(checkboolvar "dimlim")
(checkfromtovar "dimlunit" 1 6)
(checkboolvar "dimsah")
(checkboolvar "dimsd1")
(checkboolvar "dimsd2")
(checkboolvar "dimse1")
(checkboolvar "dimse2")
(checkboolvar "dimsho")
(checkboolvar "dimsoxd")
(checkfromtovar "dimtad" 0 3)
(checkfromtovar "dimtdec" 0 8)
(checkboolvar "dimtih")
(checkboolvar "dimtix")
(checkfromtovar "dimtmove" 0 2)
(checkboolvar "dimtofl")
(checkboolvar "dimtoh")
(checkboolvar "dimtol")
(checkfromtovar "dimtolj" 0 2)
(checkfromtovar "dimtzin" 0 15)
(checkfromtovar "dimunit" 1 8)
(checkboolvar "dimupt")
(checkfromtovar "dimzin" 0 15)
