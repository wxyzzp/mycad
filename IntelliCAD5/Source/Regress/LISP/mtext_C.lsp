(defun c:test_C()
	(setq i -255)
	(setq yy 0)
	(while (<= i 255)
		(command "-mtext" (list 0 yy) (list 160 (+ yy i)) (strcat "\\C" (rtos i 2 0) ";IntelliCAD" (rtos i 2 0)) "")
		(command "zoom" "C" (cdr (assoc '10. (entget (entlast)))) "4")
		(setq i (+ i 1))
		(setq yy (+ yy 0.3))
	)
)
