(defun c:76526()
(command "-mtext" "0,0" "6,2" "\\H1;OOO\\H.5;OOO" ""
	"-mtext" "0,2" "6,4" "\\H1;OOO\\H.5OOO" ""
	"-mtext" "0,4" "6,6" "\\H1OOO\\H.5;OOO" ""
	"-mtext" "0,6" "6,8" "\\H1OOO\\H.5OOO" ""
	
	"-mtext" "6,0" "12,2" "\\H;OOO\\H.5;OOO" ""
	"-mtext" "6,2" "12,4" "\\H1;OOO\\HOOO" ""
	"-mtext" "6,4" "12,6" "\\H0OOO\\H.5;OOO" ""
	"-mtext" "6,6" "12,8" "\\H1OOO\\H0OOO" ""
	"zoom" "Extents"
)
)
