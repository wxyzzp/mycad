(defun c:test_H()
	(command "textsize" 2)
	(setq stX 0)
	(setq enX 175)
	(setq IncreX 75)	
	(setq IncreI 0.5)
	(setq IncreY 7.5)
;________1___________\H0
	(command "color" 1)
	(setq i -10)
	(setq yy 0)
	(while (< i 10)
		(command "-mtext" (list stX yy) (list enX (+ yy i)) (strcat "\\H0;Intelli\\H" (rtos i) ";CAD" (rtos i)) "")
		(command "zoom" "C" (cdr (assoc '10. (entget (entlast)))) "4")
		(setq i (+ i IncreI))
		(setq yy (+ yy IncreY))
	)
;________2___________\H
	(command "color" 2)
	(setq i -10)
	(setq yy 0)
	(setq stX (+ stX IncreX))
	(setq enX (+ enX IncreX))
	(while (< i 10)
		(command "-mtext" (list stX yy) (list enX (+ yy i)) (strcat "\\H;Intelli\\H" (rtos i) ";CAD" (rtos i)) "")
		(command "zoom" "C" (cdr (assoc '10. (entget (entlast)))) "4")
		(setq i (+ i IncreI))
		(setq yy (+ yy IncreY))
	)
;________3___________\H0X_\H0x
	(command "color" 3)
	(setq i -10)
	(setq yy 0)
	(setq stX (+ stX IncreX))
	(setq enX (+ enX IncreX))
	(while (< i 10)
		(command "-mtext" (list stX yy) (list enX (+ yy i)) (strcat "\\H0X;Intelli\\H" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\H0x;Intelli\\H" (rtos i) "x;CAD" (rtos i)) "")
		(command "zoom" "C" (cdr (assoc '10. (entget (entlast)))) "4")
		(setq i (+ i IncreI))
		(setq yy (+ yy IncreY))

	)
;________4___________\HX_\Hx
	(command "color" 4)
	(setq i -10)
	(setq stX (+ stX IncreX))
	(setq enX (+ enX IncreX))
	(setq yy 0)
	(while (< i 10)
		(command "-mtext" (list stX yy) (list enX (+ yy i)) (strcat "\\HX;Intelli\\H" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\Hx;Intelli\\H" (rtos i) "x;CAD" (rtos i)) "")
		(command "zoom" "C" (cdr (assoc '10. (entget (entlast)))) "4")
		(setq i (+ i IncreI))
		(setq yy (+ yy IncreY))

	)
;________1___________\h0
	(command "color" 5)
	(setq i -10)
	(setq stX (+ stX IncreX))
	(setq enX (+ enX IncreX))
	(setq IncreX 50)
	(setq yy 0)
	(while (< i 10)
		(command "-mtext" (list stX yy) (list enX (+ yy i)) (strcat "\\h0;Intelli\\h" (rtos i) ";CAD" (rtos i)) "")
		(command "zoom" "C" (cdr (assoc '10. (entget (entlast)))) "4")
		(setq i (+ i IncreI))
		(setq yy (+ yy IncreY))
	)
;________2___________\h
	(command "color" 6)
	(setq i -10)
	(setq yy 0)
	(setq stX (+ stX IncreX))
	(setq enX (+ enX IncreX))
	(while (< i 10)
		(command "-mtext" (list stX yy) (list enX (+ yy i)) (strcat "\\h;Intelli\\h" (rtos i) ";CAD" (rtos i)) "")
		(command "zoom" "C" (cdr (assoc '10. (entget (entlast)))) "4")
		(setq i (+ i IncreI))
		(setq yy (+ yy IncreY))
	)
;________3___________\h0X_\h0x
	(command "color" 7)
	(setq i -10)
	(setq yy 0)
	(setq stX (+ stX IncreX))
	(setq enX (+ enX IncreX))
	(while (< i 10)
		(command "-mtext" (list stX yy) (list enX (+ yy i)) (strcat "\\h0X;Intelli\\h" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\h0x;Intelli\\h" (rtos i) "x;CAD" (rtos i)) "")
		(command "zoom" "C" (cdr (assoc '10. (entget (entlast)))) "4")
		(setq i (+ i IncreI))
		(setq yy (+ yy IncreY))

	)
;________4___________\hX_\hx
	(command "color" 8)
	(setq i -10)
	(setq stX (+ stX IncreX))
	(setq enX (+ enX IncreX))
	(setq yy 0)
	(while (< i 10)
		(command "-mtext" (list stX yy) (list enX (+ yy i)) (strcat "\\hX;Intelli\\h" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\hx;Intelli\\h" (rtos i) "x;CAD" (rtos i)) "")
		(command "zoom" "C" (cdr (assoc '10. (entget (entlast)))) "4")
		(setq i (+ i IncreI))
		(setq yy (+ yy IncreY))

	)

	(command "zoom" "extents")
)
