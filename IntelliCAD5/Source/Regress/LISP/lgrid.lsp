(defun lpan2()
(setq fpt (list 0 0 0) ypt 0 xpt 0 n 1)
(setq m 11)
(repeat 111
(setq ypt (+ ypt 10))
(setq spt (list xpt ypt 0))
(if (= n m)
(progn
(if (/= n 11)
(command "line" fpt spt "")
(command "pan" spt fpt)
)
(setq xpt (+ xpt 10) ypt 0)
(setq fpt (list xpt ypt 0))
(setq m (+ m 10))
) 
(progn
(command "line" fpt spt "")
(command "pan" spt fpt)
(setq fpt spt)
)
)
(setq n (1+ n))
)
(princ)
)
(defun c:lgrid()
(setq startTime (getvar "DATE"))
(princ (strcat "\n Started at " (rtos startTime)))
(setq s (getvar "DATE"))
(setq startSeconds (* 86400.0 (- s (fix s))))
(princ startSeconds)
(setq fpt (list 0 0 0) ypt 0 xpt 0 n 1)
(setq m 11)
(repeat 111
(setq xpt (+ xpt 10))
(setq spt (list xpt ypt 0))
(if (= n m)
(progn
(if (/= n 11)
(command "line" fpt spt "")
(command "pan" spt fpt)
)
(setq ypt (+ ypt 10) xpt 0)
(setq fpt (list xpt ypt 0))
(setq m (+ m 10))
) 
(progn
(command "line" fpt spt "")
(command "pan" spt fpt)
(setq fpt spt)
)
)
(setq n (1+ n))
)
(lpan2)
(command "zoom" "e")
(setq s (getvar "DATE"))
(setq endSeconds (* 86400.0 (- s (fix s))))
(princ "\n TOTAL TIME TO RUN THE LISP FILE IS ")
(princ (- endSeconds startSeconds))
(princ "\n")
(princ)
)
