;;;
;;; Lisp Acceptance Test
;;;	Symbol functions
;;;		type
;;;
;;; 17 Jun 98	MichaelHu
;;;
;;; quote is mostly tested in the list tests.
;;;
	(logmsg "")
	(load (strcat testscrdir "error"))

	(defun gettype ( val / x )
		(cond
			((= 'INT			(type val))	"INT")
			((= 'REAL			(type val))	"REAL")
			((= 'LIST			(type val))	"LIST")
			((= 'STR			(type val))	"STR")
			((= 'SUBR			(type val))	"SUBR")
			((= 'ENAME			(type val))	"ENAME")
			((= 'FILE			(type val))	"FILE")
			((= 'SYM			(type val))	"SYM")
			((= 'EXSUBR			(type val))	"EXSUBR")
			((= 'PICKSET		(type val))	"PICKSET")
			((= 'PAGETB			(type val))	"PAGETB")
			(t								"OTHER")
		)
	)

;;; ---------------------------------------------
;;; IntelliCAD help tests.
	(defun icadhlp1 ( / prverr )
		(setq prverr *error*)
		(setq *error* silent_err)
		(setq rc (gettype 2))
		(logall errloc rc)
		(setq *error* prverr)
	)
	(defun icadhlp2 ( / prverr )
		(setq prverr *error*)
		(setq *error* silent_err)
		(setq rc (gettype 2.0))
		(logall errloc rc)
		(setq *error* prverr)
	)
	(defun icadhlp3 ( / prverr )
		(setq prverr *error*)
		(setq *error* silent_err)
		(setq rc (gettype '(5 6 7)))
		(logall errloc rc)
		(setq *error* prverr)
	)
	(defun icadhlp4 ( / prverr )
		(setq prverr *error*)
		(setq *error* silent_err)
		(setq rc (gettype "Street"))
		(logall errloc rc)
		(setq *error* prverr)
	)
	(defun icadhlp5 ( / prverr )
		(setq prverr *error*)
		(setq *error* silent_err)
		(setq rc (gettype setq))
		(logall errloc rc)
		(setq *error* prverr)
	)
	(defun icadhlp6 ( / prverr )
		(setq prverr *error*)
		(setq *error* silent_err)
		(setq x (open "c:\\temp.txt" "w"))
		(setq rc (gettype x))
		(logall errloc rc)
		(setq rc (gettype 'x))
		(logall errloc rc)
		(close x)
		(setq *error* prverr)
	)
	(defun icadhlp7 ( / prverr )
		(setq prverr *error*)
		(setq *error* silent_err)
		(command "._line" "0,0" "1,1" "")
		(setq rc (gettype (entlast)))
		(logall errloc rc)
		(setq *error* prverr)
	)
	(defun icadhlp8 ( / prverr )
		(setq prverr *error*)
		(setq *error* silent_err)
		(setq rc (gettype (ssadd)))
		(logall errloc rc)
		(setq *error* prverr)
	)

;;; ---------------------------------------------
;;; AutoCAD help tests.
	(defun acadhlp1 ( / prverr )
		(setq prverr *error*)
		(setq *error* silent_err)
		(setq rc (gettype 'rc))
		(logall errloc rc)
		(setq *error* prverr)
	)
	(defun acadhlp2 ( / prverr )
		(setq prverr *error*)
		(setq *error* silent_err)
		(setq rc (gettype 123))
		(logall errloc rc)
		(setq *error* prverr)
	)
	(defun acadhlp3 ( / prverr )
		(setq prverr *error*)
		(setq *error* silent_err)
		(setq x (open "c:\\temp.txt" "w"))
		(setq rc (gettype x))
		(close x)
		(logall errloc rc)
		(setq *error* prverr)
	)
	(defun acadhlp4 ( / prverr )
		(setq prverr *error*)
		(setq *error* silent_err)
		(setq rc (gettype 3.45))
		(logall errloc rc)
		(setq *error* prverr)
	)
	(defun acadhlp5 ( / prverr )
		(setq prverr *error*)
		(setq *error* silent_err)
		(setq rc (gettype "Hello!"))
		(logall errloc rc)
		(setq *error* prverr)
	)
	(defun acadhlp6 ( / prverr )
		(setq prverr *error*)
		(setq *error* silent_err)
		(setq rc (gettype '("a" "b" "c")))
		(logall errloc rc)
		(setq *error* prverr)
	)
	(defun acadhlp7 ( / prverr )
		(setq prverr *error*)
		(setq *error* silent_err)
		(setq rc (gettype +))
		(logall errloc rc)
		(setq *error* prverr)
	)
	(defun acadhlp8 ( / prverr )
		(setq prverr *error*)
		(setq *error* silent_err)
		(setq rc (gettype nil))
		(logall errloc rc)
		(setq *error* prverr)
	)
