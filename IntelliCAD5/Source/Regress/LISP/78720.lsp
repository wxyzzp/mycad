(entmake '((0 . "BLOCK") (2 . "*u1") (70 . 1) (10 0.0 0.0 0.0)))
(entmake '((0 . "LINE") (10 2 3.0625 0) (11 2 5.180 0)))
(entmake '((0 . "LINE") (10 10 3.0625 0) (11 10 5.180 0)))
(entmake '((0 . "LINE") (10 2 5.0 0) (11 5.52 5.0 0)))
(entmake '((0 . "LINE") (10 6.48 5.0 0) (11 10 5 0)))
(entmake '((0 . "TEXT") (10 5.61 4.91 0)(40 . 0.18)(1 . "8.00") (50 . 0.0) (41 . 1) (51 . 0.0) (71 . 0) (72 . 1) (11 6.0 5.0 0)))
(setq retVal (entmake '((0 . "ENDBLK"))))
(princ retVal)
(setq retVal (strcase retVal))
(if (/= retVal "*U1") (alert "err"))
(entmake '((0 . "BLOCK") (2 . "*u1") (70 . 1) (10 0.0 0.0 0.0)))
(entmake '((0 . "LINE") (10 2 3.0625 0) (11 2 5.180 0)))
(entmake '((0 . "LINE") (10 10 3.0625 0) (11 10 5.180 0)))
(entmake '((0 . "LINE") (10 2 5.0 0) (11 5.52 5.0 0)))
(entmake '((0 . "LINE") (10 6.48 5.0 0) (11 10 5 0)))
(entmake '((0 . "TEXT") (10 5.61 4.91 0)(40 . 0.18)(1 . "8.00") (50 . 0.0) (41 . 1) (51 . 0.0) (71 . 0) (72 . 1) (11 6.0 5.0 0)))
(setq retVal (entmake '((0 . "ENDBLK"))))
(setq retVal (strcase retVal))
(princ retVal)
(if (/= retVal "*U1") (alert "err"))
(tblnext "BLOCK" T)
(tblnext "BLOCK")
