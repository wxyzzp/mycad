;_Created_by_Srinivas_on_5/13/2003
(defun checkMeasure (stpt ang len measdist)
  (command "line" stpt (polar stpt (dtor ang) len) "")
  (command "measure" stpt measdist)

(if 
	(> (rem len measdist) 0) (setq di (- len (rem len measdist))) (setq di (- len measdist)))

(princ di)
;  (setq di (/ len measdist))
;  (setq di (- di (rem len measdist)))
  (while (> di 0)
    (setq en nil)
    (setq en (cdr (assoc 10 (entget (entlast)))))
    (setq exppt (polar stpt (dtor ang) di))
    (princ en)
    (princ exppt)
    (if	(comparePoint en exppt)
      (princ "OK")
      (alert "Err")
    )
    (setq di (- di measdist))
(princ di)
    (command "erase" "l" "")
  )


)
(defun dtor (d) (* 0.0174533 d))
(defun comparePoint (ptAct ptExp)
  (and
    (equal (car ptAct) (car ptExp) 0.00001)
    (equal (cadr ptAct) (cadr ptExp) 0.00001)
    (equal (caddr ptAct) (caddr ptExp) 0.00001)
  )
)
(checkmeasure '(1 1 0) 0 6.5 0.75)
(command "erase" "all" "")
(checkmeasure '(2 4 0) 45 5.5 0.5)
(command "erase" "all" "")
(checkmeasure '(1 1 0) 180 6.0 1.90)
(command "erase" "all" "")
(checkmeasure '(1 1 0) 0 8 3.5)
(command "erase" "all" "")
