(defun c:test_t()
	(command "textsize" 2)
	(setq stX 0)
	(setq enX 175)
	(setq IncreX 75)	
	(setq IncreI 0.5)
	(setq IncreY 7.5)
;________1___________\T0
	(command "color" 1)
	(setq i -10)
	(setq yy 0)
	(while (< i 10)
		(command "-mtext" (list stX yy) (list enX (+ yy i)) (strcat "\\T0;Intelli\\T" (rtos i) ";CAD" (rtos i)) "")
		(command "zoom" "C" (cdr (assoc '10. (entget (entlast)))) "4")
		(setq i (+ i IncreI))
		(setq yy (+ yy IncreY))
	)
;________2___________\T
	(command "color" 2)
	(setq i -10)
	(setq yy 0)
	(setq stX (+ stX IncreX))
	(setq enX (+ enX IncreX))
	(while (< i 10)
		(command "-mtext" (list stX yy) (list enX (+ yy i)) (strcat "\\T;Intelli\\T" (rtos i) ";CAD" (rtos i)) "")
		(command "zoom" "C" (cdr (assoc '10. (entget (entlast)))) "4")
		(setq i (+ i IncreI))
		(setq yy (+ yy IncreY))
	)
;________3___________\T0X_\T0x
	(command "color" 3)
	(setq i -10)
	(setq yy 0)
	(setq stX (+ stX IncreX))
	(setq enX (+ enX IncreX))
	(while (< i 10)
		(command "-mtext" (list stX yy) (list enX (+ yy i)) (strcat "\\T0X;Intelli\\T" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\T0x;Intelli\\T" (rtos i) "x;CAD" (rtos i)) "")
		(command "zoom" "C" (cdr (assoc '10. (entget (entlast)))) "4")
		(setq i (+ i IncreI))
		(setq yy (+ yy IncreY))

	)
;________4___________\TX_\Tx
	(command "color" 4)
	(setq i -10)
	(setq stX (+ stX IncreX))
	(setq enX (+ enX IncreX))
	(setq yy 0)
	(while (< i 10)
		(command "-mtext" (list stX yy) (list enX (+ yy i)) (strcat "\\TX;Intelli\\T" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\Tx;Intelli\\T" (rtos i) "x;CAD" (rtos i)) "")
		(command "zoom" "C" (cdr (assoc '10. (entget (entlast)))) "4")
		(setq i (+ i IncreI))
		(setq yy (+ yy IncreY))

	)
;________1___________\t0
	(command "color" 5)
	(setq i -10)
	(setq stX (+ stX IncreX))
	(setq enX (+ enX IncreX))
	(setq IncreX 50)
	(setq yy 0)
	(while (< i 10)
		(command "-mtext" (list stX yy) (list enX (+ yy i)) (strcat "\\t0;Intelli\\t" (rtos i) ";CAD" (rtos i)) "")
		(command "zoom" "C" (cdr (assoc '10. (entget (entlast)))) "4")
		(setq i (+ i IncreI))
		(setq yy (+ yy IncreY))
	)
;________2___________\t
	(command "color" 6)
	(setq i -10)
	(setq yy 0)
	(setq stX (+ stX IncreX))
	(setq enX (+ enX IncreX))
	(while (< i 10)
		(command "-mtext" (list stX yy) (list enX (+ yy i)) (strcat "\\t;Intelli\\t" (rtos i) ";CAD" (rtos i)) "")
		(command "zoom" "C" (cdr (assoc '10. (entget (entlast)))) "4")
		(setq i (+ i IncreI))
		(setq yy (+ yy IncreY))
	)
;________3___________\t0X_\t0x
	(command "color" 7)
	(setq i -10)
	(setq yy 0)
	(setq stX (+ stX IncreX))
	(setq enX (+ enX IncreX))
	(while (< i 10)
		(command "-mtext" (list stX yy) (list enX (+ yy i)) (strcat "\\t0X;Intelli\\t" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\t0x;Intelli\\t" (rtos i) "x;CAD" (rtos i)) "")
		(command "zoom" "C" (cdr (assoc '10. (entget (entlast)))) "4")
		(setq i (+ i IncreI))
		(setq yy (+ yy IncreY))

	)
;________4___________\tX_\tx
	(command "color" 8)
	(setq i -10)
	(setq stX (+ stX IncreX))
	(setq enX (+ enX IncreX))
	(setq yy 0)
	(while (< i 10)
		(command "-mtext" (list stX yy) (list enX (+ yy i)) (strcat "\\tX;Intelli\\t" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\tx;Intelli\\t" (rtos i) "x;CAD" (rtos i)) "")
		(command "zoom" "C" (cdr (assoc '10. (entget (entlast)))) "4")
		(setq i (+ i IncreI))
		(setq yy (+ yy IncreY))

	)

	(command "zoom" "extents")
)
