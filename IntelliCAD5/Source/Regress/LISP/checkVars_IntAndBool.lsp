(defun checkFromToVar(varname from to)
(if (< (- to from) 10000) (setq incre 1) (setq incre 100))
	(setq tmp (getvar varname))
	(setq i from)
	(while (<= i to)
		(setvar varname i)
		(if (/= (getvar varname) i) (alert varname))
		(setq i (+ i incre))
	)
	(setvar varname tmp)
	(princ varname)
)
;(defun checkIntVar(varname)
;(checkfromtovar varname 0 15)
;(setq i 0)
;(while (<= i 15)
;(setvar varname i)
;(if (/= (getvar varname) i) (alert varname))
;(setq i (1+ i))
;)
;(princ varname)
;)
(defun checkBoolVar(varname)
(checkfromtovar varname 0 1)
;(setq i 0)
;(while (<= i 1)
;(setvar varname i)
;(if (/= (getvar varname) i) (alert varname))
;(setq i (1+ i))
;)
;(princ varname)
)
;;;;;;;;;;;;;;;;;;;;;;;;;;;;;;;;;;;;;;;;;;;;;;;;;;;;;;;;
(checkfromtovar "aflags" 0 15)
(checkBoolvar "angdir")
(checkBoolvar "apbox")
(checkfromtovar "aperture" 1 50)
(checkBoolvar "attdia")
(checkfromtovar "attmode" 0 2)
(checkBoolvar "attreq")
(checkBoolvar "automenuload")
(checkBoolvar "axismode")
(checkBoolvar "auditctl")
(checkfromtovar "aunits" 0 4)
(checkfromtovar "auprec" 0 8)
(checkfromtovar "autosnap" 0 63)
(checkfromtovar "bkgcolor" 0 256)
(checkBoolvar "blipmode")
(checkBoolvar "chammode")
(checkBoolvar "cmddia")
(checkBoolvar "cmdecho")
(checkfromtovar "cmljust" 0 2)
(checkfromtovar "colorx" 0 255)
(checkfromtovar "colory" 0 255)
(checkfromtovar "colorz" 0 255)
(checkfromtovar "coords" 0 2)
(checkBoolvar "ctrlmouse")
(checkfromtovar "cursorsize" 1 100)
(checkBoolvar "delobj")
(checkfromtovar "dimadec" -1 8)
(checkboolvar "dimalt")
(checkfromtovar "dimaltd" 0 8)
(checkfromtovar "dimalttd" 0 8)
(checkfromtovar "dimalttz" 0 15)
(checkfromtovar "dimaltu" 1 8)
(checkfromtovar "dimaltz" 0 15)
(checkboolvar "dimaso")
(checkfromtovar "dimatfit" 0 3)
(checkfromtovar "dimaunit" 0 3)
(checkfromtovar "dimazin" 0 3)
(checkfromtovar "dimclrd" 0 256)
(checkfromtovar "dimclre" 0 256)
(checkfromtovar "dimclrt" 0 256)
(checkfromtovar "dimdec" 0 8)
(checkfromtovar "dimfit" 0 5)
(checkfromtovar "dimfrac" 0 2)
(checkfromtovar "dimjust" 0 4)
(checkboolvar "dimlim")
(checkfromtovar "dimlunit" 1 6)
(checkboolvar "dimsah")
(checkboolvar "dimsd1")
(checkboolvar "dimsd2")
(checkboolvar "dimse1")
(checkboolvar "dimse2")
(checkboolvar "dimsho")
(checkboolvar "dimsoxd")
(checkfromtovar "dimtad" 0 3)
(checkfromtovar "dimtdec" 0 8)
(checkboolvar "dimtih")
(checkboolvar "dimtix")
(checkfromtovar "dimtmove" 0 2)
(checkboolvar "dimtofl")
(checkboolvar "dimtoh")
(checkboolvar "dimtol")
(checkfromtovar "dimtolj" 0 2)
(checkfromtovar "dimtzin" 0 15)
(checkfromtovar "dimunit" 1 8)
(checkboolvar "dimupt")
(checkfromtovar "dimzin" 0 15)
(checkboolvar "dispsilh")
(checkfromtovar "dragmode" 0 2)
(checkboolvar  "dragmode")
(checkboolvar  "edgemode")
(checkfromtovar "expert" 0 5)
(checkfromtovar "explevel" 1 3)
(checkboolvar  "explmode")
(checkboolvar  "filedia")
(checkboolvar  "fillmode")
(checkboolvar  "flatland")
(checkboolvar  "gridmode")
(checkboolvar  "gripblock")
(checkfromtovar "gripcolor" 1 255)
(checkfromtovar "griphot" 1 255)
(checkboolvar  "grips")
(checkfromtovar "gripsize" 1 255)
(checkboolvar  "highlight")
(checkboolvar  "hpbound")
(checkboolvar  "hpdouble")
(checkfromtovar "hpstyle" 0 2)
(checkfromtovar "isavepercent" 0 100)
(checkfromtovar "isolines" 0 2047)
(checkboolvar  "limcheck")
(checkboolvar  "logfilemode")
(checkboolvar  "longfname")
(checkboolvar  "ltsclwblk")
(checkfromtovar "lunits" 1 5)
(checkfromtovar "luprec" 0 8)
(checkboolvar  "lwdisplay")
(checkboolvar  "lwpolyout")
(checkboolvar  "lwunits")
(checkboolvar  "macrorec")
(checkboolvar  "macrotrace")
(checkboolvar  "makebak")
(checkfromtovar "maxactvp" 2 64)
(checkfromtovar "maxsort" 0 32767)
(checkboolvar  "mbuttonpan")
(checkboolvar  "measurement")
(checkboolvar  "menuctl")
(checkfromtovar "menuecho" 0 15)
(checkboolvar  "mirrtext")
(checkfromtovar "nfilelist" 0 10)
(checkboolvar  "orthomode")
(checkfromtovar "osmode" 0 32767)
;(checkfromtovar "pdmode" -32768 32767)
(checkboolvar  "pellipse")
(checkboolvar  "pickadd")
(checkboolvar  "pickauto")
(checkfromtovar "pickbox" 0 50)
(checkboolvar  "pickdrag")
(checkboolvar  "pickfirst")
(checkfromtovar "pickstyle" 0 3)
(checkboolvar  "plinegen")
(checkfromtovar "plinetype" 0 2)
(checkfromtovar "plotrotmode" 0 2)
(checkfromtovar "plotter" 0 0)
(checkfromtovar "polysides" 3 1024)
(checkboolvar  "progbar")
(checkfromtovar "projmode" 0 2)
(checkboolvar  "promptmenu")
(checkboolvar  "proxygraphics")
(checkboolvar  "psltscale")
(checkfromtovar "psquality" -32768 32767)
(checkfromtovar "qaflags" 0 32767)
(checkboolvar  "qtextmode")
(checkfromtovar "rasterpreview" 0 2)
(checkboolvar  "regenmode")
(checkfromtovar "savetime" 0 240)
(checkfromtovar "screenboxes" 0 32767)
(checkfromtovar "scrlhist" 0 32767)
(checkfromtovar "shadedge" 0 3)
(checkfromtovar "shadedif" 0 100)
(checkboolvar  "skpoly")
(checkboolvar  "snapallviews")
(checkfromtovar "snapcolor" 0 256)
(checkfromtovar "snapisopair" 0 2)
(checkboolvar  "snapmode")
(checkfromtovar "snapsize" 1 20)
(checkboolvar  "snapstyl")
(checkfromtovar "snapthickness" 1 5)
(checkboolvar  "splframe")
(checkfromtovar "splinesegs" -32768 32767)
(checkfromtovar "splinetype" 1 20)
(checkfromtovar "surftab1" 2 32766)
(checkfromtovar "surftab2" 2 32766)
(checkfromtovar "surftype" 5 6)
(checkfromtovar "surfu" 2 200)
(checkfromtovar "surfv" 2 200)
(checkboolvar  "tabmode")
(checkboolvar  "tbcolor")
(checkboolvar  "tbsize")
(checkboolvar  "texteval")
(checkboolvar  "textfill")
(checkfromtovar "textqlty" 0 100)
(checkboolvar  "tilemode")
(checkboolvar  "tipofday")
(checkboolvar  "tooltips")
(checkfromtovar "treedepth" -32768 32767)
(checkboolvar  "trimmode")
(checkboolvar  "ucsfollow")
(checkfromtovar "ucsicon" 0 3)
(checkfromtovar "ucsiconpos" 0 3)
(checkboolvar  "unitmode")
(checkfromtovar "useri1" -32768 32767)
(checkfromtovar "useri2" -32768 32767)
(checkfromtovar "useri3" -32768 32767)
(checkfromtovar "useri4" -32768 32767)
(checkfromtovar "useri5" -32768 32767)
(checkboolvar  "visretain")
(checkfromtovar "wndbtexp" -32768 32767)
(checkfromtovar "wndlcmd" 0 3)
(checkfromtovar "wndlmain" 0 2)
(checkboolvar  "wndlstat")
(checkfromtovar "wndltexp" 0 2)
(checkfromtovar "wndlmain" 0 2)
(checkfromtovar "wndltext" 0 3)
(checkboolvar  "worldview")
(checkfromtovar "xloadctl" 0 2)
(checkboolvar  "xrefctl")
(checkfromtovar "zoomfactor" 3 100)
(checkfromtovar "zoompercent" 1 20000)
(checkfromtovar "indexctl" 0 3)
(checkfromtovar "sortents" 0 127)
(checkboolvar  "xclipframe")
