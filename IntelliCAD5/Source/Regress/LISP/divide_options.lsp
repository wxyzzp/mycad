(defun checkDivide (stpt ang noItems ln)
  (command "line" stpt (polar stpt ang ln) "")
  (command "dist" stpt (polar stpt ang ln))

  (command "divide" stpt noItems)
  (setq dis (getvar "distance"))
  (setq decre (/ dis noitems))
  (while (> dis 0.0)
    (setq en nil)
    (setq dis (- dis decre))
    (setq en (cdr (assoc 10 (entget (entlast)))))
    (setq exppt (polar stpt ang dis))
    (princ en)
    (princ exppt)
    (if	(comparePoint en exppt)
      (princ "OK")
      (alert "Err")
    )
    (command "erase" "l" "")
  )


)
(defun dtor (d) (* 0.0174533 d))
(defun comparePoint (ptAct ptExp)
  (and
    (equal (car ptAct) (car ptExp) 0.00001)
    (equal (cadr ptAct) (cadr ptExp) 0.00001)
    (equal (caddr ptAct) (caddr ptExp) 0.00001)
  )
)
(checkdivide '(1 1 0) 0 6 9)
(command "erase" "all" "")
(checkdivide '(1 1 0) 90 3 3)
(command "erase" "all" "")
(checkdivide '(1 1 0) 180 2 1)
(command "erase" "all" "")
(checkdivide '(1 1 0) 270 8 500)
(command "erase" "all" "")
