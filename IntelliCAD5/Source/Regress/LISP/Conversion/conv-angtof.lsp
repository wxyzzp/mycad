;;;
;;; Lisp Acceptance Test
;;;	Conversion functions
;;;		angtof
;;;
;;; 17 Jun 98	MichaelHu
;;;
	(logmsg "")
	(load (strcat testscrdir "error"))
;;; ---------------------------------------------
;;; boundary tests.
	;;; ------------------------------------------
	;;; no arguments.
	(defun noargs ( / prverr )
		(setq prverr *error*)
		(setq *error* silent_err)
		(setq rc (angtof))
		(logall errloc rc)
		(setq *error* prverr)
	)
	;;; --------------------------------------------
	;;; numerics.
	;;; --------------------------------------------
	;;; valid inputs.
	(defun zero0 ( / prverr )
		(setq prverr *error*)
		(setq *error* silent_err)
		(setq rc (angtof "0" 0))
		(logall errloc rc)
		(setq *error* prverr)
	)
	(defun zero1 ( / prverr )
		(setq prverr *error*)
		(setq *error* silent_err)
		(setq rc (angtof "0" 1))
		(logall errloc rc)
		(setq *error* prverr)
	)
	(defun zero2 ( / prverr )
		(setq prverr *error*)
		(setq *error* silent_err)
		(setq rc (angtof "0" 2))
		(logall errloc rc)
		(setq *error* prverr)
	)
	(defun zero3 ( / prverr )
		(setq prverr *error*)
		(setq *error* silent_err)
		(setq rc (angtof "0" 3))
		(logall errloc rc)
		(setq *error* prverr)
	)
	(defun zero4 ( / prverr )
		(setq prverr *error*)
		(setq *error* silent_err)
		(setq rc (angtof "0" 4))
		(logall errloc rc)
		(setq *error* prverr)
	)
	(defun pi0 ( / prverr )
		(setq prverr *error*)
		(setq *error* silent_err)
		(setq rc (angtof (rtos pi 2 6) 0))
		(logall errloc rc)
		(setq *error* prverr)
	)
	(defun pi1 ( / prverr )
		(setq prverr *error*)
		(setq *error* silent_err)
		(setq rc (angtof (rtos pi 2 6) 1))
		(logall errloc rc)
		(setq *error* prverr)
	)
	(defun pi2 ( / prverr )
		(setq prverr *error*)
		(setq *error* silent_err)
		(setq rc (angtof (rtos pi 2 6) 2))
		(logall errloc rc)
		(setq *error* prverr)
	)
	(defun pi3 ( / prverr )
		(setq prverr *error*)
		(setq *error* silent_err)
		(setq rc (angtof (rtos pi 2 6) 3))
		(logall errloc rc)
		(setq *error* prverr)
	)
	(defun pi4 ( / prverr )
		(setq prverr *error*)
		(setq *error* silent_err)
		(setq rc (angtof (rtos pi 2 6) 4))
		(logall errloc rc)
		(setq *error* prverr)
	)
	(defun twopi0 ( / prverr )
		(setq prverr *error*)
		(setq *error* silent_err)
		(setq rc (angtof (rtos (* 2 pi) 2 6) 0))
		(logall errloc rc)
		(setq *error* prverr)
	)
	(defun twopi1 ( / prverr )
		(setq prverr *error*)
		(setq *error* silent_err)
		(setq rc (angtof (rtos (* 2 pi) 2 6) 1))
		(logall errloc rc)
		(setq *error* prverr)
	)
	(defun twopi2 ( / prverr )
		(setq prverr *error*)
		(setq *error* silent_err)
		(setq rc (angtof (rtos (* 2 pi) 2 6) 2))
		(logall errloc rc)
		(setq *error* prverr)
	)
	(defun twopi3 ( / prverr )
		(setq prverr *error*)
		(setq *error* silent_err)
		(setq rc (angtof (rtos (* 2 pi) 2 6) 3))
		(logall errloc rc)
		(setq *error* prverr)
	)
	(defun twopi4 ( / prverr )
		(setq prverr *error*)
		(setq *error* silent_err)
		(setq rc (angtof (rtos (* 2 pi) 2 6) 4))
		(logall errloc rc)
		(setq *error* prverr)
	)

;;; ---------------------------------------------
;;; IntelliCAD help tests.
	(defun icadhlp1 ( / prverr )
		(setq prverr *error*)
		(setq *error* silent_err)
		(setq rc (angtof "90"))
		(logall errloc rc)
		(setq *error* prverr)
	)
	(defun icadhlp2 ( / prverr )
		(setq prverr *error*)
		(setq *error* silent_err)
		(setq rc (angtof "90" 0))
		(logall errloc rc)
		(setq *error* prverr)
	)
	(defun icadhlp3 ( / prverr )
		(setq prverr *error*)
		(setq *error* silent_err)
		(setq rc (angtof "90d30'10\""))
		(logall errloc rc)
		(setq *error* prverr)
	)
	(defun icadhlp4 ( / prverr )
		(setq prverr *error*)
		(setq *error* silent_err)
		(setq rc (angtof "90d" 1))
		(logall errloc rc)
		(setq *error* prverr)
	)
	(defun icadhlp5 ( / prverr )
		(setq prverr *error*)
		(setq *error* silent_err)
		(setq rc (angtof "100g" 2))
		(logall errloc rc)
		(setq *error* prverr)
	)
	(defun icadhlp6 ( / prverr )
		(setq prverr *error*)
		(setq *error* silent_err)
		(setq rc (angtof "1.5708r" 3))
		(logall errloc rc)
		(setq *error* prverr)
	)
	(defun icadhlp7 ( / prverr )
		(setq prverr *error*)
		(setq *error* silent_err)
		(setq rc (angtof "N 0d W" 4))
		(logall errloc rc)
		(setq *error* prverr)
	)

;;; ---------------------------------------------
;;; AutoCAD help tests.
