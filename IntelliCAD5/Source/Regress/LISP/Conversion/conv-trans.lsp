;;;
;;; Lisp Acceptance Test
;;;	Conversion functions
;;;		trans
;;;
;;; 17 Jun 98	MichaelHu
;;;
	(logmsg "")
	(load (strcat testscrdir "error"))
;;; ---------------------------------------------
;;; boundary tests.
	;;; ------------------------------------------
	;;; no arguments.
	(defun noargs ( / prverr )
		(setq prverr *error*)
		(setq *error* silent_err)
		(setq rc (trans ))
		(logall errloc rc)
		(setq *error* prverr)
	)

;;; ---------------------------------------------
;;; IntelliCAD help tests.
	(defun icadhlp1 ( / prverr )
		(setq prverr *error*)
		(setq *error* silent_err)
		(command "._ucs" "x" 45)
		(command "._elev" 5 0)
		(setq rc (trans '(1 1) 0 1))
		(command "._elev" 0 0)
		(command "._ucs" "p")
		(logall errloc rc)
		(setq *error* prverr)
	)
	(defun icadhlp2 ( / prverr )
		(setq prverr *error*)
		(setq *error* silent_err)
		(command "._ucs" "x" 45)
		(command "._elev" 5 0)
		(setq rc (trans '(1 1) 1 0))
		(command "._elev" 0 0)
		(command "._ucs" "p")
		(logall errloc rc)
		(setq *error* prverr)
	)
	(defun icadhlp3 ( / prverr )
		(setq prverr *error*)
		(setq *error* silent_err)
		(command "._ucs" "x" 45)
		(command "._elev" 5 0)
		(setq rc (trans '(1 1) 1 0 t))
		(command "._elev" 0 0)
		(command "._ucs" "p")
		(logall errloc rc)
		(setq *error* prverr)
	)

;;; ---------------------------------------------
;;; AutoCAD help tests.
	(defun acadhlp1 ( / prverr )
		(setq prverr *error*)
		(setq *error* silent_err)
		(command "._ucs" "z" 90)
		(setq rc (trans '(1.0 2.0 3.0) 0 1))
		(command "._ucs" "p")
		(logall errloc rc)
		(setq *error* prverr)
	)
	(defun acadhlp2 ( / prverr )
		(setq prverr *error*)
		(setq *error* silent_err)
		(command "._ucs" "z" 90)
		(setq rc (trans '(1.0 2.0 3.0) 1 0))
		(command "._ucs" "p")
		(logall errloc rc)
		(setq *error* prverr)
	)
	(defun acadhlp3 ( / prverr )
		(setq prverr *error*)
		(setq *error* silent_err)
		(command "._ucs" "x" 45)
		(command "._text" '(5 5) 2 45 "trans test")
		(command "._ucs" "p")
		(setq rc (trans '(5 5) (entlast) 1))
		(logall errloc rc)
		(setq *error* prverr)
	)
	(defun acadhlp4 ( / prverr )
		(setq prverr *error*)
		(setq *error* silent_err)
		(command "._ucs" "x" 45)
		(command "._circle" '(5 5) 5)
		(command "._ucs" "p")
		(setq rc (trans '(1 2 3) 1 (entlast)))
		(logall errloc rc)
		(setq *error* prverr)
	)
	(defun acadhlp5 ( / prverr )
		(setq prverr *error*)
		(setq *error* silent_err)
		(command "._ucs" "x" 45)
		(setq rc (trans '(1 1) 1 2))
		(command "._ucs" "p")
		(logall errloc rc)
		(setq *error* prverr)
	)
	(defun acadhlp6 ( / prverr )
		(setq prverr *error*)
		(setq *error* silent_err)
		(command "._line" '(5 5) '(8 3) "")
		(setq rc (trans '(5 5) (entlast) 2))
		(logall errloc rc)
		(setq *error* prverr)
	)
