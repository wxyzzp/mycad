;;;
;;; Lisp Acceptance Test
;;;	Conversion functions
;;;		rtos
;;;
;;; 17 Jun 98	MichaelHu
;;;
	(logmsg "")
	(load (strcat testscrdir "error"))
;;; ---------------------------------------------
;;; boundary tests.
	;;; ------------------------------------------
	;;; no arguments.
	(defun noargs ( / prverr )
		(setq prverr *error*)
		(setq *error* silent_err)
		(setq rc (rtos ))
		(logall errloc rc)
		(setq *error* prverr)
	)
	;;; --------------------------------------------
	;;; numerics.
	;;; --------------------------------------------
	;;; valid inputs.
	(defun zero ( / prverr )
		(setq prverr *error*)
		(setq *error* silent_err)
		(setq rc (rtos 0))
		(logall errloc rc)
		(setq *error* prverr)
	)
	(defun nine ( / prverr )
		(setq prverr *error*)
		(setq *error* silent_err)
		(setq rc (rtos 9))
		(logall errloc rc)
		(setq *error* prverr)
	)
	(defun minuszero ( / prverr )
		(setq prverr *error*)
		(setq *error* silent_err)
		(setq rc (rtos -0))
		(logall errloc rc)
		(setq *error* prverr)
	)
	(defun minusnine ( / prverr )
		(setq prverr *error*)
		(setq *error* silent_err)
		(setq rc (rtos -9))
		(logall errloc rc)
		(setq *error* prverr)
	)
	;;; --------------------------------------------
	;;; invalid inputs.
	(defun belownum ( / prverr )
		(setq prverr *error*)
		(setq *error* silent_err)
		(setq rc (rtos "/"))
		(logall errloc rc)
		(setq *error* prverr)
	)
	(defun abovenum ( / prverr )
		(setq prverr *error*)
		(setq *error* silent_err)
		(setq rc (rtos ":"))
		(logall errloc rc)
		(setq *error* prverr)
	)
	(defun nilsym ( / prverr )
		(setq prverr *error*)
		(setq *error* silent_err)
		(setq rc (rtos nil))
		(logall errloc rc)
		(setq *error* prverr)
	)
	(defun tsym ( / prverr )
		(setq prverr *error*)
		(setq *error* silent_err)
		(setq rc (rtos t))
		(logall errloc rc)
		(setq *error* prverr)
	)
	;;; --------------------------------------------
	;;; integers.
	(defun zeroint ( / prverr )
		(setq prverr *error*)
		(setq *error* silent_err)
		(setq rc (rtos 0))
		(logall errloc rc)
		(setq *error* prverr)
	)
	(defun minint ( / prverr )
		(setq prverr *error*)
		(setq *error* silent_err)
		(setq rc (rtos -2147483648))
		(logall errloc rc)
		(setq *error* prverr)
	)
	(defun maxint ( / prverr )
		(setq prverr *error*)
		(setq *error* silent_err)
		(setq rc (rtos 2147483647))
		(logall errloc rc)
		(setq *error* prverr)
	)
	(defun minp1int ( / prverr )
		(setq prverr *error*)
		(setq *error* silent_err)
		(setq rc (rtos -2147483649))
		(logall errloc rc)
		(setq *error* prverr)
	)
	(defun maxp1int ( / prverr )
		(setq prverr *error*)
		(setq *error* silent_err)
		(setq rc (rtos 2147483648))
		(logall errloc rc)
		(setq *error* prverr)
	)
	;;; --------------------------------------------
	;;; reals.
	(defun zeroreal ( / prverr )
		(setq prverr *error*)
		(setq *error* silent_err)
		(setq rc (rtos 0.0))
		(logall errloc rc)
		(setq *error* prverr)
	)
	(defun minreal ( / prverr )
		(setq prverr *error*)
		(setq *error* silent_err)
		(setq rc (rtos 9.9e-324))
		(logall errloc rc)
		(setq *error* prverr)
	)
	(defun maxreal ( / prverr )
		(setq prverr *error*)
		(setq *error* silent_err)
		(setq rc (rtos 9.9e307))
		(logall errloc rc)
		(setq *error* prverr)
	)
	(defun minp1real ( / prverr )
		(setq prverr *error*)
		(setq *error* silent_err)
		(setq rc (rtos 9.9e-325))
		(logall errloc rc)
		(setq *error* prverr)
	)

;;; ---------------------------------------------
;;; IntelliCAD help tests.
	(defun icadhlp1 ( / prverr )
		(setq prverr *error*)
		(setq *error* silent_err)
		(setq rc (rtos 15.35 1 4))
		(logall errloc rc)
		(setq *error* prverr)
	)
	(defun icadhlp2 ( / prverr )
		(setq prverr *error*)
		(setq *error* silent_err)
		(setq rc (rtos 15.35 2 4))
		(logall errloc rc)
		(setq *error* prverr)
	)
	(defun icadhlp3 ( / prverr )
		(setq prverr *error*)
		(setq *error* silent_err)
		(setq rc (rtos 15.35 3 4))
		(logall errloc rc)
		(setq *error* prverr)
	)
	(defun icadhlp4 ( / prverr )
		(setq prverr *error*)
		(setq *error* silent_err)
		(setq rc (rtos 15.35 4 4))
		(logall errloc rc)
		(setq *error* prverr)
	)
	(defun icadhlp5 ( / prverr )
		(setq prverr *error*)
		(setq *error* silent_err)
		(setq rc (rtos 15.35 5 4))
		(logall errloc rc)
		(setq *error* prverr)
	)

;;; ---------------------------------------------
;;; AutoCAD help tests.
