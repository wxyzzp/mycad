;CUTUBE.LSP
;(From a group of danish student and theacher)
(defun cutubex ()
  (setq P1A (polar P1 A QD))
  (setq P1A (polar P1A (+ A HPI) (/ QD 2.0)))
  (setq P2A (polar P2 A QD))
  (setq P2A (polar P2A (- A HPI) (/ QD 2.0)))
  (setq P3A (polar P2A (+ A HPI) QD))
  (setvar "blipmode" 0)
  (command "pline" P1 "arc" "S" P1A P2 "S" P2A P3 "S" P3A P2 "")
  (setvar "blipmode" 0)
)
(defun C:CT ()
  (setvar "cmdecho" 0)
  (setq CL (getvar "clayer"))
  (setq osm (getvar "osmode"))
  (setvar "osmode" 0)
  (setq HPI (/ PI 2.0))
  (setq E1 (entsel "\nSelect one side of tube: "))
  (setq P1 (cadr E1))
  (setq LY1 (entget (car E1)))
  (setq LY1 (cdr (assoc 8 LY1)))
  (setq E3 (entsel "\nSelect the other side: "))
  (setq P13 (cadr E3))
  (setvar "lastpoint" P1)
  (setq P3 (osnap (cadr E3) "per"))
  (setq LY2 (entget (car E3)))
  (setq LY2 (cdr (assoc 8 LY2)))
  (setq A (angle P1 P3))
  (setq D (distance P1 P3))
  (setq HD (/ D 2.0))
  (setq QD (/ HD 2.0))
  (setq P2 (polar P1 A HD))
  (setq P1X P1)
  (if (/= LY1 LY2)
     (prompt "\nLines are on different layers.")
     (progn
          (command "layer" "S" ly1 "")
          (cutubex)
          (setq ans (strcase (getstring "\nChange orientation <y/N>? ")))
          (if (= ans "Y")
             (progn
               (setvar "highlight" 0)
               (setq P1 P3 P3 P1X)
               (setq A (angle P1 P3))
               (command "erase" "L" "")
               (cutubex)
               (setvar "highlight" 1)
             )
          )
          (setq ANS nil)
          (setq ANS (strcase (getstring "\nBreak one side <y/N>?")))
          (if (= ANS "Y")
             (progn
                (prompt "\n<select point on line>")
                (setq DIR (getpoint p1 "\nselect side of symbol: "))
                (setq A1 (angle P1 DIR))
                (setq D1 (distance P1 DIR))
                (setq P1X (polar P1 A1 D1))
                (setq P3X (polar P3 A1 D1))
                (setvar "highlight" 0)
                (command "break" P3X P3)
                (command "break" p1x p1)
                (setvar "highlight" 1)
             )
          )
          (setq ANS nil)
          (setq ANS (strcase (getstring "\nDarken half symbol <y/N>? ")))
          (if (= ANS "Y")
             (progn
                (prompt "   wait..")
                (setvar "blipmode" 0)
                (setvar "highlight" 0)

                (command "pline" P2 "arc" "S" P2A P3 "S" P3A P2 "")

                (command "Hatch" "U" (rtd (- A 45)) (/ QD 5) "N" "L" "")
                (command "erase" "P" "")
                (redraw)
                (setvar "blipmode" 1)
                (setvar "highlight" 1)
             )
          )
          (command "layer" "S" CL "")
       );end of progn for matching layer names
   );end of if for matching layer names
   (princ)
  (setvar "osmode" osm)
);end of command

(defun rtd (a)                          ;routine for radians to degrees
  (/ (* A 180.0) pi)
)
(princ " \n Cutube is now ready to make a break symbol for you...  Start with CT ")
(princ)
