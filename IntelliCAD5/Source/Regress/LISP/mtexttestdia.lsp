(defun c:testDia()
	(setq 	i  1
	)
	(while (< i 10)
		(test)
		(setq i (+ i 1))
	)
	(command "zoom" "extents")
)

(defun test()
	(setq strt (strcat "mtext" (rtos i 2 0)))
	(command "color" (+ i 1))
;	(command "Line" (list 0  i) (list 6  i) "")
	(command "rectangle" (list 3  i) (list 6  (+ i 0.5)) )
	(command "rectangle" (list 0  i) (list 3  (+ i 0.5)) )
	(command "-mText" (list 3  i) (list 6  (+ i 0.5)) strt "" )
	(command "-mText" (list 0  i) (list 3  (+ i 0.5)) strt "" )
	(setq en (entlast))
	(setq en1 (entget en))
	(setq en1 (subst (cons 71 i) (assoc 71 en1) en1))
	(setq en1 (subst (cons 72 5) (assoc 72 en1) en1))
	(entmod en1)
)
