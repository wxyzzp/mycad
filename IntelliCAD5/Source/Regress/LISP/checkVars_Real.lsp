(defun checkFromToVar(varname from to)
	(setq tmp (getvar varname))
	(setq i from)
	(while (<= i to)
		(setvar varname i)
;		(if (/= (getvar varname) i) (alert varname))
		(setq i (+ i (/ (- to from) 500.0)))
;		(setq i (+ i 10.0))
	)
	(setvar varname tmp)
	(princ varname)
)
;;;;;;;;;;;;;;;;;;;;;;;;;;;;;;;;;;;;;;;;;;;;;;;;;;;;;;;;
(setq REAL_MAX 300000000000000000.0)
(checkfromtovar "angbase" (- REAL_MAX) REAL_MAX)
(checkfromtovar "celtscale" 0.1 REAL_MAX)
(checkfromtovar "chamfera" 0.0 REAL_MAX)
(checkfromtovar "chamferb" 0.0 REAL_MAX)
(checkfromtovar "chamferc" 0.0 REAL_MAX)
(checkfromtovar "chamferd" 0.0 REAL_MAX)
(checkfromtovar "circlerad" 0.0 REAL_MAX)
(checkfromtovar "cmlscale" (- REAL_MAX) REAL_MAX)
(checkfromtovar "dimaltf" 0.1 REAL_MAX)
(checkfromtovar "dimaltrnd" 0.0 REAL_MAX)
(checkfromtovar "dimasz" 0.0 REAL_MAX)
(checkfromtovar "dimcen" (- REAL_MAX) REAL_MAX)
(checkfromtovar "dimdle" 0.0 REAL_MAX)
(checkfromtovar "dimdli" 0.0 REAL_MAX)
(checkfromtovar "dimexe" 0.0 REAL_MAX)
(checkfromtovar "dimexo" 0.0 REAL_MAX)
(checkfromtovar "dimgap" (- REAL_MAX) REAL_MAX)
(checkfromtovar "dimlfac" (- REAL_MAX) REAL_MAX)
(checkfromtovar "dimrnd" 0.0 REAL_MAX)
(checkfromtovar "dimscale" 0.0 REAL_MAX)
(checkfromtovar "dimtfac" 0.1 REAL_MAX)
(checkfromtovar "dimtm" (- REAL_MAX) REAL_MAX)
(checkfromtovar "dimtp" (- REAL_MAX) REAL_MAX)
(checkfromtovar "dimtsz" 0.0 REAL_MAX)
(checkfromtovar "dimtvp" (- REAL_MAX) REAL_MAX)
(checkfromtovar "dimtxt" 0.1 REAL_MAX)
(checkfromtovar "donutid" 0.0 REAL_MAX)
(checkfromtovar "donutod" 0.0 REAL_MAX)
(checkfromtovar "elevation" (- REAL_MAX) REAL_MAX)
(checkfromtovar "facetres" 0.01 10.0)
(checkfromtovar "filletrad" 0.0 REAL_MAX)
(checkfromtovar "hpscale" 0.1 REAL_MAX)
(checkfromtovar "hpspace" 0.1 REAL_MAX)
(checkfromtovar "lastangle" (- REAL_MAX) REAL_MAX)
;(checkfromtovar "lastcmdang" (- REAL_MAX) REAL_MAX)
(checkfromtovar "ltscale" 0.1 REAL_MAX)
(checkfromtovar "offsetdist" (- REAL_MAX) REAL_MAX)
(checkfromtovar "pdsize" (- REAL_MAX) REAL_MAX)
(checkfromtovar "plinewid" 0.0 REAL_MAX)
(checkfromtovar "sketchinc" 0.1 REAL_MAX)
(checkfromtovar "snapang" (- REAL_MAX) REAL_MAX)
(checkfromtovar "textangle" (- REAL_MAX) REAL_MAX)
(checkfromtovar "textsize" 0.1 REAL_MAX)
(checkfromtovar "thickness" (- REAL_MAX) REAL_MAX)
(checkfromtovar "tracewid" 0.0 REAL_MAX)
(checkfromtovar "viewaspect" (- REAL_MAX) REAL_MAX)
