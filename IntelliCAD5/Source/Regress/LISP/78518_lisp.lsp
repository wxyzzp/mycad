;_Created_by_Srinivas_on_5/13/2003
(defun checkArrPolar (stpt ang noItems arrAng)
  (command "line" stpt (polar stpt ang 1) "")
  (command "array" "l" "" "polar" stpt noItems arrAng "y")

  (setq an (+ ang arrang))
  (setq decre (/ (+ ang arrang) (1- noitems)))
  (while (/= an ang)
    (setq en nil)
    (setq en (cdr (assoc 11 (entget (entlast)))))
    (setq exppt (polar stpt (dtor an) 1))
    (princ en)
    (princ exppt)
    (if	(comparePoint en exppt)
      (princ "OK")
      (alert "Err")
    )
    (setq an (- an decre))
    (command "erase" "l" "")
  )


)
(defun dtor (d) (* 0.0174533 d))
(defun comparePoint (ptAct ptExp)
  (and
    (equal (car ptAct) (car ptExp) 0.00001)
    (equal (cadr ptAct) (cadr ptExp) 0.00001)
    (equal (caddr ptAct) (caddr ptExp) 0.00001)
  )
)
(checkarrpolar '(1 1 0) 0 6 -90)
(command "erase" "all" "")
(checkarrpolar '(1 1 0) 0 6 90)
(command "erase" "all" "")
(checkarrpolar '(1 1 0) 0 6 -190)
(command "erase" "all" "")
(checkarrpolar '(1 1 0) 0 8 350)
(command "erase" "all" "")
