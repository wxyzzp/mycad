(defun c:count()
(setq startTime (getvar "DATE"))
(princ (strcat "\n Started at " (rtos startTime)))
(setq s (getvar "DATE"))
(setq startSeconds (* 86400.0 (- s (fix s))))
(princ startSeconds)
(princ "\nCreated by Mr.MANOJ MADHAVAN")
(setq ETlist (list "LINE" "CIRCLE" "ARC" "LWPOLYLINE" "ELLIPSE" "INSERT")n 0)
(repeat (length ETlist)
(setq ETYPE (nth n etlist))
(setq sslent (ssget "x" (list (cons 0 ETYPE))))
(if (not sslent)
(progn
(princ "\n")
(princ ETYPE)
(princ " = ")
(princ "0")
(princ " Entities in the drawing file")
(setq n (1+ n))
)
(progn
(setq ecount (sslength sslent))
(princ "\n")
(princ ETYPE)
(princ " = ")
(princ ecount)
(princ " Entities in the drawing file")
(setq n (1+ n))
);progn
);if
);rep
(princ "\nCount for entities complete")
(setq s (getvar "DATE"))
(setq endSeconds (* 86400.0 (- s (fix s))))
(princ "\n TOTAL TIME TO RUN THE LISP FILE IS ")
(princ (- endSeconds startSeconds))
(princ "\n")
(princ)
(princ)
)
