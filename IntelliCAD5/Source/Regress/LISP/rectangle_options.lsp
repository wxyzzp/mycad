(defun comparelist(explist actlist)
	(Setq i 1)
	(while (<= i (length explist))
		(if (equal (nth i explist) (nth i actlist) 0.00001) (princ i) (alert "ERR"))
		(setq i (1+ i))
 	)
)
;;;;;;;;;;;;;;;;;;;;;;;;;;;;;;;;;;;;;
(defun checkCoordList (explist)
  (setq le (entget (entlast)))
  (setq entcoords nil)
  (foreach co le
;  (princ co)
    (progn (if (= (car co) 10)
		(progn
;		    (princ (cadr co))
;		    (princ (caddr co))
;		    (setq entcoords (append entcoords (cadr co)))
		    (setq entcoords (append entcoords (list (cadr co) (caddr co))))

		)
	   )
    )
  )
	(princ entcoords)
(comparelist explist entcoords)
)
;;;;;;;;;;;;;;;;;;;;;;;;;;;;;;;;;;;;;;;;;;
(defun checkBulgeList (explist)
  (setq le (entget (entlast)))
  (setq entcoords nil)
  (foreach co le
;  (princ co)
    (progn (if (= (car co) 42)
		(progn
;		    (princ (cadr co))
;		    (princ (caddr co))
;		    (setq entcoords (append entcoords (cadr co)))
		    (setq entcoords (append entcoords (list (cdr co))))

		)
	   )
    )
  )
	(princ entcoords)
(comparelist explist entcoords)
)
;___________normal__________
(command "erase" "All" "")
(command "rectangle" "0,0" "2,1")
(checkcoordlist (list 0.0 0.0 2.0 0.0 2.0 1.0 0.0 1.0))
;____________chamfer_________________
(command "erase" "All" "")
(command "rectangle" "c" "0.1" "" "0,0" "3,2")
;(checkcoordlist (list 0.1 0.0 2.9 0.0 3.0 0.1 3.0 1.9 2.9 2.0 0.1 2.0 0.0 2.9 0.0 0.1))
(command "erase" "All" "")
(command "rectangle" "c" "0.1" "0.2" "0,0" "3,2")
;(checkcoordlist (list 0.1 0.0 2.9 0.0 3.0 0.1 3.0 1.9 2.9 2.0 0.1 2.0 0.0 2.9 0.0 0.1))
(command "erase" "All" "")
(command "rectangle" "c" "0.1" "0.2" "0,0" "0.2,0.2")
(checkcoordlist (list 0.0 0.0 0.2 0.0 0.2 0.2 0.0 0.2))
;____________chamfer_off________________
(command "erase" "All" "")
(command "rectangle" "c" "off" "0,0" "2,1")
(checkcoordlist (list 0.0 0.0 2.0 0.0 2.0 1.0 0.0 1.0))
;____________chamfer_defaults________________
(command "erase" "All" "")
(command "rectangle" "c" "d" "0,0" "2,2")
;(checkcoordlist (list 0.0 0.0 2.0 0.0 2.0 1.0 0.0 1.0))
(command "rectangle" "c" "0" "0" "0,0" "2,2")
;____________elevation________________
(command "erase" "All" "")
(command "rectangle" "e" "1" "0,0" "2,1")
(checkcoordlist (list 0.0 0.0 2.0 0.0 2.0 1.0 0.0 1.0))
(if (/= (last (assoc 10 (entget (entlast)))) 1.0) (alert "ELEV ERR"))
(command "rectangle" "e" "0" "0,0" "2,1")
;____________fillet________________
(command "erase" "All" "")
(command "rectangle" "f" "0.1" "0,0" "2,1")
;(checkcoordlist (list 0.0 0.0 2.0 0.0 2.0 1.0 0.0 1.0))
(checkBulgelist (list 0.0 0.414214 0.0 0.414214 0.0 0.414214 0.0 0.414214))
(command "rectangle" "f" "0" "0,0" "2,1")
;____________rotation____________
(command "erase" "All" "")
(command "rectangle" "r" "0,0" "2,1" "90")
(checkcoordlist (list 0.0 0.0 0.0 2.0 -1.0 2.0 -1.0 0.0))
;____________square_______________
(command "erase" "All" "")
(command "rectangle" "s" "0,0" "2,0")
(checkcoordlist (list 0.0 0.0 2.0 0.0 2.0 2.0 0.0 2.0))
;_____________thickness_____________
(command "erase" "All" "")
(command "rectangle" "t" "7.0" "0,0" "2,0")
(if (/= (cdr (assoc 39 (entget (entlast)))) 7.0) (alert "thickness ERR"))
(command "rectangle" "t" "0.0" "0,0" "2,0")
;_____________width_____________
(command "erase" "All" "")
(command "rectangle" "w" "0.10" "0,0" "2,0")
(if (/= (cdr (assoc 43 (entget (entlast)))) 0.1) (alert "width ERR"))
(command "rectangle" "w" "0.0" "0,0" "2,0")
