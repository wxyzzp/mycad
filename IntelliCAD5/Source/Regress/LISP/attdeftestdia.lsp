(defun c:testDia()
	(setq 	i72  0
		i74  3
		i  0
	)
	(while (< i 15)
		(test)
		(If (= i74  0)
			(If (< i72 6)
				(setq i72 (+ i72 1))
			)
			(If (< i72 2)
				(setq i72 (+ i72 1))
				(setq i74 (- i74 1) i72 0)
			)
			    
		)
	(setq i (+ i 1))
	)
	(command "zoom" "extents")
)

(defun test()
	(setq strt (strcat (rtos i 2 0) " 72. " (rtos i72 2 0) " 74. " (rtos i74 2 0)))
	(command "color" (+ i 1))
	(command "Line" (list 0  i) (list 6  i) "")
	(command "attdef" "" strt strt strt (list 4  i) "" "" )
	(command "attdef" "" strt strt strt (list 2  i) "" "" )
	(setq en (entlast))
	(setq en1 (entget en))
	(setq en1 (subst (cons 74 i74) (assoc 74 en1) en1))
	(setq en1 (subst (cons 72 i72) (assoc 72 en1) en1))
	(setq en1 (subst (cons 10 (list 0 i)) (assoc 10 en1) en1))
	(setq en1 (subst (cons 11 (list 2 i)) (assoc 11 en1) en1))
	(entmod en1)
)
