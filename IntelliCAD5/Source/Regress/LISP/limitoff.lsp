(prompt "\nType in Limitoff  to start this routine")
(defun C:limitoff (/ pt1 pt2 r1 r2)
(setq pt1 (getvar "LIMMIN")
pt2 (getvar "LIMMAX")
)
(grvecs (list 256 (list (car pt1)(cadr pt2)) pt2
256 (list (car pt2)(cadr pt1)) pt1
256 pt1 (list (car pt1)(cadr pt2))
256 pt2 (list (car pt2)(cadr pt1))
)
)
(grdraw pt1 pt2 -1)
(grdraw (list (car pt1) (cadr pt2))
(list (car pt2) (cadr pt1))
-1
)
(princ "Limit rect info:")
(setq r1 (rtos (car (getvar "limmin")))
r2 (rtos (cadr (getvar "limmin")))
)
(prompt (strcat "\nUpper right: " r1 "," r2))
(if (= (getvar "LIMCHECK") 0)
(setq linf "off")
(setq linf "on")
)
(prompt (strcat "\nLimits are " linf))
(princ)
)
