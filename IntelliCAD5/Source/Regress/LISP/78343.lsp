(defun c:test_Q()
	(command "textsize" 1)
	(setq i 1)
	(while (<= i 1080)
		(command "-mtext" (list (* (/ i 120) 20) (abs (rem i 120))) (list (+ 260 (* (/ i 120) 20)) (+ (abs (rem i 120)) 2)) (strcat "\\Q" (rtos (- i 360) 2 0) ";IntelliCAD " (rtos (- i 360) 2 0)) "") 
		(command "zoom" "C" (cdr (assoc '10. (entget (entlast)))) "8")
		(setq i (+ i 1))
	)
)
