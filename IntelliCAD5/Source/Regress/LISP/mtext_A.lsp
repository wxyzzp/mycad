(defun c:test_a()
	(command "textsize" 2)
	(setq stX 0)
	(setq enX 175)
	(setq IncreX 75)	
	(setq IncreI 0.5)
	(setq IncreY 7.5)
;________1___________\A0
	(command "color" 1)
	(setq i -10)
	(setq yy 0)
	(while (< i 10)
		(Command "Color" 2)
		(command "-mtext" (list stX yy) (list enX (+ yy i)) (strcat "\\A0;Intelli\\A;CAD" (rtos i)) "")
		(Command "Color" 1)
		(command "-mtext" (list stX yy) (list enX (+ yy i)) (strcat "\\A0;Intelli\\A" (rtos i) ";CAD" (rtos i)) "")
		(command "zoom" "C" (cdr (assoc '10. (entget (entlast)))) "4")
		(setq i (+ i IncreI))
		(setq yy (+ yy IncreY))
	)
;________2___________\A
	(command "color" 2)
	(setq i -10)
	(setq yy 0)
	(setq stX (+ stX IncreX))
	(setq enX (+ enX IncreX))
	(while (< i 10)
		(Command "Color" 2)
		(command "-mtext" (list stX yy) (list enX (+ yy i)) (strcat "\\A0;Intelli\\A;CAD" (rtos i)) "")
		(Command "Color" 1)
		(command "-mtext" (list stX yy) (list enX (+ yy i)) (strcat "\\A;Intelli\\A" (rtos i) ";CAD" (rtos i)) "")
		(command "zoom" "C" (cdr (assoc '10. (entget (entlast)))) "4")
		(setq i (+ i IncreI))
		(setq yy (+ yy IncreY))
	)
;________3___________\A0X_\A0x
	(command "color" 3)
	(setq i -10)
	(setq yy 0)
	(setq stX (+ stX IncreX))
	(setq enX (+ enX IncreX))
	(while (< i 10)
		(Command "Color" 2)
		(command "-mtext" (list stX yy) (list enX (+ yy i)) (strcat "\\A0;Intelli\\A;CAD" (rtos i)) "")
		(Command "Color" 1)
		(command "-mtext" (list stX yy) (list enX (+ yy i)) (strcat "\\A0X;Intelli\\A" (rtos i) "X;CAD" (rtos i)) "")
		(command "zoom" "C" (cdr (assoc '10. (entget (entlast)))) "4")
		(setq i (+ i IncreI))
		(setq yy (+ yy IncreY))
		(command "-mtext" (list stX yy) (list enX (+ yy i)) (strcat "\\A0;Intelli\\A;CAD" (rtos i)) "")
		(Command "Color" 1)
		(command "-mtext" (list stX yy) (list enX (+ yy i)) (strcat "\\A0x;Intelli\\A" (rtos i) "x;CAD" (rtos i)) "")
		(command "zoom" "C" (cdr (assoc '10. (entget (entlast)))) "4")
		(setq i (+ i IncreI))
		(setq yy (+ yy IncreY))

	)
;________4___________\AX_\Ax
	(command "color" 4)
	(setq i -10)
	(setq stX (+ stX IncreX))
	(setq enX (+ enX IncreX))
	(setq yy 0)
	(while (< i 10)
		(Command "Color" 2)
		(command "-mtext" (list stX yy) (list enX (+ yy i)) (strcat "\\A0;Intelli\\A;CAD" (rtos i)) "")
		(Command "Color" 1)
		(command "-mtext" (list stX yy) (list enX (+ yy i)) (strcat "\\AX;Intelli\\A" (rtos i) "X;CAD" (rtos i)) "")
		(command "zoom" "C" (cdr (assoc '10. (entget (entlast)))) "4")
		(setq i (+ i IncreI))
		(setq yy (+ yy IncreY))
		(Command "Color" 2)
		(command "-mtext" (list stX yy) (list enX (+ yy i)) (strcat "\\A0;Intelli\\A;CAD" (rtos i)) "")
		(Command "Color" 1)
		(command "-mtext" (list stX yy) (list enX (+ yy i)) (strcat "\\Ax;Intelli\\A" (rtos i) "x;CAD" (rtos i)) "")
		(command "zoom" "C" (cdr (assoc '10. (entget (entlast)))) "4")
		(setq i (+ i IncreI))
		(setq yy (+ yy IncreY))

	)
;________1___________\a0
	(command "color" 5)
	(setq i -10)
	(setq stX (+ stX IncreX))
	(setq enX (+ enX IncreX))
	(setq IncreX 50)
	(setq yy 0)
	(while (< i 10)
		(Command "Color" 2)
		(command "-mtext" (list stX yy) (list enX (+ yy i)) (strcat "\\A0;Intelli\\A;CAD" (rtos i)) "")
		(Command "Color" 1)
		(command "-mtext" (list stX yy) (list enX (+ yy i)) (strcat "\\a0;Intelli\\a" (rtos i) ";CAD" (rtos i)) "")
		(command "zoom" "C" (cdr (assoc '10. (entget (entlast)))) "4")
		(setq i (+ i IncreI))
		(setq yy (+ yy IncreY))
	)
;________2___________\a
	(command "color" 6)
	(setq i -10)
	(setq yy 0)
	(setq stX (+ stX IncreX))
	(setq enX (+ enX IncreX))
	(while (< i 10)
		(Command "Color" 2)
		(command "-mtext" (list stX yy) (list enX (+ yy i)) (strcat "\\A0;Intelli\\A;CAD" (rtos i)) "")
		(Command "Color" 1)
		(command "-mtext" (list stX yy) (list enX (+ yy i)) (strcat "\\a;Intelli\\a" (rtos i) ";CAD" (rtos i)) "")
		(command "zoom" "C" (cdr (assoc '10. (entget (entlast)))) "4")
		(setq i (+ i IncreI))
		(setq yy (+ yy IncreY))
	)
;________3___________\a0X_\a0x
	(command "color" 7)
	(setq i -10)
	(setq yy 0)
	(setq stX (+ stX IncreX))
	(setq enX (+ enX IncreX))
	(while (< i 10)
		(Command "Color" 2)
		(command "-mtext" (list stX yy) (list enX (+ yy i)) (strcat "\\A0;Intelli\\A;CAD" (rtos i)) "")
		(Command "Color" 1)
		(command "-mtext" (list stX yy) (list enX (+ yy i)) (strcat "\\a0X;Intelli\\a" (rtos i) "X;CAD" (rtos i)) "")
		(command "zoom" "C" (cdr (assoc '10. (entget (entlast)))) "4")
		(setq i (+ i IncreI))
		(setq yy (+ yy IncreY))
		(Command "Color" 2)
		(command "-mtext" (list stX yy) (list enX (+ yy i)) (strcat "\\a0x;Intelli\\a" (rtos i) "x;CAD" (rtos i)) "")
		(command "zoom" "C" (cdr (assoc '10. (entget (entlast)))) "4")
		(setq i (+ i IncreI))
		(setq yy (+ yy IncreY))

	)
;________4___________\aX_\ax
	(command "color" 8)
	(setq i -10)
	(setq stX (+ stX IncreX))
	(setq enX (+ enX IncreX))
	(setq yy 0)
	(while (< i 10)
		(Command "Color" 2)
		(command "-mtext" (list stX yy) (list enX (+ yy i)) (strcat "\\A0;Intelli\\A;CAD" (rtos i)) "")
		(Command "Color" 1)
		(command "-mtext" (list stX yy) (list enX (+ yy i)) (strcat "\\aX;Intelli\\a" (rtos i) "X;CAD" (rtos i)) "")
		(command "zoom" "C" (cdr (assoc '10. (entget (entlast)))) "4")
		(setq i (+ i IncreI))
		(setq yy (+ yy IncreY))
		(Command "Color" 2)
		(command "-mtext" (list stX yy) (list enX (+ yy i)) (strcat "\\A0;Intelli\\A;CAD" (rtos i)) "")
		(Command "Color" 1)
		(command "-mtext" (list stX yy) (list enX (+ yy i)) (strcat "\\ax;Intelli\\a" (rtos i) "x;CAD" (rtos i)) "")
		(command "zoom" "C" (cdr (assoc '10. (entget (entlast)))) "4")
		(setq i (+ i IncreI))
		(setq yy (+ yy IncreY))

	)

	(command "zoom" "extents")
)
