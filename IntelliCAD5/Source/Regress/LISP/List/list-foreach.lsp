;;;
;;; Lisp Acceptance Test
;;;	List functions
;;;		foreach
;;;
;;; 17 Jun 98	MichaelHu
;;;
	(logmsg "")
	(load (strcat testscrdir "error"))
;;; ---------------------------------------------
;;; boundary tests.
	;;; ------------------------------------------
	;;; no arguments.
	(defun noargs ( / prverr )
		(setq prverr *error*)
		(setq *error* silent_err)
		(setq rc (foreach x (append) (logstr errloc x)))
		(setq *error* prverr)
	)
	(defun noargs2 ( / prverr )
		(setq prverr *error*)
		(setq *error* silent_err)
		(setq rc (foreach x (append '()) (logstr errloc x)))
		(setq *error* prverr)
	)
	;;; --------------------------------------------
	;;; strings
	;;; --------------------------------------------
	;;; valid inputs.
	(defun emptystr ( / prverr )
		(setq prverr *error*)
		(setq *error* silent_err)
		(setq rc (foreach x (append '("")) (logstr errloc x)))
		(setq *error* prverr)
	)
	(defun emptyemptystr ( / prverr )
		(setq prverr *error*)
		(setq *error* silent_err)
		(setq rc (foreach x (append '("" "")) (logstr errloc x)))
		(setq *error* prverr)
	)
	(defun emptystrtxt ( / prverr )
		(setq prverr *error*)
		(setq *error* silent_err)
		(setq rc (foreach x (append '("" "hi")) (logstr errloc x)))
		(setq *error* prverr)
	)
	(defun txtemptystr ( / prverr )
		(setq prverr *error*)
		(setq *error* silent_err)
		(setq rc (foreach x (append '("hi" "")) (logstr errloc x)))
		(setq *error* prverr)
	)
	(defun spacestr ( / prverr )
		(setq prverr *error*)
		(setq *error* silent_err)
		(setq rc (foreach x (append '(" ")) (logstr errloc x)))
		(setq *error* prverr)
	)
	(defun spacestrtxt ( / prverr )
		(setq prverr *error*)
		(setq *error* silent_err)
		(setq rc (foreach x (append '(" " "hi")) (logstr errloc x)))
		(setq *error* prverr)
	)
	(defun txtspacestr ( / prverr )
		(setq prverr *error*)
		(setq *error* silent_err)
		(setq rc (foreach x (append '("hi" " ")) (logstr errloc x)))
		(setq *error* prverr)
	)
	(defun below0str ( / prverr )
		(setq prverr *error*)
		(setq *error* silent_err)
		(setq rc (foreach x (append '("/" "." "-" "," "+" "*" ")" "(" "'" "&" "%" "$" "#" "\"" "!")) (logstr errloc x)))
		(setq *error* prverr)
	)
	(defun below0strtxt ( / prverr )
		(setq prverr *error*)
		(setq *error* silent_err)
		(setq rc (foreach x (append '("!\"#$%&'()*+,-./" "hi")) (logstr errloc x)))
		(setq *error* prverr)
	)
	(defun txtbelow0str ( / prverr )
		(setq prverr *error*)
		(setq *error* silent_err)
		(setq rc (foreach x (append '("hi" "!\"#$%&'()*+,-./")) (logstr errloc x)))
		(setq *error* prverr)
	)
	(defun 0to9str ( / prverr )
		(setq prverr *error*)
		(setq *error* silent_err)
		(setq rc (foreach x (append '("9" "8" "7" "6" "5" "4" "3" "2" "1" "0")) (logstr errloc x)))
		(setq *error* prverr)
	)
	(defun 0to9strtxt ( / prverr )
		(setq prverr *error*)
		(setq *error* silent_err)
		(setq rc (foreach x (append '("0123456789" "hi")) (logstr errloc x)))
		(setq *error* prverr)
	)
	(defun txt0to9str ( / prverr )
		(setq prverr *error*)
		(setq *error* silent_err)
		(setq rc (foreach x (append '("hi" "0123456789")) (logstr errloc x)))
		(setq *error* prverr)
	)
	(defun above9str ( / prverr )
		(setq prverr *error*)
		(setq *error* silent_err)
		(setq rc (foreach x (append '("@" "?" ">" "=" "<" ";" ":")) (logstr errloc x)))
		(setq *error* prverr)
	)
	(defun above9strtxt ( / prverr )
		(setq prverr *error*)
		(setq *error* silent_err)
		(setq rc (foreach x (append '(":;<=>?@" "hi")) (logstr errloc x)))
		(setq *error* prverr)
	)
	(defun txtabove9str ( / prverr )
		(setq prverr *error*)
		(setq *error* silent_err)
		(setq rc (foreach x (append '("hi" ":;<=>?@")) (logstr errloc x)))
		(setq *error* prverr)
	)
	(defun bigatozstr ( / prverr )
		(setq prverr *error*)
		(setq *error* silent_err)
		(setq rc (foreach x (append '("Z" "Y" "X" "W" "V" "U" "T" "S" "R" "Q" "P" "O" "N" "M" "L" "K" "J" "I" "H" "G" "F" "E" "D" "C" "B" "A")) (logstr errloc x)))
		(setq *error* prverr)
	)
	(defun bigatozstrtxt ( / prverr )
		(setq prverr *error*)
		(setq *error* silent_err)
		(setq rc (foreach x (append '("ABCDEFGHIJKLMNOPQRSTUVWXYZ" "hi")) (logstr errloc x)))
		(setq *error* prverr)
	)
	(defun txtbigatozstr ( / prverr )
		(setq prverr *error*)
		(setq *error* silent_err)
		(setq rc (foreach x (append '("hi" "ABCDEFGHIJKLMNOPQRSTUVWXYZ")) (logstr errloc x)))
		(setq *error* prverr)
	)
	(defun btwnalphastr ( / prverr )
		(setq prverr *error*)
		(setq *error* silent_err)
		(setq rc (foreach x (append '("`" "_" "^" "]" "\\" "[")) (logstr errloc x)))
		(setq *error* prverr)
	)
	(defun btwnalphastrtxt ( / prverr )
		(setq prverr *error*)
		(setq *error* silent_err)
		(setq rc (foreach x (append '("[\\]^_`" "hi")) (logstr errloc x)))
		(setq *error* prverr)
	)
	(defun txtbtwnalphastr ( / prverr )
		(setq prverr *error*)
		(setq *error* silent_err)
		(setq rc (foreach x (append '("hi" "[\\]^_`")) (logstr errloc x)))
		(setq *error* prverr)
	)
	(defun smallatozstr ( / prverr )
		(setq prverr *error*)
		(setq *error* silent_err)
		(setq rc (foreach x (append '("z" "y" "x" "w" "v" "u" "t" "s" "r" "q" "p" "o" "n" "m" "l" "k" "j" "i" "h" "g" "f" "e" "d" "c" "b" "a")) (logstr errloc x)))
		(setq *error* prverr)
	)
	(defun smallatozstrtxt ( / prverr )
		(setq prverr *error*)
		(setq *error* silent_err)
		(setq rc (foreach x (append '("abcdefghijklmnopqrstuvwxyz" "hi")) (logstr errloc x)))
		(setq *error* prverr)
	)
	(defun txtsmallatozstr ( / prverr )
		(setq prverr *error*)
		(setq *error* silent_err)
		(setq rc (foreach x (append "hi" '("abcdefghijklmnopqrstuvwxyz")) (logstr errloc x)))
		(setq *error* prverr)
	)
	(defun abovezstr ( / prverr )
		(setq prverr *error*)
		(setq *error* silent_err)
		(setq rc (foreach x (append '("~" "}" "|" "{")) (logstr errloc x)))
		(setq *error* prverr)
	)
	(defun abovezstrtxt ( / prverr )
		(setq prverr *error*)
		(setq *error* silent_err)
		(setq rc (foreach x (append '("{|}~" "hi")) (logstr errloc x)))
		(setq *error* prverr)
	)
	(defun txtabovezstr ( / prverr )
		(setq prverr *error*)
		(setq *error* silent_err)
		(setq rc (foreach x (append '("hi" "{|}~")) (logstr errloc x)))
		(setq *error* prverr)
	)
	(defun nilsymstr ( / prverr )
		(setq prverr *error*)
		(setq *error* silent_err)
		(setq rc (foreach x (append '(nil)) (logstr errloc x)))
		(setq *error* prverr)
	)
	(defun nilsymstrtxt ( / prverr )
		(setq prverr *error*)
		(setq *error* silent_err)
		(setq rc (foreach x (append '(nil "hi")) (logstr errloc x)))
		(setq *error* prverr)
	)
	(defun txtnilsymstr ( / prverr )
		(setq prverr *error*)
		(setq *error* silent_err)
		(setq rc (foreach x (append '("hi" nil)) (logstr errloc x)))
		(setq *error* prverr)
	)
	(defun tsymstr ( / prverr )
		(setq prverr *error*)
		(setq *error* silent_err)
		(setq rc (foreach x (append '(t)) (logstr errloc x)))
		(setq *error* prverr)
	)
	(defun tsymstrtxt ( / prverr )
		(setq prverr *error*)
		(setq *error* silent_err)
		(setq rc (foreach x (append '(t "hi")) (logstr errloc x)))
		(setq *error* prverr)
	)
	(defun txttsymstr ( / prverr )
		(setq prverr *error*)
		(setq *error* silent_err)
		(setq rc (foreach x (append '("hi" t)) (logstr errloc x)))
		(setq *error* prverr)
	)
	(defun maxstr ( / prverr )
		(setq prverr *error*)
		(setq *error* silent_err)
		(setq rc (foreach x (append '("1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "5" "6" "7" "8" "9" "0" "1" "2" "3" "4" "5" "6" "7" "8" "9" "0" "1" "2")) (logstr errloc x)))
		(setq *error* prverr)
	)
	(defun maxstrtxt ( / prverr )
		(setq prverr *error*)
		(setq *error* silent_err)
		(setq rc (foreach x (append '("1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "5" "6" "7" "8" "9" "0" "1" "2" "3" "4" "5" "6" "7" "8" "9" "0" "1" "2" "hi")) (logstr errloc x)))
		(setq *error* prverr)
	)
	(defun txtmaxstr ( / prverr )
		(setq prverr *error*)
		(setq *error* silent_err)
		(setq rc (foreach x (append '("hi" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "5" "6" "7" "8" "9" "0" "1" "2" "3" "4" "5" "6" "7" "8" "9" "0" "1" "2")) (logstr errloc x)))
		(setq *error* prverr)
	)
	(defun maxp1str ( / prverr )
		(setq prverr *error*)
		(setq *error* silent_err)
		(setq rc (foreach x (append '("1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "5" "6" "7" "8" "9" "0" "1" "2" "3" "4" "5" "6" "7" "8" "9" "0" "1" "2" "3")) (logstr errloc x)))
		(setq *error* prverr)
	)
	(defun maxp1strtxt ( / prverr )
		(setq prverr *error*)
		(setq *error* silent_err)
		(setq rc (foreach x (append '("1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "5" "6" "7" "8" "9" "0" "1" "2" "3" "4" "5" "6" "7" "8" "9" "0" "1" "2" "3" "hi")) (logstr errloc x)))
		(setq *error* prverr)
	)
	(defun txtmaxp1str ( / prverr )
		(setq prverr *error*)
		(setq *error* silent_err)
		(setq rc (foreach x (append '("hi" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "4" "5" "6" "7" "8" "9" "0" "1" "2" "3" "5" "6" "7" "8" "9" "0" "1" "2" "3" "4" "5" "6" "7" "8" "9" "0" "1" "2" "3")) (logstr errloc x)))
		(setq *error* prverr)
	)
	;;; --------------------------------------------
	;;; numerics.
	;;; --------------------------------------------
	;;; valid inputs.
	(defun zero ( / prverr )
		(setq prverr *error*)
		(setq *error* silent_err)
		(setq rc (foreach x (append '(0)) (logflt errloc x)))
		(setq *error* prverr)
	)
	(defun nine ( / prverr )
		(setq prverr *error*)
		(setq *error* silent_err)
		(setq rc (foreach x (append '(9)) (logflt errloc x)))
		(setq *error* prverr)
	)
	(defun minuszero ( / prverr )
		(setq prverr *error*)
		(setq *error* silent_err)
		(setq rc (foreach x (append '(-0)) (logflt errloc x)))
		(setq *error* prverr)
	)
	(defun minusnine ( / prverr )
		(setq prverr *error*)
		(setq *error* silent_err)
		(setq rc (foreach x (append '(-9)) (logflt errloc x)))
		(setq *error* prverr)
	)
	;;; --------------------------------------------
	;;; invalid inputs.
	(defun belownum ( / prverr )
		(setq prverr *error*)
		(setq *error* silent_err)
		(setq rc (foreach x (append '("/")) (logstr errloc x)))
		(setq *error* prverr)
	)
	(defun abovenum ( / prverr )
		(setq prverr *error*)
		(setq *error* silent_err)
		(setq rc (foreach x (append '(":")) (logstr errloc x)))
		(setq *error* prverr)
	)
	(defun nilsym ( / prverr )
		(setq prverr *error*)
		(setq *error* silent_err)
		(setq rc (foreach x (append '(nil)) (logbool errloc x)))
		(setq *error* prverr)
	)
	(defun tsym ( / prverr )
		(setq prverr *error*)
		(setq *error* silent_err)
		(setq rc (foreach x (append '(t)) (logbool errloc x)))
		(setq *error* prverr)
	)
	;;; --------------------------------------------
	;;; integers.
	(defun zerozeroint ( / prverr )
		(setq prverr *error*)
		(setq *error* silent_err)
		(setq rc (foreach x (append '(0 0)) (logflt errloc x)))
		(setq *error* prverr)
	)
	(defun zerominint ( / prverr )
		(setq prverr *error*)
		(setq *error* silent_err)
		(setq rc (foreach x (append '(0 -2147483648)) (logflt errloc x)))
		(setq *error* prverr)
	)
	(defun minzeroint ( / prverr )
		(setq prverr *error*)
		(setq *error* silent_err)
		(setq rc (foreach x (append '(-2147483648 0)) (logflt errloc x)))
		(setq *error* prverr)
	)
	(defun zeromaxint ( / prverr )
		(setq prverr *error*)
		(setq *error* silent_err)
		(setq rc (foreach x (append '(0 2147483647)) (logflt errloc x)))
		(setq *error* prverr)
	)
	(defun maxzeroint ( / prverr )
		(setq prverr *error*)
		(setq *error* silent_err)
		(setq rc (foreach x (append '(2147483647 0)) (logflt errloc x)))
		(setq *error* prverr)
	)
	(defun oneminint ( / prverr )
		(setq prverr *error*)
		(setq *error* silent_err)
		(setq rc (foreach x (append '(1 -2147483648)) (logflt errloc x)))
		(setq *error* prverr)
	)
	(defun minoneint ( / prverr )
		(setq prverr *error*)
		(setq *error* silent_err)
		(setq rc (foreach x (append '(-2147483648 1)) (logflt errloc x)))
		(setq *error* prverr)
	)
	(defun onemaxint ( / prverr )
		(setq prverr *error*)
		(setq *error* silent_err)
		(setq rc (foreach x (append '(1 2147483647)) (logflt errloc x)))
		(setq *error* prverr)
	)
	(defun maxoneint ( / prverr )
		(setq prverr *error*)
		(setq *error* silent_err)
		(setq rc (foreach x (append '(2147483647 1)) (logflt errloc x)))
		(setq *error* prverr)
	)
	(defun zerominp1int ( / prverr )
		(setq prverr *error*)
		(setq *error* silent_err)
		(setq rc (foreach x (append '(0 -2147483649)) (logflt errloc x)))
		(setq *error* prverr)
	)
	(defun minp1zeroint ( / prverr )
		(setq prverr *error*)
		(setq *error* silent_err)
		(setq rc (foreach x (append '(-2147483649 0)) (logflt errloc x)))
		(setq *error* prverr)
	)
	(defun zeromaxp1int ( / prverr )
		(setq prverr *error*)
		(setq *error* silent_err)
		(setq rc (foreach x (append '(0 2147483648)) (logflt errloc x)))
		(setq *error* prverr)
	)
	(defun maxp1zeroint ( / prverr )
		(setq prverr *error*)
		(setq *error* silent_err)
		(setq rc (foreach x (append '(2147483648 0)) (logflt errloc x)))
		(setq *error* prverr)
	)
	(defun oneminp1int ( / prverr )
		(setq prverr *error*)
		(setq *error* silent_err)
		(setq rc (foreach x (append '(1 -2147483649)) (logflt errloc x)))
		(setq *error* prverr)
	)
	(defun minp1oneint ( / prverr )
		(setq prverr *error*)
		(setq *error* silent_err)
		(setq rc (foreach x (append '(-2147483649 1)) (logflt errloc x)))
		(setq *error* prverr)
	)
	(defun onemaxp1int ( / prverr )
		(setq prverr *error*)
		(setq *error* silent_err)
		(setq rc (foreach x (append '(1 2147483648)) (logflt errloc x)))
		(setq *error* prverr)
	)
	(defun maxp1oneint ( / prverr )
		(setq prverr *error*)
		(setq *error* silent_err)
		(setq rc (foreach x (append '(2147483648 1)) (logflt errloc x)))
		(setq *error* prverr)
	)
	;;; --------------------------------------------
	;;; reals.
	(defun zerozeroreal1 ( / prverr )
		(setq prverr *error*)
		(setq *error* silent_err)
		(setq rc (foreach x (append '(0 0.0)) (logflt errloc x)))
		(setq *error* prverr)
	)
	(defun zerozeroreal2 ( / prverr )
		(setq prverr *error*)
		(setq *error* silent_err)
		(setq rc (foreach x (append '(0.0 0)) (logflt errloc x)))
		(setq *error* prverr)
	)
	(defun zerominreal ( / prverr )
		(setq prverr *error*)
		(setq *error* silent_err)
		(setq rc (foreach x (append '(0 9.9e-324)) (logflt errloc x)))
		(setq *error* prverr)
	)
	(defun minzeroreal ( / prverr )
		(setq prverr *error*)
		(setq *error* silent_err)
		(setq rc (foreach x (append '(9.9e-324 0)) (logflt errloc x)))
		(setq *error* prverr)
	)
	(defun zeromaxreal ( / prverr )
		(setq prverr *error*)
		(setq *error* silent_err)
		(setq rc (foreach x (append '(0 9.9e307)) (logflt errloc x)))
		(setq *error* prverr)
	)
	(defun maxzeroreal ( / prverr )
		(setq prverr *error*)
		(setq *error* silent_err)
		(setq rc (foreach x (append '(9.9e307 0)) (logflt errloc x)))
		(setq *error* prverr)
	)
	(defun oneminreal ( / prverr )
		(setq prverr *error*)
		(setq *error* silent_err)
		(setq rc (foreach x (append '(1 9.9e-324)) (logflt errloc x)))
		(setq *error* prverr)
	)
	(defun minonereal ( / prverr )
		(setq prverr *error*)
		(setq *error* silent_err)
		(setq rc (foreach x (append '(9.9e-324 1)) (logflt errloc x)))
		(setq *error* prverr)
	)
	(defun onemaxreal ( / prverr )
		(setq prverr *error*)
		(setq *error* silent_err)
		(setq rc (foreach x (append '(1 9.9e307)) (logflt errloc x)))
		(setq *error* prverr)
	)
	(defun maxonereal ( / prverr )
		(setq prverr *error*)
		(setq *error* silent_err)
		(setq rc (foreach x (append '(9.9e307 1)) (logflt errloc x)))
		(setq *error* prverr)
	)
	(defun zerominp1real ( / prverr )
		(setq prverr *error*)
		(setq *error* silent_err)
		(setq rc (foreach x (append '(0 9.9e-325)) (logflt errloc x)))
		(setq *error* prverr)
	)
	(defun minp1zeroreal ( / prverr )
		(setq prverr *error*)
		(setq *error* silent_err)
		(setq rc (foreach x (append '(9.9e-325 0)) (logflt errloc x)))
		(setq *error* prverr)
	)
	(defun oneminp1real ( / prverr )
		(setq prverr *error*)
		(setq *error* silent_err)
		(setq rc (foreach x (append '(1 9.9e-325)) (logflt errloc x)))
		(setq *error* prverr)
	)
	(defun minp1onereal ( / prverr )
		(setq prverr *error*)
		(setq *error* silent_err)
		(setq rc (foreach x (append '(9.9e-325 1)) (logflt errloc x)))
		(setq *error* prverr)
	)

;;; ---------------------------------------------
;;; IntelliCAD help tests.
	(defun icadhlp1 ( / prverr )
		(setq prverr *error*)
		(setq *error* silent_err)
		(setq a '(1.0 1.5 2.0 2.5))
		(foreach rc a
			(progn
				(setq a (* 2.0 a))
				(logstr (strcat "\nTwice the value is " (rtos a)))
			)
		)
		(setq *error* prverr)
	)

;;; ---------------------------------------------
;;; AutoCAD help tests.
	(defun acadhlp1 ( / prverr )
		(setq prverr *error*)
		(setq *error* silent_err)
		(setq rc (foreach x '("a" "b" "c") (logstr errloc x)))
		(setq *error* prverr)
	)
