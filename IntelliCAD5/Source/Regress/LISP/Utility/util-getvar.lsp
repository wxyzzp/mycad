;;;
;;; Lisp Acceptance Test
;;;	Utility functions
;;;		getvar/setvar
;;;
;;; 17 Jun 98	MichaelHu
;;;
	(logmsg "")
	(load (strcat testscrdir "error"))
;;; ---------------------------------------------
;;; boundary tests.
	;;; ------------------------------------------
	;;; no arguments.
	(defun noargs ( / prverr )
		(setq prverr *error*)
		(setq *error* silent_err)
		(setq rc (getvar))
		(logall errloc rc)
		(setq rc (setvar))
		(logall errloc rc)
		(setq *error* prverr)
	)
	;;; --------------------------------------------
	;;; data types.
	;;; --------------------------------------------
	;;; valid inputs.
	(defun tfval ( / prverr )
		(setq prverr *error*)
		(setq *error* silent_err)
		(setq ori (getvar "angdir"))
		(logall errloc ori)
		(if (= 0 ori)
			(setq rc (setvar "angdir" 1))
			(setq rc (setvar "angdir" 0))
		)
		(logall errloc rc)
		(setvar "angdir" ori)
		(setq *error* prverr)
	)
	(defun tfinval ( / prverr )
		(setq prverr *error*)
		(setq *error* silent_err)
		(setq ori (getvar "angdir"))
		(logall errloc ori)
		(setq rc (setvar "angdir" 5))
		(logall errloc rc)
		(setvar "angdir" ori)
		(setq *error* prverr)
	)
	(command "._layer" "_new" "test" "")
	(defun strval ( / prverr )
		(setq prverr *error*)
		(setq *error* silent_err)
		(setq ori (getvar "clayer"))
		(logall errloc ori)
		(setq rc (setvar "clayer" "test"))
		(logall errloc rc)
		(setvar "clayer" ori)
		(setq *error* prverr)
	)
	(defun strinval ( / prverr )
		(setq prverr *error*)
		(setq *error* silent_err)
		(setq ori (getvar "clayer"))
		(logall errloc ori)
		(setq rc (setvar "clayer" "dummy_that_is_not_here"))
		(logall errloc rc)
		(setvar "clayer" ori)
		(setq *error* prverr)
	)
	(defun intval ( / prverr )
		(setq prverr *error*)
		(setq *error* silent_err)
		(setq ori (getvar "aperture"))
		(logall errloc ori)
		(setq rc (setvar "aperture" 42))
		(logall errloc rc)
		(setvar "aperture" ori)
		(setq *error* prverr)
	)
	(defun intinval ( / prverr )
		(setq prverr *error*)
		(setq *error* silent_err)
		(setq ori (getvar "aperture"))
		(logall errloc ori)
		(setq rc (setvar "aperture" -42))
		(logall errloc rc)
		(setvar "aperture" ori)
		(setq *error* prverr)
	)
	(defun realval ( / prverr )
		(setq prverr *error*)
		(setq *error* silent_err)
		(setq ori (getvar "celtscale"))
		(logall errloc ori)
		(setq rc (setvar "celtscale" 42))
		(logall errloc rc)
		(setvar "celtscale" ori)
		(setq *error* prverr)
	)
	(defun realinval ( / prverr )
		(setq prverr *error*)
		(setq *error* silent_err)
		(setq ori (getvar "celtscale"))
		(logall errloc ori)
		(setq rc (setvar "celtscale" -42))
		(logall errloc rc)
		(setvar "celtscale" ori)
		(setq *error* prverr)
	)
	(defun 2dptval ( / prverr )
		(setq prverr *error*)
		(setq *error* silent_err)
		(setq ori (getvar "limmax"))
		(logall errloc ori)
		(setq rc (setvar "limmax" '(42 42)))
		(logall errloc rc)
		(setvar "limmax" ori)
		(setq *error* prverr)
	)
	(defun 3dptval ( / prverr )
		(setq prverr *error*)
		(setq *error* silent_err)
		(setq ori (getvar "insbase"))
		(logall errloc ori)
		(setq rc (setvar "insbase" '(42 42 42)))
		(logall errloc rc)
		(setvar "insbase" ori)
		(setq *error* prverr)
	)
	(defun rdonly ( / prverr )
		(setq prverr *error*)
		(setq *error* silent_err)
		(setq ori (getvar "dwgprefix"))
		(logall errloc ori)
		(setq rc (setvar "dwgprefix" "hi_there"))
		(logall errloc rc)
		(setvar "dwgprefix" ori)
		(setq *error* prverr)
	)

;;; ---------------------------------------------
;;; IntelliCAD help tests.
	(defun icadhlp1 ( / prverr )
		(setq prverr *error*)
		(setq *error* silent_err)
		(setq ori (getvar "blipmode"))
		(logall errloc ori)
		(setq rc (setvar "blipmode" 0))
		(logall errloc rc)
		(setvar "blipmode" ori)
		(setq *error* prverr)
	)
	(defun icadhlp2 ( / prverr )
		(setq prverr *error*)
		(setq *error* silent_err)
		(setq ori (getvar "cmdecho"))
		(logall errloc ori)
		(if (= 0 ori)
			(setq rc (setvar "cmdecho" 1))
			(setq rc (setvar "cmdecho" 0))
		)
		(logall errloc rc)
		(setvar "cmdecho" ori)
		(setq *error* prverr)
	)
	(defun icadhlp3 ( / prverr )
		(setq prverr *error*)
		(setq *error* silent_err)
		(setq ori (getvar "gridunit"))
		(logall errloc ori)
		(setq rc (setvar "gridunit" '(1 1)))
		(logall errloc rc)
		(setvar "gridunit" ori)
		(setq *error* prverr)
	)
	(defun icadhlp4 ( / prverr )
		(setq prverr *error*)
		(setq *error* silent_err)
		(setq ori (getvar "insbase"))
		(logall errloc ori)
		(setq rc (setvar "insbase" '(1 2 3)))
		(logall errloc rc)
		(setvar "insbase" ori)
		(setq *error* prverr)
	)
	(defun icadhlp5 ( / prverr )
		(setq prverr *error*)
		(setq *error* silent_err)
		(setq ori (getvar "dwgname"))
		(logall errloc ori)
		(setq rc (setvar "dwgname" "drawing1"))
		(logall errloc rc)
		(setvar "dwgname" ori)
		(setq *error* prverr)
	)

;;; ---------------------------------------------
;;; AutoCAD help tests.
	(defun acadhlp1 ( / prverr )
		(setq prverr *error*)
		(setq *error* silent_err)
		(setq ori (getvar "FILLETRAD"))
		(logall errloc ori)
		(setq rc (setvar "FILLETRAD" 0.50))
		(logall errloc rc)
		(setvar "FILLETRAD" ori)
		(setq *error* prverr)
	)
