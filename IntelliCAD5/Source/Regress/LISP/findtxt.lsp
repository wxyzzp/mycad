(defun findtxt (ftxt stxt)
(setq ssftxt (ssget "X" (list (cons 0 "TEXT")(cons 1 ftxt))))
(princ (sslength ssftxt))
(princ)
(chtxt ssftxt stxt)
)
(defun chtxt(alltxt stxt)
(setq n 0)
(repeat (sslength alltxt)
(setq ent (entget (ssname alltxt n)))
(setq ent (subst (cons 1 stxt) (assoc 1 ent) ent))
(entmod ent)
(setq n (1+ n))
(princ "\nProcessing text no ")(princ n) (princ " Please wait....")(princ)
)
)
