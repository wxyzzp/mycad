(defun comparelist(explist actlist)
	(Setq i 1)
	(while (<= i (length explist))
		(if (equal (nth i explist) (nth i actlist) 0.00001) (princ i) (alert "ERR"))
		(setq i (1+ i))
 	)
)

(defun checkCoordList (explist)
  (setq le (entget (entlast)))
  (setq entcoords nil)
  (foreach co le
;  (princ co)
    (progn (if (= (car co) 10)
		(progn
;		    (princ (cadr co))
;		    (princ (caddr co))
;		    (setq entcoords (append entcoords (cadr co)))
		    (setq entcoords (append entcoords (list (cadr co) (caddr co))))

		)
	   )
    )
  )
	(princ entcoords)
(comparelist explist entcoords)
)
;___________4__________
(command "polygon" "4" "1,1" "i" "2,2")
(checkcoordlist (list 2.0 2.0 0.0 2.0 0.0 0.0 2.0 0.0))
(command "polygon" "4" "1,1" "c" "2,2")
(checkcoordlist (list 1.0 3.0 -1.0 1.0 1.0 -1.0 3.0 1.0))
(command "polygon" "4" "E" "2,2" "0,2")
(checkcoordlist (list 2.0 2.0 0.0 2.0 0.0 0.0 2.0 0.0))
(command "polygon" "4" "E" "1,3" "-1,1")
(checkcoordlist (list 1.0 3.0 -1.0 1.0 1.0 -1.0 3.0 1.0))
;______________6_________
(command "polygon" "6" "1,1" "i" "2,1")
(checkcoordlist (list 2.0 1.0 1.5 1.86603 0.5 1.86603 0.0 1.0 0.5 0.133975 1.5 0.133975))
(command "polygon" "6" "1,1" "c" "1,1.86603")
(checkcoordlist (list 0.5 1.86603 0.0 1.0 0.5 0.133975 1.5 0.133975 2.0 1.0 1.5 1.86603 ))
(command "polygon" "6" "E" "2,1" "1.5,1.86603")
(checkcoordlist (list 2.0 1.0 1.5 1.86603 0.5 1.86603 0.0 1.0 0.5 0.133975 1.5 0.133975))
(command "polygon" "6" "E" "0.5,1.86603" "0,1.0")
(checkcoordlist (list 0.5 1.86603 0.0 1.0 0.5 0.133975 1.5 0.133975 2.0 1.0 1.5 1.86603 ))
