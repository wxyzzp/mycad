(defun c:testDia()
	(setq 	i72  0
		i73  3
		i  0
	)
	(while (< i 15)
		(test)
		(If (= i73  0)
			(If (< i72 6)
				(setq i72 (+ i72 1))
			)
			(If (< i72 2)
				(setq i72 (+ i72 1))
				(setq i73 (- i73 1) i72 0)
			)
			    
		)
	(setq i (+ i 1))
	)
	(command "zoom" "extents")
)

(defun test()
	(setq strt (strcat (rtos i 2 0) " 72. " (rtos i72 2 0) " 73. " (rtos i73 2 0)))
	(command "color" (+ i 1))
	(command "Line" (list 0  i) (list 6  i) "")
	(command "Text" (list 4  i) "" "" strt)
	(command "Text" (list 2  i) "" "" strt)
	(setq en (entlast))
	(setq en1 (entget en))
	(setq en1 (subst (cons 73 i73) (assoc 73 en1) en1))
	(setq en1 (subst (cons 72 i72) (assoc 72 en1) en1))
	(setq en1 (subst (cons 10 (list 0 i)) (assoc 10 en1) en1))
	(setq en1 (subst (cons 11 (list 2 i)) (assoc 11 en1) en1))
	(entmod en1)
)
