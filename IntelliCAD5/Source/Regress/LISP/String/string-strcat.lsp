;;;
;;; Lisp Acceptance Test
;;;	String functions
;;;		strcat
;;;
;;; 17 Jun 98	MichaelHu
;;;
	(logmsg "")
	(load (strcat testscrdir "error"))

;;; ---------------------------------------------
;;; boundary tests.
	;;; ------------------------------------------
	;;; no arguments.
	(defun noargs ( / prverr )
		(setq prverr *error*)
		(setq *error* silent_err)
		(setq rc (strcat))
		(logstr errloc rc)
		(setq *error* prverr)
	)
	;;; --------------------------------------------
	;;; strings
	;;; --------------------------------------------
	;;; valid inputs.
	(defun emptystr ( / prverr )
		(setq prverr *error*)
		(setq *error* silent_err)
		(setq rc (strcat ""))
		(logstr errloc rc)
		(setq *error* prverr)
	)
	(defun emptyemptystr ( / prverr )
		(setq prverr *error*)
		(setq *error* silent_err)
		(setq rc (strcat "" ""))
		(logstr errloc rc)
		(setq *error* prverr)
	)
	(defun emptystrtxt ( / prverr )
		(setq prverr *error*)
		(setq *error* silent_err)
		(setq rc (strcat "" "hi"))
		(logstr errloc rc)
		(setq *error* prverr)
	)
	(defun txtemptystr ( / prverr )
		(setq prverr *error*)
		(setq *error* silent_err)
		(setq rc (strcat "hi" ""))
		(logstr errloc rc)
		(setq *error* prverr)
	)
	(defun spacestr ( / prverr )
		(setq prverr *error*)
		(setq *error* silent_err)
		(setq rc (strcat " "))
		(logstr errloc rc)
		(setq *error* prverr)
	)
	(defun spacestrtxt ( / prverr )
		(setq prverr *error*)
		(setq *error* silent_err)
		(setq rc (strcat " " "hi"))
		(logstr errloc rc)
		(setq *error* prverr)
	)
	(defun txtspacestr ( / prverr )
		(setq prverr *error*)
		(setq *error* silent_err)
		(setq rc (strcat "hi" " "))
		(logstr errloc rc)
		(setq *error* prverr)
	)
	(defun below0strs ( / prverr )
		(setq prverr *error*)
		(setq *error* silent_err)
		(setq rc (strcat "!"))
		(logstr errloc rc)
		(setq *error* prverr)
	)
	(defun below0stre ( / prverr )
		(setq prverr *error*)
		(setq *error* silent_err)
		(setq rc (strcat "/"))
		(logstr errloc rc)
		(setq *error* prverr)
	)
	(defun below0strtxt ( / prverr )
		(setq prverr *error*)
		(setq *error* silent_err)
		(setq rc (strcat "!\"#$%&'()*+,-./" "hi"))
		(logstr errloc rc)
		(setq *error* prverr)
	)
	(defun txtbelow0str ( / prverr )
		(setq prverr *error*)
		(setq *error* silent_err)
		(setq rc (strcat "hi" "!\"#$%&'()*+,-./"))
		(logstr errloc rc)
		(setq *error* prverr)
	)
	(defun 0to9strs ( / prverr )
		(setq prverr *error*)
		(setq *error* silent_err)
		(setq rc (strcat "0"))
		(logstr errloc rc)
		(setq *error* prverr)
	)
	(defun 0to9stre ( / prverr )
		(setq prverr *error*)
		(setq *error* silent_err)
		(setq rc (strcat "9"))
		(logstr errloc rc)
		(setq *error* prverr)
	)
	(defun 0to9strtxt ( / prverr )
		(setq prverr *error*)
		(setq *error* silent_err)
		(setq rc (strcat "0123456789" "hi"))
		(logstr errloc rc)
		(setq *error* prverr)
	)
	(defun txt0to9str ( / prverr )
		(setq prverr *error*)
		(setq *error* silent_err)
		(setq rc (strcat "hi" "0123456789"))
		(logstr errloc rc)
		(setq *error* prverr)
	)
	(defun above9strs ( / prverr )
		(setq prverr *error*)
		(setq *error* silent_err)
		(setq rc (strcat ":"))
		(logstr errloc rc)
		(setq *error* prverr)
	)
	(defun above9stre ( / prverr )
		(setq prverr *error*)
		(setq *error* silent_err)
		(setq rc (strcat "@"))
		(logstr errloc rc)
		(setq *error* prverr)
	)
	(defun above9strtxt ( / prverr )
		(setq prverr *error*)
		(setq *error* silent_err)
		(setq rc (strcat ":;<=>?@" "hi"))
		(logstr errloc rc)
		(setq *error* prverr)
	)
	(defun txtabove9str ( / prverr )
		(setq prverr *error*)
		(setq *error* silent_err)
		(setq rc (strcat "hi" ":;<=>?@"))
		(logstr errloc rc)
		(setq *error* prverr)
	)
	(defun bigatozstrs ( / prverr )
		(setq prverr *error*)
		(setq *error* silent_err)
		(setq rc (strcat "A"))
		(logstr errloc rc)
		(setq *error* prverr)
	)
	(defun bigatozstre ( / prverr )
		(setq prverr *error*)
		(setq *error* silent_err)
		(setq rc (strcat "Z"))
		(logstr errloc rc)
		(setq *error* prverr)
	)
	(defun bigatozstrtxt ( / prverr )
		(setq prverr *error*)
		(setq *error* silent_err)
		(setq rc (strcat "ABCDEFGHIJKLMNOPQRSTUVWXYZ" "hi"))
		(logstr errloc rc)
		(setq *error* prverr)
	)
	(defun txtbigatozstr ( / prverr )
		(setq prverr *error*)
		(setq *error* silent_err)
		(setq rc (strcat "hi" "ABCDEFGHIJKLMNOPQRSTUVWXYZ"))
		(logstr errloc rc)
		(setq *error* prverr)
	)
	(defun btwnalphastrs ( / prverr )
		(setq prverr *error*)
		(setq *error* silent_err)
		(setq rc (strcat "["))
		(logstr errloc rc)
		(setq *error* prverr)
	)
	(defun btwnalphastre ( / prverr )
		(setq prverr *error*)
		(setq *error* silent_err)
		(setq rc (strcat "`"))
		(logstr errloc rc)
		(setq *error* prverr)
	)
	(defun btwnalphastrtxt ( / prverr )
		(setq prverr *error*)
		(setq *error* silent_err)
		(setq rc (strcat "[\\]^_`" "hi"))
		(logstr errloc rc)
		(setq *error* prverr)
	)
	(defun txtbtwnalphastr ( / prverr )
		(setq prverr *error*)
		(setq *error* silent_err)
		(setq rc (strcat "hi" "[\\]^_`"))
		(logstr errloc rc)
		(setq *error* prverr)
	)
	(defun smallatozstrs ( / prverr )
		(setq prverr *error*)
		(setq *error* silent_err)
		(setq rc (strcat "a"))
		(logstr errloc rc)
		(setq *error* prverr)
	)
	(defun smallatozstre ( / prverr )
		(setq prverr *error*)
		(setq *error* silent_err)
		(setq rc (strcat "z"))
		(logstr errloc rc)
		(setq *error* prverr)
	)
	(defun smallatozstrtxt ( / prverr )
		(setq prverr *error*)
		(setq *error* silent_err)
		(setq rc (strcat "abcdefghijklmnopqrstuvwxyz" "hi"))
		(logstr errloc rc)
		(setq *error* prverr)
	)
	(defun txtsmallatozstr ( / prverr )
		(setq prverr *error*)
		(setq *error* silent_err)
		(setq rc (strcat "hi" "abcdefghijklmnopqrstuvwxyz"))
		(logstr errloc rc)
		(setq *error* prverr)
	)
	(defun abovezstrs ( / prverr )
		(setq prverr *error*)
		(setq *error* silent_err)
		(setq rc (strcat "{"))
		(logstr errloc rc)
		(setq *error* prverr)
	)
	(defun abovezstre ( / prverr )
		(setq prverr *error*)
		(setq *error* silent_err)
		(setq rc (strcat "~"))
		(logstr errloc rc)
		(setq *error* prverr)
	)
	(defun abovezstrtxt ( / prverr )
		(setq prverr *error*)
		(setq *error* silent_err)
		(setq rc (strcat "{|}~" "hi"))
		(logstr errloc rc)
		(setq *error* prverr)
	)
	(defun txtabovezstr ( / prverr )
		(setq prverr *error*)
		(setq *error* silent_err)
		(setq rc (strcat "hi" "{|}~"))
		(logstr errloc rc)
		(setq *error* prverr)
	)
	(defun nilsymstr ( / prverr )
		(setq prverr *error*)
		(setq *error* silent_err)
		(setq rc (strcat nil))
		(logstr errloc rc)
		(setq *error* prverr)
	)
	(defun nilsymstrtxt ( / prverr )
		(setq prverr *error*)
		(setq *error* silent_err)
		(setq rc (strcat nil "hi"))
		(logstr errloc rc)
		(setq *error* prverr)
	)
	(defun txtnilsymstr ( / prverr )
		(setq prverr *error*)
		(setq *error* silent_err)
		(setq rc (strcat "hi" nil))
		(logstr errloc rc)
		(setq *error* prverr)
	)
	(defun tsymstr ( / prverr )
		(setq prverr *error*)
		(setq *error* silent_err)
		(setq rc (strcat t))
		(logstr errloc rc)
		(setq *error* prverr)
	)
	(defun tsymstrtxt ( / prverr )
		(setq prverr *error*)
		(setq *error* silent_err)
		(setq rc (strcat t "hi"))
		(logstr errloc rc)
		(setq *error* prverr)
	)
	(defun txttsymstr ( / prverr )
		(setq prverr *error*)
		(setq *error* silent_err)
		(setq rc (strcat "hi" t))
		(logstr errloc rc)
		(setq *error* prverr)
	)
	(defun maxstr ( / prverr )
		(setq prverr *error*)
		(setq *error* silent_err)
		(setq rc (strcat "123456789012345678901234567890123456789012345678901234567890123456789012345678901234567890123456789012345678901234567890123456789012"))
		(logstr errloc rc)
		(setq *error* prverr)
	)
	(defun maxstrtxt ( / prverr )
		(setq prverr *error*)
		(setq *error* silent_err)
		(setq rc (strcat "123456789012345678901234567890123456789012345678901234567890123456789012345678901234567890123456789012345678901234567890123456789012" "hi"))
		(logstr errloc rc)
		(setq *error* prverr)
	)
	(defun txtmaxstr ( / prverr )
		(setq prverr *error*)
		(setq *error* silent_err)
		(setq rc (strcat "hi" "123456789012345678901234567890123456789012345678901234567890123456789012345678901234567890123456789012345678901234567890123456789012"))
		(logstr errloc rc)
		(setq *error* prverr)
	)
	(defun maxp1str ( / prverr )
		(setq prverr *error*)
		(setq *error* silent_err)
		(setq rc (strcat "1234567890123456789012345678901234567890123456789012345678901234567890123456789012345678901234567890123456789012345678901234567890123"))
		(logstr errloc rc)
		(setq *error* prverr)
	)
	(defun maxp1strtxt ( / prverr )
		(setq prverr *error*)
		(setq *error* silent_err)
		(setq rc (strcat "1234567890123456789012345678901234567890123456789012345678901234567890123456789012345678901234567890123456789012345678901234567890123" "hi"))
		(logstr errloc rc)
		(setq *error* prverr)
	)
	(defun txtmaxp1str ( / prverr )
		(setq prverr *error*)
		(setq *error* silent_err)
		(setq rc (strcat "hi" "1234567890123456789012345678901234567890123456789012345678901234567890123456789012345678901234567890123456789012345678901234567890123"))
		(logstr errloc rc)
		(setq *error* prverr)
	)
	(defun plusedgestr ( / prverr )
		(setq prverr *error*)
		(setq *error* silent_err)
		(setq rc (strcat "123456789012345678901234567890123456789012345678901234567890123456" "1234567890123456789012345678901234567890123456789012345678901234567"))
		(logstr errloc rc)
		(setq *error* prverr)
	)
	(defun plusoverstr ( / prverr )
		(setq prverr *error*)
		(setq *error* silent_err)
		(setq rc (strcat "1234567890123456789012345678901234567890123456789012345678901234567" "1234567890123456789012345678901234567890123456789012345678901234567"))
		(logstr errloc rc)
		(setq *error* prverr)
	)

;;; ---------------------------------------------
;;; IntelliCAD help tests.
	(defun icadhlp1 ( / prverr )
		(setq prverr *error*)
		(setq *error* silent_err)
		(setq rc (strcat "Jack and Jill" "went up the hill"))
		(logstr errloc rc)
		(setq *error* prverr)
	)
	(defun icadhlp2 ( / prverr )
		(setq prverr *error*)
		(setq *error* silent_err)
		(setq rc (strcat "The radius is " (rtos 7.0)))
		(logstr errloc rc)
		(setq *error* prverr)
	)

;;; ---------------------------------------------
;;; AutoCAD help tests.
	(defun acadhlp1 ( / prverr )
		(setq prverr *error*)
		(setq *error* silent_err)
		(setq rc (strcat "a" "bout"))
		(logstr errloc rc)
		(setq *error* prverr)
	)
	(defun acadhlp2 ( / prverr )
		(setq prverr *error*)
		(setq *error* silent_err)
		(setq rc (strcat "a" "b" "c"))
		(logstr errloc rc)
		(setq *error* prverr)
	)
	(defun acadhlp3 ( / prverr )
		(setq prverr *error*)
		(setq *error* silent_err)
		(setq rc (strcat "a" "" "c"))
		(logstr errloc rc)
		(setq *error* prverr)
	)
