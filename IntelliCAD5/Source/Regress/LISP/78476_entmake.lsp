;_This_LISP_is_created_by_Srinivas_Chavan
(defun c:entmake_78476()
(entmake '((0 . "LEADER") (5 . "4A") (100 . "AcDbEntity") (67 . 0) (410 . "Model") (8 . "0") (100 . "AcDbLeader") (3 . "Standard") (71 . 1) (72 . 0) (73 . 0) (74 . 0) (75 . 1) (40 . 0.18) (41 . 0.48) (76 . 3) (10 8.69542 3.38115 1.0) (10 12.7801 72.87234 2.0) (10 12.9601 7.2334 -31.0) (10 12.9601 7.87234 21.0) (211 1.0 0.0 0.0) (210 0.0 0.0 1.0) (212 0.0 0.0 0.0) (213 0.0 0.0 0.0)))
(checkleader)
(entmake '((0 . "LEADER") (5 . "4A") (100 . "AcDbEntity") (67 . 0) (410 . "Model") (8 . "0") (100 . "AcDbLeader") (3 . "Standard") (71 . 1) (72 . 0) (73 . 0) (74 . 0) (75 . 1) (40 . 0.18) (41 . 0.48) (76 . 3) (10 82.69542 32.38115 1.0) (10 122.7801 7.87234 12.0) (10 12.9601 7.87234 -14.0) (10 1.9601 7.34 -14.0) (211 1.0 0.0 0.0) (210 0.0 0.0 1.0) (212 0.0 0.0 0.0) (213 0.0 0.0 0.0)))
(checkleader)
(entmake '((0 . "LEADER") (5 . "4A") (100 . "AcDbEntity") (67 . 0) (410 . "Model") (8 . "0") (100 . "AcDbLeader") (3 . "Standard") (71 . 1) (72 . 0) (73 . 0) (74 . 0) (75 . 1) (40 . 0.18) (41 . 0.48) (76 . 3) (10 8.69542 3.38115 122.0) (10 12.7801 7.87234 2.20) (10 122.9601 7.87234 -41.0) (10 12.9601 7.87234 1.0) (211 1.0 0.0 0.0) (210 0.0 0.0 1.0) (212 0.0 0.0 0.0) (213 0.0 0.0 0.0)))
(checkleader)
)

(defun checkleader ()
  (setq le (entget (entlast)))
  (setq coordoffirst (cadddr (assoc 10 le)))
  (foreach co le
    (progn (if (= (car co) 10)
	     (if (/= coordoffirst (cadddr co))
	       (alert "Err")
	     )
	   )
    )
  )
)
