;;;;;;;;;;Created_by_Cybage_on_2:29PM7/15/2002;;;;;;;;;;
(defun c:Cardiod()
(command 	"limits" (list 0 0) (list 200 200)
		"zoom" "a")
(setq j 40.0)
(setq pt1 (getpoint "\nEnter Center point:"))
(command "circle" pt1 j)
(setq i 0)
(setq k 1)
(while (<= i 720)
	(setq x1 (* 30 (cos (/ (* i pi) 360.0)))
	      y1 (* 30 (sin (/ (* i pi) 360.0)))
		x2 (expt (+ x1 j) 2)
		y2 (expt y1 2)
		r1 (expt (+ x2 y2) 0.5)
		pt2x (+ x1 (car pt1))
		pt2y (+ y1 (cadr pt1))
		pt2 (list pt2x pt2y)
	)
(command "color" k)
(command "circle" pt2 r1)
(setq i (+ i 15))
(setq k (+ k 1))
)
)
