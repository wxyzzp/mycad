(defun c:64188_Base()
(Command "line" 
		(list 7 2) (list 7 5) (list 6 5) (list 6 8) (list 7 8) (list 7 10) (list 5 10)
		(list 5 12) (list 6 12) (list 6 13) (list 3 13) (list 3 12) (list 4 12) 
		(list 4 10)	 (list 2 10) (list 2 8) (list 4 8) (list 4 6) (list 2 6) 
		(list 2 3) (list 6 3) (list 6 1) (list 8 1) (list 8 2) (list 7 2) ""
	"dimaligned" (list 8 1) (list 8 2) (list 9 2)
	"dimbaseline" (list 7 5) (list 7 8) (list 7 10) (list 6 12) (list 6 13) "" ""
	"dimaligned" (list 3 13) (list 3 12) (list 1 12)
	"dimbaseline" (list 2 10) (list 2 8) (list 2 6) (list 2 3) (list  6 1) "" ""
)
)
